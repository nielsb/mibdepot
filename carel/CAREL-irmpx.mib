--
-- CAREL-irmpx.MIB
-- MIB generated by CAREL
-- Friday, 14 March 2003
--

    CAREL-irmpx-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        irmpxMIB MODULE-IDENTITY
      		LAST-UPDATED  "200303141724Z"		-- March 14, 2003 at 17:24 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the irmpx device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- irmpxMIB OBJECT IDENTIFIER ::= { instruments 1 }
		
        -- 1.3.6.1.4.1.9839.2.1.1
        digitalObjects OBJECT IDENTIFIER ::= { irmpxMIB 1 }

        -- 1.3.6.1.4.1.9839.2.1.1.1
        dig-output1 OBJECT-TYPE
                    SYNTAX Integer32 (0..1)
                    UNITS "N/A"
                    MAX-ACCESS read-only
                    STATUS current
                    DESCRIPTION "Compressor"
                    ::= { digitalObjects 1 }

        -- 1.3.6.1.4.1.9839.2.1.1.2
        dig-output2 OBJECT-TYPE
                    SYNTAX Integer32 (0..1)
                    UNITS "N/A"
                    MAX-ACCESS read-only
                    STATUS current
                    DESCRIPTION "Defrost"
                    ::= { digitalObjects 2 }

        -- 1.3.6.1.4.1.9839.2.1.1.3
        dig-output3 OBJECT-TYPE
                    SYNTAX Integer32 (0..1)
                    UNITS "N/A"
                    MAX-ACCESS read-only
                    STATUS current
                    DESCRIPTION "Fan"
                    DEFVAL { 0 }
                    ::= { digitalObjects 3 }

        -- 1.3.6.1.4.1.9839.2.1.1.4
        dig-output4 OBJECT-TYPE
                    SYNTAX Integer32 (0..1)
                    UNITS "N/A"
                    MAX-ACCESS read-only
                    STATUS current
                    DESCRIPTION "Aux"
                    ::= { digitalObjects 4 }

        -- 1.3.6.1.4.1.9839.2.1.1.11
        dig-input1 OBJECT-TYPE
                    SYNTAX Integer32 (0..1)
                    UNITS "N/A"
                    MAX-ACCESS read-only
                    STATUS current
                    DESCRIPTION "Digital input 1"
                    ::= { digitalObjects 11 }

        -- 1.3.6.1.4.1.9839.2.1.1.12
        dig-input2 OBJECT-TYPE
                    SYNTAX Integer32 (0..1)
                    UNITS "N/A"
                    MAX-ACCESS read-only
                    STATUS current
                    DESCRIPTION "Digital input 2"
                    ::= { digitalObjects 12 }

        -- 1.3.6.1.4.1.9839.2.1.1.21
        ko-b1 OBJECT-TYPE
                    SYNTAX Integer32 (0..1)
                    UNITS "N/A"
                    MAX-ACCESS read-only
                    STATUS current
                    DESCRIPTION "Room temperature probe demaged or not connected"
                    ::= { digitalObjects 21 }

        -- 1.3.6.1.4.1.9839.2.1.1.22
        ko-b2 OBJECT-TYPE
                    SYNTAX Integer32 (0..1)
                    UNITS "N/A"
                    MAX-ACCESS read-only
                    STATUS current
                    DESCRIPTION "Defrost temperature probe demaged or not connected"
                    ::= { digitalObjects 22 }

        -- 1.3.6.1.4.1.9839.2.1.1.23
        id-al-immdt-sel OBJECT-TYPE
                    SYNTAX Integer32 (0..1)
                    UNITS "N/A"
                    MAX-ACCESS read-only
                    STATUS current
                    DESCRIPTION "Immediate external alarm (ai)"
                    ::= { digitalObjects 23 }

        -- 1.3.6.1.4.1.9839.2.1.1.24
        id-al-dlyd-sel OBJECT-TYPE
                    SYNTAX Integer32 (0..1)
                    UNITS "N/A"
                    MAX-ACCESS read-only
                    STATUS current
                    DESCRIPTION "Delayed external alarm (ad)"
                    ::= { digitalObjects 24 }

        -- 1.3.6.1.4.1.9839.2.1.1.25
        lowt OBJECT-TYPE
                    SYNTAX Integer32 (0..1)
                    UNITS "N/A"
                    MAX-ACCESS read-only
                    STATUS current
                    DESCRIPTION "Room low temperature"
                    ::= { digitalObjects 25 }

        -- 1.3.6.1.4.1.9839.2.1.1.26
        hight OBJECT-TYPE
                    SYNTAX Integer32 (0..1)
                    UNITS "N/A"
                    MAX-ACCESS read-only
                    STATUS current
                    DESCRIPTION "Room high temperature"
                    ::= { digitalObjects 26 }

        -- 1.3.6.1.4.1.9839.2.1.1.27
        def-al OBJECT-TYPE
                    SYNTAX Integer32 (0..1)
                    UNITS "N/A"
                    MAX-ACCESS read-only
                    STATUS current
                    DESCRIPTION "Defrost by time-out"
                    ::= { digitalObjects 27 }

        -- 1.3.6.1.4.1.9839.2.1.1.37
        lost1 OBJECT-TYPE
                    SYNTAX Integer32 (0..1)
                    UNITS "N/A"
                    MAX-ACCESS read-only
                    STATUS current
                    DESCRIPTION "Slave 1 offline"
                    ::= { digitalObjects 37 }

        -- 1.3.6.1.4.1.9839.2.1.1.38
        lost2 OBJECT-TYPE
                    SYNTAX Integer32 (0..1)
                    UNITS "N/A"
                    MAX-ACCESS read-only
                    STATUS current
                    DESCRIPTION "Slave 2 offline"
                    ::= { digitalObjects 38 }

        -- 1.3.6.1.4.1.9839.2.1.1.39
        lost3 OBJECT-TYPE
                    SYNTAX Integer32 (0..1)
                    UNITS "N/A"
                    MAX-ACCESS read-only
                    STATUS current
                    DESCRIPTION "Slave 3 offline"
                    ::= { digitalObjects 39 }

        -- 1.3.6.1.4.1.9839.2.1.1.40
        lost4 OBJECT-TYPE
                    SYNTAX Integer32 (0..1)
                    UNITS "N/A"
                    MAX-ACCESS read-only
                    STATUS current
                    DESCRIPTION "Slave 4 offline"
                    ::= { digitalObjects 40 }

        -- 1.3.6.1.4.1.9839.2.1.1.41
        lost5 OBJECT-TYPE
                    SYNTAX Integer32 (0..1)
                    UNITS "N/A"
                    MAX-ACCESS read-only
                    STATUS current
                    DESCRIPTION "Slave 5 offline"
                    ::= { digitalObjects 41 }

        -- 1.3.6.1.4.1.9839.2.1.1.42
        lostm OBJECT-TYPE
                    SYNTAX Integer32 (0..1)
                    UNITS "N/A"
                    MAX-ACCESS read-only
                    STATUS current
                    DESCRIPTION "Master offline"
                    ::= { digitalObjects 42 }

        -- 1.3.6.1.4.1.9839.2.1.1.43
        rtc-al OBJECT-TYPE
                    SYNTAX Integer32 (0..1)
                    UNITS "N/A"
                    MAX-ACCESS read-only
                    STATUS current
                    DESCRIPTION "Real time clock error"
                    ::= { digitalObjects 43 }

        -- 1.3.6.1.4.1.9839.2.1.1.45
        rem1 OBJECT-TYPE
                    SYNTAX Integer32 (0..1)
                    UNITS "N/A"
                    MAX-ACCESS read-only
                    STATUS current
                    DESCRIPTION "Remote alarm on slave 1"
                    ::= { digitalObjects 45 }

        -- 1.3.6.1.4.1.9839.2.1.1.46
        rem2 OBJECT-TYPE
                    SYNTAX Integer32 (0..1)
                    UNITS "N/A"
                    MAX-ACCESS read-only
                    STATUS current
                    DESCRIPTION "Remote alarm on slave 2"
                    ::= { digitalObjects 46 }

        -- 1.3.6.1.4.1.9839.2.1.1.47
        rem3 OBJECT-TYPE
                    SYNTAX Integer32 (0..1)
                    UNITS "N/A"
                    MAX-ACCESS read-only
                    STATUS current
                    DESCRIPTION "Remote alarm on slave 3"
                    ::= { digitalObjects 47 }

        -- 1.3.6.1.4.1.9839.2.1.1.48
        rem4 OBJECT-TYPE
                    SYNTAX Integer32 (0..1)
                    UNITS "N/A"
                    MAX-ACCESS read-only
                    STATUS current
                    DESCRIPTION "Remote alarm on slave 4"
                    ::= { digitalObjects 48 }

        -- 1.3.6.1.4.1.9839.2.1.1.49
        rem5 OBJECT-TYPE
                    SYNTAX Integer32 (0..1)
                    UNITS "N/A"
                    MAX-ACCESS read-only
                    STATUS current
                    DESCRIPTION "Remote alarm on slave 5"
                    ::= { digitalObjects 49 }

        -- 1.3.6.1.4.1.9839.2.1.1.60
        def-cmd OBJECT-TYPE
                    SYNTAX Integer32 (0..1)
                    UNITS "N/A"
                    MAX-ACCESS read-write
                    STATUS current
                    DESCRIPTION "Defrost command"
                    DEFVAL { 0 }
                    ::= { digitalObjects 60 }



        -- 1.3.6.1.4.1.9839.2.1.2
        analogObjects OBJECT IDENTIFIER ::= { irmpxMIB 2 }

        -- 1.3.6.1.4.1.9839.2.1.2.1
        probe1 OBJECT-TYPE
                    SYNTAX Integer32 (-32767..32767)
                    UNITS "°C x10"
                    MAX-ACCESS read-only
                    STATUS current
                    DESCRIPTION "Room temperature"
                    ::= { analogObjects 1 }

        -- 1.3.6.1.4.1.9839.2.1.2.2
        probe2 OBJECT-TYPE
                    SYNTAX Integer32 (-32767..32767)
                    UNITS "°C x10"
                    MAX-ACCESS read-only
                    STATUS current
                    DESCRIPTION "Evaporator temperature"
                    ::= { analogObjects 2 }

        -- 1.3.6.1.4.1.9839.2.1.2.3
        probe3 OBJECT-TYPE
                    SYNTAX Integer32 (-32767..32767)
                    UNITS "°C x10"
                    MAX-ACCESS read-only
                    STATUS current
                    DESCRIPTION "3rd probe"
                    ::= { analogObjects 3 }

        -- 1.3.6.1.4.1.9839.2.1.2.7
        temp-setp-st OBJECT-TYPE
                    SYNTAX Integer32 (-32767..32767)
                    UNITS "°C/°F x10"
                    MAX-ACCESS read-write
                    STATUS current
                    DESCRIPTION "Set-point"
                    DEFVAL { -100 }
                    ::= { analogObjects 7 }

        -- 1.3.6.1.4.1.9839.2.1.2.8
        probe1-cal--c OBJECT-TYPE
                    SYNTAX Integer32 (-200..200)
                    UNITS "°C/°F x10"
                    MAX-ACCESS read-write
                    STATUS current
                    DESCRIPTION "Regulation probe calibration"
                    DEFVAL { 0 }
                    ::= { analogObjects 8 }

        -- 1.3.6.1.4.1.9839.2.1.2.15
        probe3-cal--8 OBJECT-TYPE
                    SYNTAX Integer32 (-200..200)
                    UNITS "°C/°F x10"
                    MAX-ACCESS read-write
                    STATUS current
                    DESCRIPTION "3rd probe calibration"
                    DEFVAL { 0 }
                    ::= { analogObjects 15 }

        -- 1.3.6.1.4.1.9839.2.1.2.17
        probe2-cal--d OBJECT-TYPE
                    SYNTAX Integer32 (-200..200)
                    UNITS "°C/°F x10"
                    MAX-ACCESS read-write
                    STATUS current
                    DESCRIPTION "Defrost probe calibration"
                    DEFVAL { 0 }
                    ::= { analogObjects 17 }

        -- 1.3.6.1.4.1.9839.2.1.2.19
        temp-diff-rd OBJECT-TYPE
                    SYNTAX Integer32 (1..199)
                    UNITS "°C/°F x10"
                    MAX-ACCESS read-write
                    STATUS current
                    DESCRIPTION "Regulator differential"
                    DEFVAL { 20 }
                    ::= { analogObjects 19 }

        -- 1.3.6.1.4.1.9839.2.1.2.23
        aut-ngt-set-r4 OBJECT-TYPE
                    SYNTAX Integer32 (-200..200)
                    UNITS "°C/°F x10"
                    MAX-ACCESS read-write
                    STATUS current
                    DESCRIPTION "Set point variation by digital imput"
                    DEFVAL { 30 }
                    ::= { analogObjects 23 }

        -- 1.3.6.1.4.1.9839.2.1.2.27
        t-max-tm-rt-rh OBJECT-TYPE
                    SYNTAX Integer32 (-32767..32767)
                    UNITS "°C/°F x10"
                    MAX-ACCESS read-only
                    STATUS current
                    DESCRIPTION "Maximum temperature measured in rt interval"
                    ::= { analogObjects 27 }

        -- 1.3.6.1.4.1.9839.2.1.2.28
        t-min-tm-rt-rl OBJECT-TYPE
                    SYNTAX Integer32 (-32767..32767)
                    UNITS "°C/°F x10"
                    MAX-ACCESS read-only
                    STATUS current
                    DESCRIPTION "Minimum temperature measured in rt interval"
                    ::= { analogObjects 28 }

        -- 1.3.6.1.4.1.9839.2.1.2.46
        vis-temp-def-d OBJECT-TYPE
                    SYNTAX Integer32 (-32767..32767)
                    UNITS "°C/°F x10"
                    MAX-ACCESS read-only
                    STATUS current
                    DESCRIPTION "1st defrost probe display (probe 1)"
                    ::= { analogObjects 46 }

        -- 1.3.6.1.4.1.9839.2.1.2.47
        vis-temp-3-da OBJECT-TYPE
                    SYNTAX Integer32 (-32767..32767)
                    UNITS "°C/°F x10"
                    MAX-ACCESS read-only
                    STATUS current
                    DESCRIPTION "2nd defrost probe display (probe3)"
                    ::= { analogObjects 47 }

        -- 1.3.6.1.4.1.9839.2.1.2.49
        fan-alrm-dif-a0 OBJECT-TYPE
                    SYNTAX Integer32 (1..200)
                    UNITS "°C/°F x10"
                    MAX-ACCESS read-write
                    STATUS current
                    DESCRIPTION "Fan and alarm differential"
                    DEFVAL { 2 }
                    ::= { analogObjects 49 }

        -- 1.3.6.1.4.1.9839.2.1.2.61
        fan-on-temp-f1 OBJECT-TYPE
                    SYNTAX Integer32 (-400..500)
                    UNITS "°C/°F x10"
                    MAX-ACCESS read-write
                    STATUS current
                    DESCRIPTION "Fan starting absolute setpoint"
                    ::= { analogObjects 61 }



        -- 1.3.6.1.4.1.9839.2.1.3
        integerObjects OBJECT IDENTIFIER ::= { irmpxMIB 3 }

        -- 1.3.6.1.4.1.9839.2.1.3.9
        msrmnt-stab--2 OBJECT-TYPE
                    SYNTAX Integer32 (1..15)
                    UNITS "N/A"
                    MAX-ACCESS read-write
                    STATUS current
                    DESCRIPTION "Measurement stability"
                    DEFVAL { 4 }
                    ::= { integerObjects 9 }

        -- 1.3.6.1.4.1.9839.2.1.3.10
        prb-read-spd--3 OBJECT-TYPE
                    SYNTAX Integer32 (1..15)
                    UNITS "N/A"
                    MAX-ACCESS read-write
                    STATUS current
                    DESCRIPTION "Probe reading rate"
                    DEFVAL { 8 }
                    ::= { integerObjects 10 }

        -- 1.3.6.1.4.1.9839.2.1.3.11
        prb-virtual--4 OBJECT-TYPE
                    SYNTAX Integer32 (0..100)
                    UNITS "N/A"
                    MAX-ACCESS read-write
                    STATUS current
                    DESCRIPTION "Virtual probe"
                    DEFVAL { 0 }
                    ::= { integerObjects 11 }

        -- 1.3.6.1.4.1.9839.2.1.3.12
        unit-msrmnt--5 OBJECT-TYPE
                    SYNTAX Integer32 (0..1)
                    UNITS "flag"
                    MAX-ACCESS read-write
                    STATUS current
                    DESCRIPTION "°C/°F"
                    DEFVAL { 0 }
                    ::= { integerObjects 12 }

        -- 1.3.6.1.4.1.9839.2.1.3.13
        en-dec-point--6 OBJECT-TYPE
                    SYNTAX Integer32 (0..1)
                    UNITS "flag"
                    MAX-ACCESS read-write
                    STATUS current
                    DESCRIPTION "Enable the use of the decimal point in the display"
                    DEFVAL { 0 }
                    ::= { integerObjects 13 }

        -- 1.3.6.1.4.1.9839.2.1.3.14
        vis-repeater--7 OBJECT-TYPE
                    SYNTAX Integer32 (0..3)
                    UNITS "flag"
                    MAX-ACCESS read-write
                    STATUS current
                    DESCRIPTION "Visualisation on display and repeater"
                    DEFVAL { 0 }
                    ::= { integerObjects 14 }

        -- 1.3.6.1.4.1.9839.2.1.3.16
        def-probe3--9 OBJECT-TYPE
                    SYNTAX Integer32 (0..1)
                    UNITS "flag"
                    MAX-ACCESS read-write
                    STATUS current
                    DESCRIPTION "Use third probe for defrost"
                    DEFVAL { 0 }
                    ::= { integerObjects 16 }

        -- 1.3.6.1.4.1.9839.2.1.3.18
        exist-probe--a OBJECT-TYPE
                    SYNTAX Integer32 (0..3)
                    UNITS "flag"
                    MAX-ACCESS read-write
                    STATUS current
                    DESCRIPTION "Defrostp probe presence"
                    DEFVAL { 3 }
                    ::= { integerObjects 18 }

        -- 1.3.6.1.4.1.9839.2.1.3.20
        set-r1 OBJECT-TYPE
                    SYNTAX Integer32 (-50..32767)
                    UNITS "°C/°F"
                    MAX-ACCESS read-write
                    STATUS current
                    DESCRIPTION "Set minimum allowed"
                    DEFVAL { -50 }
                    ::= { integerObjects 20 }

        -- 1.3.6.1.4.1.9839.2.1.3.21
        set-r2 OBJECT-TYPE
                    SYNTAX Integer32 (-32767..199)
                    UNITS "°C/°F"
                    MAX-ACCESS read-write
                    STATUS current
                    DESCRIPTION "Set maximum allowed"
                    DEFVAL { 90 }
                    ::= { integerObjects 21 }

        -- 1.3.6.1.4.1.9839.2.1.3.22
        en-ed-alarm-r3 OBJECT-TYPE
                    SYNTAX Integer32 (0..1)
                    UNITS "flag"
                    MAX-ACCESS read-write
                    STATUS current
                    DESCRIPTION "Ed alarm enabling"
                    DEFVAL { 0 }
                    ::= { integerObjects 22 }

        -- 1.3.6.1.4.1.9839.2.1.3.24
        en-t-maxmin-r5 OBJECT-TYPE
                    SYNTAX Integer32 (0..32767)
                    UNITS "flag"
                    MAX-ACCESS read-write
                    STATUS current
                    DESCRIPTION "Min. and max. temperature monitoring enabling 0 = No; 1 = Yes"
                    DEFVAL { 0 }
                    ::= { integerObjects 24 }

        -- 1.3.6.1.4.1.9839.2.1.3.25
        reg-n-prb3-r6 OBJECT-TYPE
                    SYNTAX Integer32 (0..1)
                    UNITS "flag"
                    MAX-ACCESS read-write
                    STATUS current
                    DESCRIPTION "Nocturnal regulation with 3rd probe"
                    DEFVAL { 0 }
                    ::= { integerObjects 25 }

        -- 1.3.6.1.4.1.9839.2.1.3.26
        tm-t-maxmin-rt OBJECT-TYPE
                    SYNTAX Integer32 (0..199)
                    UNITS "hours"
                    MAX-ACCESS read-only
                    STATUS current
                    DESCRIPTION "Min. and max. temperature measuring interval"
                    ::= { integerObjects 26 }

        -- 1.3.6.1.4.1.9839.2.1.3.29
        tm-delay-c0 OBJECT-TYPE
                    SYNTAX Integer32 (0..15)
                    UNITS "min"
                    MAX-ACCESS read-write
                    STATUS current
                    DESCRIPTION "Compressor starting delay when the instrument is ON"
                    DEFVAL { 0 }
                    ::= { integerObjects 29 }

        -- 1.3.6.1.4.1.9839.2.1.3.30
        tm-btwn-comp-c1 OBJECT-TYPE
                    SYNTAX Integer32 (0..15)
                    UNITS "min"
                    MAX-ACCESS read-write
                    STATUS current
                    DESCRIPTION "Minimum time between two sucessive compressor star"
                    DEFVAL { 0 }
                    ::= { integerObjects 30 }

        -- 1.3.6.1.4.1.9839.2.1.3.31
        comp-off-tm-c2 OBJECT-TYPE
                    SYNTAX Integer32 (0..15)
                    UNITS "min"
                    MAX-ACCESS read-write
                    STATUS current
                    DESCRIPTION "Minimum compressor off time"
                    DEFVAL { 0 }
                    ::= { integerObjects 31 }

        -- 1.3.6.1.4.1.9839.2.1.3.32
        comp-on-tm-c3 OBJECT-TYPE
                    SYNTAX Integer32 (0..15)
                    UNITS "min"
                    MAX-ACCESS read-write
                    STATUS current
                    DESCRIPTION "Minimum compressor on time"
                    DEFVAL { 0 }
                    ::= { integerObjects 32 }

        -- 1.3.6.1.4.1.9839.2.1.3.33
        relay-safety-c4 OBJECT-TYPE
                    SYNTAX Integer32 (0..100)
                    UNITS "min"
                    MAX-ACCESS read-write
                    STATUS current
                    DESCRIPTION "Relay safety"
                    DEFVAL { 4 }
                    ::= { integerObjects 33 }

        -- 1.3.6.1.4.1.9839.2.1.3.34
        cnt-cycl-dur-cc OBJECT-TYPE
                    SYNTAX Integer32 (0..15)
                    UNITS "hours"
                    MAX-ACCESS read-write
                    STATUS current
                    DESCRIPTION "Continuous cycle duration"
                    DEFVAL { 4 }
                    ::= { integerObjects 34 }

        -- 1.3.6.1.4.1.9839.2.1.3.35
        al-time-excl-c6 OBJECT-TYPE
                    SYNTAX Integer32 (0..15)
                    UNITS "hours"
                    MAX-ACCESS read-write
                    STATUS current
                    DESCRIPTION "Low temp. alarm exclusion-time after continuos cycle"
                    DEFVAL { 2 }
                    ::= { integerObjects 35 }

        -- 1.3.6.1.4.1.9839.2.1.3.36
        defrost-type-d0 OBJECT-TYPE
                    SYNTAX Integer32 (0..3)
                    UNITS "N/A"
                    MAX-ACCESS read-write
                    STATUS current
                    DESCRIPTION "Defrost types"
                    DEFVAL { 0 }
                    ::= { integerObjects 36 }

        -- 1.3.6.1.4.1.9839.2.1.3.37
        tm-btwn-defs-di OBJECT-TYPE
                    SYNTAX Integer32 (0..199)
                    UNITS "hours"
                    MAX-ACCESS read-write
                    STATUS current
                    DESCRIPTION "Interval between two defrosts"
                    DEFVAL { 8 }
                    ::= { integerObjects 37 }

        -- 1.3.6.1.4.1.9839.2.1.3.38
        def-end-time-dt OBJECT-TYPE
                    SYNTAX Integer32 (-50..199)
                    UNITS "°C/°F"
                    MAX-ACCESS read-write
                    STATUS current
                    DESCRIPTION "Set point for end defrost temperature"
                    DEFVAL { 4 }
                    ::= { integerObjects 38 }

        -- 1.3.6.1.4.1.9839.2.1.3.40
        def-max-time-dp OBJECT-TYPE
                    SYNTAX Integer32 (1..199)
                    UNITS "min"
                    MAX-ACCESS read-write
                    STATUS current
                    DESCRIPTION "Maximum defrost time"
                    DEFVAL { 30 }
                    ::= { integerObjects 40 }

        -- 1.3.6.1.4.1.9839.2.1.3.41
        def-startup-d4 OBJECT-TYPE
                    SYNTAX Integer32 (0..1)
                    UNITS "flasg"
                    MAX-ACCESS read-write
                    STATUS current
                    DESCRIPTION "Defrost when the instrument starts"
                    DEFVAL { 0 }
                    ::= { integerObjects 41 }

        -- 1.3.6.1.4.1.9839.2.1.3.42
        def-del-su-d5 OBJECT-TYPE
                    SYNTAX Integer32 (0..199)
                    UNITS "min"
                    MAX-ACCESS read-write
                    STATUS current
                    DESCRIPTION "Defrost delay when instrument starts or from dig.input"
                    DEFVAL { 0 }
                    ::= { integerObjects 42 }

        -- 1.3.6.1.4.1.9839.2.1.3.43
        stop-vis-def-d6 OBJECT-TYPE
                    SYNTAX Integer32 (0..1)
                    UNITS "flasg"
                    MAX-ACCESS read-write
                    STATUS current
                    DESCRIPTION "Display block during defrosting"
                    DEFVAL { 1 }
                    ::= { integerObjects 43 }

        -- 1.3.6.1.4.1.9839.2.1.3.44
        drip-tm-def-dd OBJECT-TYPE
                    SYNTAX Integer32 (0..15)
                    UNITS "min"
                    MAX-ACCESS read-write
                    STATUS current
                    DESCRIPTION "Dripping time after defrost"
                    DEFVAL { 2 }
                    ::= { integerObjects 44 }

        -- 1.3.6.1.4.1.9839.2.1.3.45
        aloff-tm-def-d8 OBJECT-TYPE
                    SYNTAX Integer32 (0..15)
                    UNITS "hours"
                    MAX-ACCESS read-write
                    STATUS current
                    DESCRIPTION "High temperature exclusion time after defrost"
                    DEFVAL { 1 }
                    ::= { integerObjects 45 }

        -- 1.3.6.1.4.1.9839.2.1.3.46
        def-priority-d9 OBJECT-TYPE
                    SYNTAX Integer32 (0..1)
                    UNITS "flasg"
                    MAX-ACCESS read-write
                    STATUS current
                    DESCRIPTION "Defrost priority over compressor protection"
                    DEFVAL { 0 }
                    ::= { integerObjects 46 }

        -- 1.3.6.1.4.1.9839.2.1.3.49
        time-base-dc OBJECT-TYPE
                    SYNTAX Integer32 (0..1)
                    UNITS "flasg"
                    MAX-ACCESS read-write
                    STATUS current
                    DESCRIPTION "Time base for the intervals between defrosts"
                    DEFVAL { 0 }
                    ::= { integerObjects 49 }

        -- 1.3.6.1.4.1.9839.2.1.3.52
        lt-al-thrsh-al OBJECT-TYPE
                    SYNTAX Integer32 (0..199)
                    UNITS "°K"
                    MAX-ACCESS read-write
                    STATUS current
                    DESCRIPTION "Low temperature alarm"
                    DEFVAL { 0 }
                    ::= { integerObjects 52 }

        -- 1.3.6.1.4.1.9839.2.1.3.53
        di1-config-a4 OBJECT-TYPE
                    SYNTAX Integer32 (0..7)
                    UNITS "N/A"
                    MAX-ACCESS read-write
                    STATUS current
                    DESCRIPTION "Digital input no.1 configuration"
                    DEFVAL { 0 }
                    ::= { integerObjects 53 }

        -- 1.3.6.1.4.1.9839.2.1.3.54
        di2-config-a5 OBJECT-TYPE
                    SYNTAX Integer32 (0..7)
                    UNITS "N/A"
                    MAX-ACCESS read-write
                    STATUS current
                    DESCRIPTION "Digital input no.2 configuration"
                    DEFVAL { 0 }
                    ::= { integerObjects 54 }

        -- 1.3.6.1.4.1.9839.2.1.3.55
        comp-off-ext-a6 OBJECT-TYPE
                    SYNTAX Integer32 (0..100)
                    UNITS "min"
                    MAX-ACCESS read-write
                    STATUS current
                    DESCRIPTION "Compressor block"
                    DEFVAL { 0 }
                    ::= { integerObjects 55 }

        -- 1.3.6.1.4.1.9839.2.1.3.56
        tm-delay-id-a7 OBJECT-TYPE
                    SYNTAX Integer32 (0..199)
                    UNITS "min"
                    MAX-ACCESS read-write
                    STATUS current
                    DESCRIPTION "Detection delay time for the delayed alarm input"
                    DEFVAL { 0 }
                    ::= { integerObjects 56 }

        -- 1.3.6.1.4.1.9839.2.1.3.57
        temp-al-del-ad OBJECT-TYPE
                    SYNTAX Integer32 (0..199)
                    UNITS "min"
                    MAX-ACCESS read-write
                    STATUS current
                    DESCRIPTION "Temperature alarm delay"
                    DEFVAL { 120 }
                    ::= { integerObjects 57 }

        -- 1.3.6.1.4.1.9839.2.1.3.58
        cnf-di-virt-a8 OBJECT-TYPE
                    SYNTAX Integer32 (0..7)
                    UNITS "N/A"
                    MAX-ACCESS read-write
                    STATUS current
                    DESCRIPTION "Virtual input configuration"
                    DEFVAL { 0 }
                    ::= { integerObjects 58 }

        -- 1.3.6.1.4.1.9839.2.1.3.59
        en-lan-di2-a9 OBJECT-TYPE
                    SYNTAX Integer32 (0..1)
                    UNITS "flag"
                    MAX-ACCESS read-write
                    STATUS current
                    DESCRIPTION "2nd input LAN propagation enable"
                    DEFVAL { 1 }
                    ::= { integerObjects 59 }

        -- 1.3.6.1.4.1.9839.2.1.3.60
        en-mt-al-slv-ra OBJECT-TYPE
                    SYNTAX Integer32 (0..1)
                    UNITS "flag"
                    MAX-ACCESS read-write
                    STATUS current
                    DESCRIPTION "Slave remote alarms on Master enable"
                    DEFVAL { 1 }
                    ::= { integerObjects 60 }

        -- 1.3.6.1.4.1.9839.2.1.3.61
        fans-mng-f0 OBJECT-TYPE
                    SYNTAX Integer32 (0..1)
                    UNITS "flag"
                    MAX-ACCESS read-write
                    STATUS current
                    DESCRIPTION "Fan management"
                    DEFVAL { 0 }
                    ::= { integerObjects 61 }

        -- 1.3.6.1.4.1.9839.2.1.3.63
        fan-0-cmp-0-f2 OBJECT-TYPE
                    SYNTAX Integer32 (0..1)
                    UNITS "flag"
                    MAX-ACCESS read-write
                    STATUS current
                    DESCRIPTION "Fans off when compressor off"
                    DEFVAL { 1 }
                    ::= { integerObjects 63 }

        -- 1.3.6.1.4.1.9839.2.1.3.64
        fan-0-on-def-f3 OBJECT-TYPE
                    SYNTAX Integer32 (0..1)
                    UNITS "flag"
                    MAX-ACCESS read-write
                    STATUS current
                    DESCRIPTION "Fans OFF in defrost (0 = No, 1 = Yes)"
                    DEFVAL { 1 }
                    ::= { integerObjects 64 }

        -- 1.3.6.1.4.1.9839.2.1.3.65
        fan-rele-f4 OBJECT-TYPE
                    SYNTAX Integer32 (0..2)
                    UNITS "flag"
                    MAX-ACCESS read-write
                    STATUS current
                    DESCRIPTION "Fan relay configuration"
                    DEFVAL { 0 }
                    ::= { integerObjects 65 }

        -- 1.3.6.1.4.1.9839.2.1.3.66
        tm-off-drip-fd OBJECT-TYPE
                    SYNTAX Integer32 (0..15)
                    UNITS "min"
                    MAX-ACCESS read-write
                    STATUS current
                    DESCRIPTION "After-dripping fan stopping"
                    DEFVAL { 1 }
                    ::= { integerObjects 66 }

        -- 1.3.6.1.4.1.9839.2.1.3.67
        serial-address OBJECT-TYPE
                    SYNTAX Integer32 (0..199)
                    UNITS "N/A"
                    MAX-ACCESS read-only
                    STATUS current
                    DESCRIPTION "Serial address (only for the network Master)"
                    DEFVAL { 0 }
                    ::= { integerObjects 67 }

        -- 1.3.6.1.4.1.9839.2.1.3.68
        relay4-mode-h1 OBJECT-TYPE
                    SYNTAX Integer32 (0..3)
                    UNITS "flag"
                    MAX-ACCESS read-write
                    STATUS current
                    DESCRIPTION "Relay 4 working selection:"
                    DEFVAL { 0 }
                    ::= { integerObjects 68 }

        -- 1.3.6.1.4.1.9839.2.1.3.69
        en-dis-keyb-h2 OBJECT-TYPE
                    SYNTAX Integer32 (-32767..32767)
                    UNITS "N/A"
                    MAX-ACCESS read-write
                    STATUS current
                    DESCRIPTION "Keypad enable parameter"
                    ::= { integerObjects 69 }

        -- 1.3.6.1.4.1.9839.2.1.3.70
        remote-control OBJECT-TYPE
                    SYNTAX Integer32 (-32767..32767)
                    UNITS "N/A"
                    MAX-ACCESS read-write
                    STATUS current
                    DESCRIPTION "Remote-control programming enabling code"
                    ::= { integerObjects 70 }

        -- 1.3.6.1.4.1.9839.2.1.3.74
        lan-address-sa OBJECT-TYPE
                    SYNTAX Integer32 (0..5)
                    UNITS "N/A"
                    MAX-ACCESS read-write
                    STATUS current
                    DESCRIPTION "Slave address in the LAN"
                    DEFVAL { 0 }
                    ::= { integerObjects 74 }

        -- 1.3.6.1.4.1.9839.2.1.3.75
        lan-lenght-sn OBJECT-TYPE
                    SYNTAX Integer32 (0..5)
                    UNITS "N/A"
                    MAX-ACCESS read-write
                    STATUS current
                    DESCRIPTION "Number of Slaves"
                    DEFVAL { 0 }
                    ::= { integerObjects 75 }

        -- 1.3.6.1.4.1.9839.2.1.3.76
        hh-def-sched1 OBJECT-TYPE
                    SYNTAX Integer32 (0..24)
                    UNITS "hours"
                    MAX-ACCESS read-write
                    STATUS current
                    DESCRIPTION "Hour of the 1st defrosting"
                    ::= { integerObjects 76 }

        -- 1.3.6.1.4.1.9839.2.1.3.77
        mm-def-sched1 OBJECT-TYPE
                    SYNTAX Integer32 (0..60)
                    UNITS "10 min."
                    MAX-ACCESS read-write
                    STATUS current
                    DESCRIPTION "Minute of the 1st defrosting"
                    ::= { integerObjects 77 }

        -- 1.3.6.1.4.1.9839.2.1.3.78
        hh-def-sched2 OBJECT-TYPE
                    SYNTAX Integer32 (0..24)
                    UNITS "hours"
                    MAX-ACCESS read-write
                    STATUS current
                    DESCRIPTION "Hour of the 2nd defrosting"
                    ::= { integerObjects 78 }

        -- 1.3.6.1.4.1.9839.2.1.3.79
        mm-def-sched2 OBJECT-TYPE
                    SYNTAX Integer32 (0..60)
                    UNITS "10 min."
                    MAX-ACCESS read-write
                    STATUS current
                    DESCRIPTION "Minute of the 2nd defrosting"
                    ::= { integerObjects 79 }

        -- 1.3.6.1.4.1.9839.2.1.3.80
        hh-def-sched3 OBJECT-TYPE
                    SYNTAX Integer32 (0..24)
                    UNITS "hours"
                    MAX-ACCESS read-write
                    STATUS current
                    DESCRIPTION "Hour of the 3th defrosting"
                    ::= { integerObjects 80 }

        -- 1.3.6.1.4.1.9839.2.1.3.81
        mm-def-sched3 OBJECT-TYPE
                    SYNTAX Integer32 (0..60)
                    UNITS "10 min."
                    MAX-ACCESS read-write
                    STATUS current
                    DESCRIPTION "Minute of the 3th defrosting"
                    ::= { integerObjects 81 }

        -- 1.3.6.1.4.1.9839.2.1.3.82
        hh-def-sched4 OBJECT-TYPE
                    SYNTAX Integer32 (0..24)
                    UNITS "hours"
                    MAX-ACCESS read-write
                    STATUS current
                    DESCRIPTION "Hour of the 4th defrosting"
                    ::= { integerObjects 82 }

        -- 1.3.6.1.4.1.9839.2.1.3.83
        mm-def-sched4 OBJECT-TYPE
                    SYNTAX Integer32 (0..60)
                    UNITS "10 min."
                    MAX-ACCESS read-write
                    STATUS current
                    DESCRIPTION "Minute of the 4th defrosting"
                    ::= { integerObjects 83 }

        -- 1.3.6.1.4.1.9839.2.1.3.84
        hh-def-sched5 OBJECT-TYPE
                    SYNTAX Integer32 (0..24)
                    UNITS "hours"
                    MAX-ACCESS read-write
                    STATUS current
                    DESCRIPTION "Hour of the 5th defrosting"
                    ::= { integerObjects 84 }

        -- 1.3.6.1.4.1.9839.2.1.3.85
        mm-def-sched5 OBJECT-TYPE
                    SYNTAX Integer32 (0..60)
                    UNITS "10 min."
                    MAX-ACCESS read-write
                    STATUS current
                    DESCRIPTION "Minute of the 5th defrosting"
                    ::= { integerObjects 85 }

        -- 1.3.6.1.4.1.9839.2.1.3.86
        hh-def-sched6 OBJECT-TYPE
                    SYNTAX Integer32 (0..24)
                    UNITS "hours"
                    MAX-ACCESS read-write
                    STATUS current
                    DESCRIPTION "Hour of the 6th defrosting"
                    ::= { integerObjects 86 }

        -- 1.3.6.1.4.1.9839.2.1.3.87
        mm-def-sched6 OBJECT-TYPE
                    SYNTAX Integer32 (0..60)
                    UNITS "10 min."
                    MAX-ACCESS read-write
                    STATUS current
                    DESCRIPTION "Minute of the 6th defrosting"
                    ::= { integerObjects 87 }

        -- 1.3.6.1.4.1.9839.2.1.3.88
        hh-def-sched7 OBJECT-TYPE
                    SYNTAX Integer32 (0..24)
                    UNITS "hours"
                    MAX-ACCESS read-write
                    STATUS current
                    DESCRIPTION "Hour of the 7th defrosting"
                    ::= { integerObjects 88 }

        -- 1.3.6.1.4.1.9839.2.1.3.89
        mm-def-sched7 OBJECT-TYPE
                    SYNTAX Integer32 (0..60)
                    UNITS "10 min."
                    MAX-ACCESS read-write
                    STATUS current
                    DESCRIPTION "Minute of the 7th defrosting"
                    ::= { integerObjects 89 }

        -- 1.3.6.1.4.1.9839.2.1.3.90
        hh-def-sched8 OBJECT-TYPE
                    SYNTAX Integer32 (0..24)
                    UNITS "hours"
                    MAX-ACCESS read-write
                    STATUS current
                    DESCRIPTION "Hour of the 8th defrosting"
                    ::= { integerObjects 90 }

        -- 1.3.6.1.4.1.9839.2.1.3.91
        mm-def-sched8 OBJECT-TYPE
                    SYNTAX Integer32 (0..60)
                    UNITS "10 min."
                    MAX-ACCESS read-write
                    STATUS current
                    DESCRIPTION "Minute of the 8th defrosting"
                    ::= { integerObjects 91 }

        -- 1.3.6.1.4.1.9839.2.1.3.92
        hh-clock OBJECT-TYPE
                    SYNTAX Integer32 (0..23)
                    UNITS "hours"
                    MAX-ACCESS read-write
                    STATUS current
                    DESCRIPTION "Set hours"
                    ::= { integerObjects 92 }

        -- 1.3.6.1.4.1.9839.2.1.3.93
        mm-clock OBJECT-TYPE
                    SYNTAX Integer32 (0..59)
                    UNITS "min"
                    MAX-ACCESS read-write
                    STATUS current
                    DESCRIPTION "Set minutes"
                    ::= { integerObjects 93 }

        -- 1.3.6.1.4.1.9839.2.1.3.94
        hh-vis OBJECT-TYPE
                    SYNTAX Integer32 (0..23)
                    UNITS "hours"
                    MAX-ACCESS read-only
                    STATUS current
                    DESCRIPTION "Current hour"
                    ::= { integerObjects 94 }

        -- 1.3.6.1.4.1.9839.2.1.3.95
        mm-vis OBJECT-TYPE
                    SYNTAX Integer32 (0..59)
                    UNITS "min"
                    MAX-ACCESS read-only
                    STATUS current
                    DESCRIPTION "Current minute"
                    ::= { integerObjects 95 }

        -- 1.3.6.1.4.1.9839.2.1.3.106
        ht-al-thrsh-ah OBJECT-TYPE
                    SYNTAX Integer32 (0..199)
                    UNITS "°K"
                    MAX-ACCESS read-write
                    STATUS current
                    DESCRIPTION "High temperature alarm"
                    DEFVAL { 0 }
                    ::= { integerObjects 106 }


	
	END

--
-- CAREL-irmpx.MIB
--
