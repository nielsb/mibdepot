--
-- CAREL-ir32un-t.MIB
-- MIB generated by CAREL
-- Friday, 14 March 2003
--

    CAREL-ir32un-t-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        ir32un-tMIB MODULE-IDENTITY
      		LAST-UPDATED  "200303141724Z"		-- March 14, 2003 at 17:24 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the ir32un-t device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- ir32un-tMIB OBJECT IDENTIFIER ::= { instruments 1 }
		
        -- 1.3.6.1.4.1.9839.2.1.1
        digitalObjects OBJECT IDENTIFIER ::= { ir32un-tMIB 1 }

        -- 1.3.6.1.4.1.9839.2.1.1.1
        stato-id-1 OBJECT-TYPE
                    SYNTAX Integer32 (0..1)
                    UNITS "N/A"
                    MAX-ACCESS read-only
                    STATUS current
                    DESCRIPTION "Digital input 1"
                    ::= { digitalObjects 1 }

        -- 1.3.6.1.4.1.9839.2.1.1.2
        stato-id-2 OBJECT-TYPE
                    SYNTAX Integer32 (0..1)
                    UNITS "N/A"
                    MAX-ACCESS read-only
                    STATUS current
                    DESCRIPTION "Digital input 2"
                    ::= { digitalObjects 2 }

        -- 1.3.6.1.4.1.9839.2.1.1.3
        stato-ud-1 OBJECT-TYPE
                    SYNTAX Integer32 (0..1)
                    UNITS "N/A"
                    MAX-ACCESS read-only
                    STATUS current
                    DESCRIPTION "Out 1"
                    ::= { digitalObjects 3 }

        -- 1.3.6.1.4.1.9839.2.1.1.4
        stato-ud-2 OBJECT-TYPE
                    SYNTAX Integer32 (0..1)
                    UNITS "N/A"
                    MAX-ACCESS read-only
                    STATUS current
                    DESCRIPTION "Out 2"
                    ::= { digitalObjects 4 }

        -- 1.3.6.1.4.1.9839.2.1.1.5
        stato-ud-3 OBJECT-TYPE
                    SYNTAX Integer32 (0..1)
                    UNITS "N/A"
                    MAX-ACCESS read-only
                    STATUS current
                    DESCRIPTION "Out 3"
                    ::= { digitalObjects 5 }

        -- 1.3.6.1.4.1.9839.2.1.1.6
        stato-ud-4 OBJECT-TYPE
                    SYNTAX Integer32 (0..1)
                    UNITS "N/A"
                    MAX-ACCESS read-only
                    STATUS current
                    DESCRIPTION "Out 4"
                    ::= { digitalObjects 6 }

        -- 1.3.6.1.4.1.9839.2.1.1.8
        all-sonda-0 OBJECT-TYPE
                    SYNTAX Integer32 (0..1)
                    UNITS "N/A"
                    MAX-ACCESS read-only
                    STATUS current
                    DESCRIPTION "Probe 1 error (er0)"
                    ::= { digitalObjects 8 }

        -- 1.3.6.1.4.1.9839.2.1.1.9
        all-sonda-1 OBJECT-TYPE
                    SYNTAX Integer32 (0..1)
                    UNITS "N/A"
                    MAX-ACCESS read-only
                    STATUS current
                    DESCRIPTION "Probe 2 error (er1)"
                    ::= { digitalObjects 9 }

        -- 1.3.6.1.4.1.9839.2.1.1.10
        all-eeprom OBJECT-TYPE
                    SYNTAX Integer32 (0..1)
                    UNITS "N/A"
                    MAX-ACCESS read-only
                    STATUS current
                    DESCRIPTION "Eeprom memory error (er2)"
                    ::= { digitalObjects 10 }

        -- 1.3.6.1.4.1.9839.2.1.1.11
        all-id-1 OBJECT-TYPE
                    SYNTAX Integer32 (0..1)
                    UNITS "N/A"
                    MAX-ACCESS read-only
                    STATUS current
                    DESCRIPTION "Alarm from digital input 1 (er3)"
                    ::= { digitalObjects 11 }

        -- 1.3.6.1.4.1.9839.2.1.1.12
        all-alta-temp OBJECT-TYPE
                    SYNTAX Integer32 (0..1)
                    UNITS "N/A"
                    MAX-ACCESS read-only
                    STATUS current
                    DESCRIPTION "Ligh temperature alarm (er4)"
                    ::= { digitalObjects 12 }

        -- 1.3.6.1.4.1.9839.2.1.1.13
        all-bassa-temp OBJECT-TYPE
                    SYNTAX Integer32 (0..1)
                    UNITS "N/A"
                    MAX-ACCESS read-only
                    STATUS current
                    DESCRIPTION "Low temperature alarm (er5)"
                    ::= { digitalObjects 13 }

        -- 1.3.6.1.4.1.9839.2.1.1.14
        prop-prop-int OBJECT-TYPE
                    SYNTAX Integer32 (0..1)
                    UNITS "N/A"
                    MAX-ACCESS read-write
                    STATUS current
                    DESCRIPTION "Type of regulation (0=P, 1=P+I)"
                    DEFVAL { 0 }
                    ::= { digitalObjects 14 }

        -- 1.3.6.1.4.1.9839.2.1.1.15
        tipo-sonda OBJECT-TYPE
                    SYNTAX Integer32 (0..1)
                    UNITS "N/A"
                    MAX-ACCESS read-write
                    STATUS current
                    DESCRIPTION "Sensor type"
                    DEFVAL { 0 }
                    ::= { digitalObjects 15 }

        -- 1.3.6.1.4.1.9839.2.1.1.16
        celsius-farhan OBJECT-TYPE
                    SYNTAX Integer32 (0..1)
                    UNITS "N/A"
                    MAX-ACCESS read-write
                    STATUS current
                    DESCRIPTION "Temperature unit of measure: °C or °F"
                    DEFVAL { 0 }
                    ::= { digitalObjects 16 }

        -- 1.3.6.1.4.1.9839.2.1.1.17
        modo-speciale OBJECT-TYPE
                    SYNTAX Integer32 (0..1)
                    UNITS "N/A"
                    MAX-ACCESS read-write
                    STATUS current
                    DESCRIPTION "“special” mode of operation"
                    DEFVAL { 0 }
                    ::= { digitalObjects 17 }

        -- 1.3.6.1.4.1.9839.2.1.1.18
        tipo-out-grad4 OBJECT-TYPE
                    SYNTAX Integer32 (0..1)
                    UNITS "N/A"
                    MAX-ACCESS read-write
                    STATUS current
                    DESCRIPTION "OUT4: Type of output"
                    ::= { digitalObjects 18 }

        -- 1.3.6.1.4.1.9839.2.1.1.19
        tipo-out-grad3 OBJECT-TYPE
                    SYNTAX Integer32 (0..1)
                    UNITS "N/A"
                    MAX-ACCESS read-write
                    STATUS current
                    DESCRIPTION "OUT3: Type of output"
                    ::= { digitalObjects 19 }

        -- 1.3.6.1.4.1.9839.2.1.1.20
        tipo-out-grad2 OBJECT-TYPE
                    SYNTAX Integer32 (0..1)
                    UNITS "N/A"
                    MAX-ACCESS read-write
                    STATUS current
                    DESCRIPTION "OUT2: Type of output"
                    ::= { digitalObjects 20 }

        -- 1.3.6.1.4.1.9839.2.1.1.21
        tipo-out-grad1 OBJECT-TYPE
                    SYNTAX Integer32 (0..1)
                    UNITS "N/A"
                    MAX-ACCESS read-write
                    STATUS current
                    DESCRIPTION "OUT1: Type of output"
                    ::= { digitalObjects 21 }



        -- 1.3.6.1.4.1.9839.2.1.2
        analogObjects OBJECT IDENTIFIER ::= { ir32un-tMIB 2 }

        -- 1.3.6.1.4.1.9839.2.1.2.1
        ing-sonda-0 OBJECT-TYPE
                    SYNTAX Integer32 (-32767..32767)
                    UNITS "°C x10"
                    MAX-ACCESS read-only
                    STATUS current
                    DESCRIPTION "Probe 1"
                    ::= { analogObjects 1 }

        -- 1.3.6.1.4.1.9839.2.1.2.2
        ing-sonda-1 OBJECT-TYPE
                    SYNTAX Integer32 (-32767..32767)
                    UNITS "°C x10"
                    MAX-ACCESS read-only
                    STATUS current
                    DESCRIPTION "Probe 2"
                    ::= { analogObjects 2 }

        -- 1.3.6.1.4.1.9839.2.1.2.3
        set-point1 OBJECT-TYPE
                    SYNTAX Integer32 (-32767..32767)
                    UNITS "°C x10"
                    MAX-ACCESS read-write
                    STATUS current
                    DESCRIPTION "Setpoint 1"
                    DEFVAL { 200 }
                    ::= { analogObjects 3 }

        -- 1.3.6.1.4.1.9839.2.1.2.4
        set-point2 OBJECT-TYPE
                    SYNTAX Integer32 (-32767..32767)
                    UNITS "°C x10"
                    MAX-ACCESS read-write
                    STATUS current
                    DESCRIPTION "Setpoint 2"
                    DEFVAL { 400 }
                    ::= { analogObjects 4 }

        -- 1.3.6.1.4.1.9839.2.1.2.5
        differenziale1 OBJECT-TYPE
                    SYNTAX Integer32 (1..999)
                    UNITS "°C x10"
                    MAX-ACCESS read-write
                    STATUS current
                    DESCRIPTION "Differential 1"
                    DEFVAL { 20 }
                    ::= { analogObjects 5 }

        -- 1.3.6.1.4.1.9839.2.1.2.6
        differenziale2 OBJECT-TYPE
                    SYNTAX Integer32 (1..999)
                    UNITS "°C x10"
                    MAX-ACCESS read-write
                    STATUS current
                    DESCRIPTION "Differential 2"
                    DEFVAL { 20 }
                    ::= { analogObjects 6 }

        -- 1.3.6.1.4.1.9839.2.1.2.7
        zona-morta OBJECT-TYPE
                    SYNTAX Integer32 (0..999)
                    UNITS "°C x10"
                    MAX-ACCESS read-write
                    STATUS current
                    DESCRIPTION "Dead zone"
                    DEFVAL { 20 }
                    ::= { analogObjects 7 }

        -- 1.3.6.1.4.1.9839.2.1.2.8
        offset-sonda OBJECT-TYPE
                    SYNTAX Integer32 (-990..999)
                    UNITS "°C x10"
                    MAX-ACCESS read-write
                    STATUS current
                    DESCRIPTION "Inlet probe calibration"
                    DEFVAL { 0 }
                    ::= { analogObjects 8 }

        -- 1.3.6.1.4.1.9839.2.1.2.9
        sog-bassa-temp OBJECT-TYPE
                    SYNTAX Integer32 (-990..32767)
                    UNITS "°C x10"
                    MAX-ACCESS read-write
                    STATUS current
                    DESCRIPTION "Low temperature set"
                    ::= { analogObjects 9 }

        -- 1.3.6.1.4.1.9839.2.1.2.10
        sog-alta-temp OBJECT-TYPE
                    SYNTAX Integer32 (-32767..9990)
                    UNITS "°C x10"
                    MAX-ACCESS read-write
                    STATUS current
                    DESCRIPTION "High temperature set"
                    ::= { analogObjects 10 }

        -- 1.3.6.1.4.1.9839.2.1.2.11
        differenz-all OBJECT-TYPE
                    SYNTAX Integer32 (-990..990)
                    UNITS "°C x10"
                    MAX-ACCESS read-write
                    STATUS current
                    DESCRIPTION "Alarm differential (absolute value)"
                    DEFVAL { 20 }
                    ::= { analogObjects 11 }

        -- 1.3.6.1.4.1.9839.2.1.2.12
        tempo-di-pwm OBJECT-TYPE
                    SYNTAX Integer32 (2..9990)
                    UNITS "sec-0.2 x10"
                    MAX-ACCESS read-write
                    STATUS current
                    DESCRIPTION "PWM cycle time"
                    DEFVAL { 200 }
                    ::= { analogObjects 12 }

        -- 1.3.6.1.4.1.9839.2.1.2.13
        val-minimo-av OBJECT-TYPE
                    SYNTAX Integer32 (-990..32767)
                    UNITS "N/A"
                    MAX-ACCESS read-write
                    STATUS current
                    DESCRIPTION "Minimum value of voltage and current inputs"
                    DEFVAL { 0 }
                    ::= { analogObjects 13 }

        -- 1.3.6.1.4.1.9839.2.1.2.14
        val-massimo-av OBJECT-TYPE
                    SYNTAX Integer32 (-32767..9990)
                    UNITS "N/A"
                    MAX-ACCESS read-write
                    STATUS current
                    DESCRIPTION "Maximum value of voltage and current inputs"
                    DEFVAL { 1000 }
                    ::= { analogObjects 14 }

        -- 1.3.6.1.4.1.9839.2.1.2.15
        set1-min-ok OBJECT-TYPE
                    SYNTAX Integer32 (-990..32767)
                    UNITS "°C x10"
                    MAX-ACCESS read-write
                    STATUS current
                    DESCRIPTION "Minimum value of St1"
                    ::= { analogObjects 15 }

        -- 1.3.6.1.4.1.9839.2.1.2.16
        set1-max-ok OBJECT-TYPE
                    SYNTAX Integer32 (-32767..9990)
                    UNITS "°C x10"
                    MAX-ACCESS read-write
                    STATUS current
                    DESCRIPTION "Maximum value of St1"
                    ::= { analogObjects 16 }

        -- 1.3.6.1.4.1.9839.2.1.2.17
        set2-min-ok OBJECT-TYPE
                    SYNTAX Integer32 (-990..32767)
                    UNITS "°C x10"
                    MAX-ACCESS read-write
                    STATUS current
                    DESCRIPTION "Minimum value of St2"
                    ::= { analogObjects 17 }

        -- 1.3.6.1.4.1.9839.2.1.2.18
        set2-max-ok OBJECT-TYPE
                    SYNTAX Integer32 (-32767..9990)
                    UNITS "°C x10"
                    MAX-ACCESS read-write
                    STATUS current
                    DESCRIPTION "maximum value of St2"
                    ::= { analogObjects 18 }

        -- 1.3.6.1.4.1.9839.2.1.2.19
        autorita OBJECT-TYPE
                    SYNTAX Integer32 (-20..20)
                    UNITS "N/A"
                    MAX-ACCESS read-write
                    STATUS current
                    DESCRIPTION "Authority"
                    DEFVAL { 5 }
                    ::= { analogObjects 19 }



        -- 1.3.6.1.4.1.9839.2.1.3
        integerObjects OBJECT IDENTIFIER ::= { ir32un-tMIB 3 }

        -- 1.3.6.1.4.1.9839.2.1.3.1
        modo-funz-c0 OBJECT-TYPE
                    SYNTAX Integer32 (1..9)
                    UNITS "N/A"
                    MAX-ACCESS read-write
                    STATUS current
                    DESCRIPTION "Mode of operation"
                    DEFVAL { 2 }
                    ::= { integerObjects 1 }

        -- 1.3.6.1.4.1.9839.2.1.3.2
        rit-2ins-c6 OBJECT-TYPE
                    SYNTAX Integer32 (0..999)
                    UNITS "sec"
                    MAX-ACCESS read-write
                    STATUS current
                    DESCRIPTION "Delay between energizations of different outputs"
                    DEFVAL { 5 }
                    ::= { integerObjects 2 }

        -- 1.3.6.1.4.1.9839.2.1.3.3
        tmin-2out-c7 OBJECT-TYPE
                    SYNTAX Integer32 (0..15)
                    UNITS "min"
                    MAX-ACCESS read-write
                    STATUS current
                    DESCRIPTION "Minimum time between 2 sucess. energ. output"
                    DEFVAL { 0 }
                    ::= { integerObjects 3 }

        -- 1.3.6.1.4.1.9839.2.1.3.4
        tmin-off-out-c8 OBJECT-TYPE
                    SYNTAX Integer32 (0..15)
                    UNITS "min"
                    MAX-ACCESS read-write
                    STATUS current
                    DESCRIPTION "Minimum disenergization time-interval"
                    DEFVAL { 0 }
                    ::= { integerObjects 4 }

        -- 1.3.6.1.4.1.9839.2.1.3.5
        tmin-on-c9 OBJECT-TYPE
                    SYNTAX Integer32 (0..15)
                    UNITS "min"
                    MAX-ACCESS read-write
                    STATUS current
                    DESCRIPTION "Minimum energization time-interval"
                    DEFVAL { 0 }
                    ::= { integerObjects 5 }

        -- 1.3.6.1.4.1.9839.2.1.3.6
        sicur-sonde OBJECT-TYPE
                    SYNTAX Integer32 (0..3)
                    UNITS "N/A"
                    MAX-ACCESS read-write
                    STATUS current
                    DESCRIPTION "Outputs status in the event of sensor alarm (Er0)"
                    DEFVAL { 0 }
                    ::= { integerObjects 6 }

        -- 1.3.6.1.4.1.9839.2.1.3.7
        rotazione OBJECT-TYPE
                    SYNTAX Integer32 (0..7)
                    UNITS "N/A"
                    MAX-ACCESS read-write
                    STATUS current
                    DESCRIPTION "Rotation"
                    DEFVAL { 0 }
                    ::= { integerObjects 7 }

        -- 1.3.6.1.4.1.9839.2.1.3.8
        velocita-sonda OBJECT-TYPE
                    SYNTAX Integer32 (1..14)
                    UNITS "N/A"
                    MAX-ACCESS read-write
                    STATUS current
                    DESCRIPTION "Sensor response"
                    DEFVAL { 5 }
                    ::= { integerObjects 8 }

        -- 1.3.6.1.4.1.9839.2.1.3.9
        presenza-sonda OBJECT-TYPE
                    SYNTAX Integer32 (0..4)
                    UNITS "N/A"
                    MAX-ACCESS read-write
                    STATUS current
                    DESCRIPTION "Use of the second sensor"
                    DEFVAL { 0 }
                    ::= { integerObjects 9 }

        -- 1.3.6.1.4.1.9839.2.1.3.10
        tempo-allarme OBJECT-TYPE
                    SYNTAX Integer32 (0..120)
                    UNITS "min"
                    MAX-ACCESS read-write
                    STATUS current
                    DESCRIPTION "Delayed alarm"
                    ::= { integerObjects 10 }

        -- 1.3.6.1.4.1.9839.2.1.3.11
        gestione-id1 OBJECT-TYPE
                    SYNTAX Integer32 (0..4)
                    UNITS "N/A"
                    MAX-ACCESS read-write
                    STATUS current
                    DESCRIPTION "Digital input 1 management"
                    DEFVAL { 0 }
                    ::= { integerObjects 11 }

        -- 1.3.6.1.4.1.9839.2.1.3.12
        gestione-id2 OBJECT-TYPE
                    SYNTAX Integer32 (0..4)
                    UNITS "N/A"
                    MAX-ACCESS read-write
                    STATUS current
                    DESCRIPTION "Digital input 2 management"
                    DEFVAL { 0 }
                    ::= { integerObjects 12 }

        -- 1.3.6.1.4.1.9839.2.1.3.13
        sicur-all-id OBJECT-TYPE
                    SYNTAX Integer32 (0..3)
                    UNITS "N/A"
                    MAX-ACCESS read-write
                    STATUS current
                    DESCRIPTION "Outputs status in the event of alarm via dig. input"
                    DEFVAL { 0 }
                    ::= { integerObjects 13 }

        -- 1.3.6.1.4.1.9839.2.1.3.14
        set-gradino1 OBJECT-TYPE
                    SYNTAX Integer32 (0..15)
                    UNITS "N/A"
                    MAX-ACCESS read-write
                    STATUS current
                    DESCRIPTION "OUT1: Dependence out1"
                    ::= { integerObjects 14 }

        -- 1.3.6.1.4.1.9839.2.1.3.15
        offset-grad1 OBJECT-TYPE
                    SYNTAX Integer32 (-100..100)
                    UNITS "N/A"
                    MAX-ACCESS read-write
                    STATUS current
                    DESCRIPTION "OUT1: Energization"
                    ::= { integerObjects 15 }

        -- 1.3.6.1.4.1.9839.2.1.3.16
        diff-gradino1 OBJECT-TYPE
                    SYNTAX Integer32 (-100..100)
                    UNITS "N/A"
                    MAX-ACCESS read-write
                    STATUS current
                    DESCRIPTION "OUT1: Differential / Logic"
                    ::= { integerObjects 16 }

        -- 1.3.6.1.4.1.9839.2.1.3.17
        set-gradino2 OBJECT-TYPE
                    SYNTAX Integer32 (0..15)
                    UNITS "N/A"
                    MAX-ACCESS read-write
                    STATUS current
                    DESCRIPTION "OUT2: Dependence out2"
                    ::= { integerObjects 17 }

        -- 1.3.6.1.4.1.9839.2.1.3.18
        offset-grad2 OBJECT-TYPE
                    SYNTAX Integer32 (-100..100)
                    UNITS "N/A"
                    MAX-ACCESS read-write
                    STATUS current
                    DESCRIPTION "OUT2: Energization"
                    ::= { integerObjects 18 }

        -- 1.3.6.1.4.1.9839.2.1.3.19
        diff-gradino2 OBJECT-TYPE
                    SYNTAX Integer32 (-100..100)
                    UNITS "N/A"
                    MAX-ACCESS read-write
                    STATUS current
                    DESCRIPTION "OUT2: Differential / Logic"
                    ::= { integerObjects 19 }

        -- 1.3.6.1.4.1.9839.2.1.3.20
        set-gradino3 OBJECT-TYPE
                    SYNTAX Integer32 (0..15)
                    UNITS "N/A"
                    MAX-ACCESS read-write
                    STATUS current
                    DESCRIPTION "OUT3: Dependence out3"
                    ::= { integerObjects 20 }

        -- 1.3.6.1.4.1.9839.2.1.3.21
        offset-grad3 OBJECT-TYPE
                    SYNTAX Integer32 (-100..100)
                    UNITS "N/A"
                    MAX-ACCESS read-write
                    STATUS current
                    DESCRIPTION "OUT3: Energization"
                    ::= { integerObjects 21 }

        -- 1.3.6.1.4.1.9839.2.1.3.22
        diff-gradino3 OBJECT-TYPE
                    SYNTAX Integer32 (-100..100)
                    UNITS "N/A"
                    MAX-ACCESS read-write
                    STATUS current
                    DESCRIPTION "OUT3: Differential / Logic"
                    ::= { integerObjects 22 }

        -- 1.3.6.1.4.1.9839.2.1.3.23
        set-gradino4 OBJECT-TYPE
                    SYNTAX Integer32 (0..15)
                    UNITS "N/A"
                    MAX-ACCESS read-write
                    STATUS current
                    DESCRIPTION "OUT4: Dependence out4"
                    ::= { integerObjects 23 }

        -- 1.3.6.1.4.1.9839.2.1.3.24
        offset-grad4 OBJECT-TYPE
                    SYNTAX Integer32 (-100..100)
                    UNITS "N/A"
                    MAX-ACCESS read-write
                    STATUS current
                    DESCRIPTION "OUT4: Energization"
                    ::= { integerObjects 24 }

        -- 1.3.6.1.4.1.9839.2.1.3.25
        diff-gradino4 OBJECT-TYPE
                    SYNTAX Integer32 (-100..100)
                    UNITS "N/A"
                    MAX-ACCESS read-write
                    STATUS current
                    DESCRIPTION "OUT4: Differential / Logic"
                    ::= { integerObjects 25 }

        -- 1.3.6.1.4.1.9839.2.1.3.26
        tast-telecom OBJECT-TYPE
                    SYNTAX Integer32 (0..4)
                    UNITS "N/A"
                    MAX-ACCESS read-write
                    STATUS current
                    DESCRIPTION "Operating keypad and/or remote control"
                    DEFVAL { 4 }
                    ::= { integerObjects 26 }

        -- 1.3.6.1.4.1.9839.2.1.3.27
        codice-telecom OBJECT-TYPE
                    SYNTAX Integer32 (0..120)
                    UNITS "N/A"
                    MAX-ACCESS read-write
                    STATUS current
                    DESCRIPTION "Operating the remote control"
                    DEFVAL { 0 }
                    ::= { integerObjects 27 }


	
	END

--
-- CAREL-ir32un-t.MIB
--
