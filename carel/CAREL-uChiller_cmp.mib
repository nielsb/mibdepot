--
-- CAREL-uchiller-cmp.MIB
-- MIB generated by CAREL
-- Friday, 14 March 2003
--

    CAREL-uchiller-cmp-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        uchiller-cmpMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the uchiller-cmp device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- uchiller-cmpMIB OBJECT IDENTIFIER ::= { instruments 1 }
		
        -- 1.3.6.1.4.1.9839.2.1.1
        digitalObjects OBJECT IDENTIFIER ::= { uchiller-cmpMIB 1 }

        -- 1.3.6.1.4.1.9839.2.1.1.1
        est-inv OBJECT-TYPE
                    SYNTAX Integer32 (0..1)
                    UNITS "N/A"
                    MAX-ACCESS read-write
                    STATUS current
                    DESCRIPTION "Cooling - Heating"
                    ::= { digitalObjects 1 }

        -- 1.3.6.1.4.1.9839.2.1.1.2
        on-off-unita OBJECT-TYPE
                    SYNTAX Integer32 (0..1)
                    UNITS "N/A"
                    MAX-ACCESS read-write
                    STATUS current
                    DESCRIPTION "On-Off if remote On/Off is disabled"
                    ::= { digitalObjects 2 }

        -- 1.3.6.1.4.1.9839.2.1.1.5
        allarme-hp OBJECT-TYPE
                    SYNTAX Integer32 (0..1)
                    UNITS "N/A"
                    MAX-ACCESS read-only
                    STATUS current
                    DESCRIPTION "High pressure alarm"
                    ::= { digitalObjects 5 }

        -- 1.3.6.1.4.1.9839.2.1.1.6
        allarme-lp OBJECT-TYPE
                    SYNTAX Integer32 (0..1)
                    UNITS "N/A"
                    MAX-ACCESS read-only
                    STATUS current
                    DESCRIPTION "Low pressure alarm"
                    ::= { digitalObjects 6 }

        -- 1.3.6.1.4.1.9839.2.1.1.8
        all-flusso OBJECT-TYPE
                    SYNTAX Integer32 (0..1)
                    UNITS "N/A"
                    MAX-ACCESS read-only
                    STATUS current
                    DESCRIPTION "Flowmeter alarm"
                    ::= { digitalObjects 8 }

        -- 1.3.6.1.4.1.9839.2.1.1.9
        err-sonda-b3 OBJECT-TYPE
                    SYNTAX Integer32 (0..1)
                    UNITS "N/A"
                    MAX-ACCESS read-only
                    STATUS current
                    DESCRIPTION "Probe b3 faulty or not connected"
                    ::= { digitalObjects 9 }

        -- 1.3.6.1.4.1.9839.2.1.1.10
        err-sonda-b2 OBJECT-TYPE
                    SYNTAX Integer32 (0..1)
                    UNITS "N/A"
                    MAX-ACCESS read-only
                    STATUS current
                    DESCRIPTION "Probe b2 faulty or not connected"
                    ::= { digitalObjects 10 }

        -- 1.3.6.1.4.1.9839.2.1.1.11
        err-sonda-b1 OBJECT-TYPE
                    SYNTAX Integer32 (0..1)
                    UNITS "N/A"
                    MAX-ACCESS read-only
                    STATUS current
                    DESCRIPTION "Probe b1 faulty or not connected"
                    ::= { digitalObjects 11 }

        -- 1.3.6.1.4.1.9839.2.1.1.13
        err-eeprom-s OBJECT-TYPE
                    SYNTAX Integer32 (0..1)
                    UNITS "N/A"
                    MAX-ACCESS read-only
                    STATUS current
                    DESCRIPTION "Faulty eeprom alarm"
                    ::= { digitalObjects 13 }

        -- 1.3.6.1.4.1.9839.2.1.1.16
        all-termin-off OBJECT-TYPE
                    SYNTAX Integer32 (0..1)
                    UNITS "N/A"
                    MAX-ACCESS read-only
                    STATUS current
                    DESCRIPTION "Alarm in the communic. with the remote terminal"
                    ::= { digitalObjects 16 }

        -- 1.3.6.1.4.1.9839.2.1.1.17
        sbrinamento-on OBJECT-TYPE
                    SYNTAX Integer32 (0..1)
                    UNITS "N/A"
                    MAX-ACCESS read-only
                    STATUS current
                    DESCRIPTION "Defrost in progress"
                    ::= { digitalObjects 17 }

        -- 1.3.6.1.4.1.9839.2.1.1.18
        all-sbrinamento OBJECT-TYPE
                    SYNTAX Integer32 (0..1)
                    UNITS "N/A"
                    MAX-ACCESS read-only
                    STATUS current
                    DESCRIPTION "Defrost timeout"
                    ::= { digitalObjects 18 }

        -- 1.3.6.1.4.1.9839.2.1.1.19
        all-antigelo OBJECT-TYPE
                    SYNTAX Integer32 (0..1)
                    UNITS "N/A"
                    MAX-ACCESS read-only
                    STATUS current
                    DESCRIPTION "Freezing alarm"
                    ::= { digitalObjects 19 }

        -- 1.3.6.1.4.1.9839.2.1.1.20
        all-agelo-sonda OBJECT-TYPE
                    SYNTAX Integer32 (0..1)
                    UNITS "N/A"
                    MAX-ACCESS read-only
                    STATUS current
                    DESCRIPTION "Low temperature alarm"
                    ::= { digitalObjects 20 }

        -- 1.3.6.1.4.1.9839.2.1.1.21
        all-sovratens OBJECT-TYPE
                    SYNTAX Integer32 (0..1)
                    UNITS "N/A"
                    MAX-ACCESS read-only
                    STATUS current
                    DESCRIPTION "Overvoltage alarm"
                    ::= { digitalObjects 21 }

        -- 1.3.6.1.4.1.9839.2.1.1.22
        all-sottotens OBJECT-TYPE
                    SYNTAX Integer32 (0..1)
                    UNITS "N/A"
                    MAX-ACCESS read-only
                    STATUS current
                    DESCRIPTION "Undervoltage alarm"
                    ::= { digitalObjects 22 }

        -- 1.3.6.1.4.1.9839.2.1.1.25
        stato-pompa OBJECT-TYPE
                    SYNTAX Integer32 (0..1)
                    UNITS "N/A"
                    MAX-ACCESS read-only
                    STATUS current
                    DESCRIPTION "Pump status"
                    ::= { digitalObjects 25 }

        -- 1.3.6.1.4.1.9839.2.1.1.26
        stato-compress OBJECT-TYPE
                    SYNTAX Integer32 (0..1)
                    UNITS "N/A"
                    MAX-ACCESS read-only
                    STATUS current
                    DESCRIPTION "Comp. 1 status"
                    ::= { digitalObjects 26 }

        -- 1.3.6.1.4.1.9839.2.1.1.27
        stato-resists OBJECT-TYPE
                    SYNTAX Integer32 (0..1)
                    UNITS "N/A"
                    MAX-ACCESS read-only
                    STATUS current
                    DESCRIPTION "Resist. status"
                    ::= { digitalObjects 27 }

        -- 1.3.6.1.4.1.9839.2.1.1.28
        stato-valvola OBJECT-TYPE
                    SYNTAX Integer32 (0..1)
                    UNITS "N/A"
                    MAX-ACCESS read-only
                    STATUS current
                    DESCRIPTION "Valve status"
                    ::= { digitalObjects 28 }

        -- 1.3.6.1.4.1.9839.2.1.1.30
        stato-ventils OBJECT-TYPE
                    SYNTAX Integer32 (0..1)
                    UNITS "N/A"
                    MAX-ACCESS read-only
                    STATUS current
                    DESCRIPTION "Fan status"
                    ::= { digitalObjects 30 }

        -- 1.3.6.1.4.1.9839.2.1.1.40
        unita-misura OBJECT-TYPE
                    SYNTAX Integer32 (0..1)
                    UNITS "flag"
                    MAX-ACCESS read-write
                    STATUS current
                    DESCRIPTION "Measurement Unit"
                    DEFVAL { 0 }
                    ::= { digitalObjects 40 }

        -- 1.3.6.1.4.1.9839.2.1.1.41
        out-per-fan-f1 OBJECT-TYPE
                    SYNTAX Integer32 (0..1)
                    UNITS "flags"
                    MAX-ACCESS read-write
                    STATUS current
                    DESCRIPTION "Fans Output"
                    DEFVAL { 0 }
                    ::= { digitalObjects 41 }

        -- 1.3.6.1.4.1.9839.2.1.1.42
        esecuz-sbrin-d1 OBJECT-TYPE
                    SYNTAX Integer32 (0..1)
                    UNITS "flag"
                    MAX-ACCESS read-write
                    STATUS current
                    DESCRIPTION "Defrosting cycle / condensation antifreeze"
                    DEFVAL { 1 }
                    ::= { digitalObjects 42 }

        -- 1.3.6.1.4.1.9839.2.1.1.43
        def-time-tmp-d2 OBJECT-TYPE
                    SYNTAX Integer32 (0..1)
                    UNITS "flag"
                    MAX-ACCESS read-write
                    STATUS current
                    DESCRIPTION "Timed or temperature-based defrosting"
                    DEFVAL { 0 }
                    ::= { digitalObjects 43 }

        -- 1.3.6.1.4.1.9839.2.1.1.44
        res-gelo-sbr-db OBJECT-TYPE
                    SYNTAX Integer32 (0..1)
                    UNITS "flag"
                    MAX-ACCESS read-write
                    STATUS current
                    DESCRIPTION "Antifreeze heaters activated while defrosting"
                    DEFVAL { 0 }
                    ::= { digitalObjects 44 }

        -- 1.3.6.1.4.1.9839.2.1.1.45
        en-sonda-res-a6 OBJECT-TYPE
                    SYNTAX Integer32 (0..1)
                    UNITS "flag"
                    MAX-ACCESS read-write
                    STATUS current
                    DESCRIPTION "Support heaters probe"
                    DEFVAL { 0 }
                    ::= { digitalObjects 45 }

        -- 1.3.6.1.4.1.9839.2.1.1.46
        all-lp-sonda-p7 OBJECT-TYPE
                    SYNTAX Integer32 (0..1)
                    UNITS "flag"
                    MAX-ACCESS read-write
                    STATUS current
                    DESCRIPTION "Low pressure alarm with pressure probes"
                    DEFVAL { 0 }
                    ::= { digitalObjects 46 }

        -- 1.3.6.1.4.1.9839.2.1.1.47
        en-id-on-off-h7 OBJECT-TYPE
                    SYNTAX Integer32 (0..1)
                    UNITS "flag"
                    MAX-ACCESS read-write
                    STATUS current
                    DESCRIPTION "ON/OFF digital input"
                    DEFVAL { 0 }
                    ::= { digitalObjects 47 }

        -- 1.3.6.1.4.1.9839.2.1.1.48
        all-lp-comp-pa OBJECT-TYPE
                    SYNTAX Integer32 (0..1)
                    UNITS "flag"
                    MAX-ACCESS read-write
                    STATUS current
                    DESCRIPTION "Low pressure alarm selection"
                    DEFVAL { 0 }
                    ::= { digitalObjects 48 }

        -- 1.3.6.1.4.1.9839.2.1.1.49
        en-set2-hc OBJECT-TYPE
                    SYNTAX Integer32 (0..1)
                    UNITS "flag"
                    MAX-ACCESS read-write
                    STATUS current
                    DESCRIPTION "Second set of param."
                    DEFVAL { 0 }
                    ::= { digitalObjects 49 }

        -- 1.3.6.1.4.1.9839.2.1.1.50
        inv-est-inv-hd OBJECT-TYPE
                    SYNTAX Integer32 (0..1)
                    UNITS "flag"
                    MAX-ACCESS read-write
                    STATUS current
                    DESCRIPTION "Logic inversion cooling/heating"
                    DEFVAL { 0 }
                    ::= { digitalObjects 50 }

        -- 1.3.6.1.4.1.9839.2.1.1.51
        sel-rele-all-hf OBJECT-TYPE
                    SYNTAX Integer32 (0..1)
                    UNITS "flag"
                    MAX-ACCESS read-write
                    STATUS current
                    DESCRIPTION "Alarm relay status without alarm condition"
                    DEFVAL { 1 }
                    ::= { digitalObjects 51 }

        -- 1.3.6.1.4.1.9839.2.1.1.55
        ab-estate-inv-h6 OBJECT-TYPE
                    SYNTAX Integer32 (0..1)
                    UNITS "flag"
                    MAX-ACCESS read-write
                    STATUS current
                    DESCRIPTION "Cooling/heating digital input with P8/P9 = 8, 9"
                    DEFVAL { 0 }
                    ::= { digitalObjects 55 }

        -- 1.3.6.1.4.1.9839.2.1.1.56
        rotaz-compr-r5 OBJECT-TYPE
                    SYNTAX Integer32 (0..1)
                    UNITS "N/A"
                    MAX-ACCESS read-only
                    STATUS current
                    DESCRIPTION "Compressor rotation"
                    DEFVAL { 3 }
                    ::= { digitalObjects 56 }



        -- 1.3.6.1.4.1.9839.2.1.2
        analogObjects OBJECT IDENTIFIER ::= { uchiller-cmpMIB 2 }

        -- 1.3.6.1.4.1.9839.2.1.2.1
        sonda-b1 OBJECT-TYPE
                    SYNTAX Integer32 (-32767..32767)
                    UNITS "N/A"
                    MAX-ACCESS read-only
                    STATUS current
                    DESCRIPTION "Inlet probe"
                    ::= { analogObjects 1 }

        -- 1.3.6.1.4.1.9839.2.1.2.2
        sonda-b2 OBJECT-TYPE
                    SYNTAX Integer32 (-32767..32767)
                    UNITS "N/A"
                    MAX-ACCESS read-only
                    STATUS current
                    DESCRIPTION "Water temperaturte at evaporator output B2"
                    ::= { analogObjects 2 }

        -- 1.3.6.1.4.1.9839.2.1.2.3
        sonda-b3 OBJECT-TYPE
                    SYNTAX Integer32 (-32767..32767)
                    UNITS "N/A"
                    MAX-ACCESS read-only
                    STATUS current
                    DESCRIPTION "Temperature/pressure defrosting B3"
                    ::= { analogObjects 3 }

        -- 1.3.6.1.4.1.9839.2.1.2.5
        i-scala-press OBJECT-TYPE
                    SYNTAX Integer32 (0..32767)
                    UNITS "bar x10"
                    MAX-ACCESS read-write
                    STATUS current
                    DESCRIPTION "Min. value current input"
                    DEFVAL { 0 }
                    ::= { analogObjects 5 }

        -- 1.3.6.1.4.1.9839.2.1.2.6
        f-scala-press OBJECT-TYPE
                    SYNTAX Integer32 (-32767..400)
                    UNITS "bar x10"
                    MAX-ACCESS read-write
                    STATUS current
                    DESCRIPTION "Max value current input"
                    DEFVAL { 300 }
                    ::= { analogObjects 6 }

        -- 1.3.6.1.4.1.9839.2.1.2.7
        calibra-b1 OBJECT-TYPE
                    SYNTAX Integer32 (-120..120)
                    UNITS "°C/°F x10"
                    MAX-ACCESS read-only
                    STATUS current
                    DESCRIPTION "Probe B1 calibration"
                    DEFVAL { 0 }
                    ::= { analogObjects 7 }

        -- 1.3.6.1.4.1.9839.2.1.2.8
        calibra-b2 OBJECT-TYPE
                    SYNTAX Integer32 (-120..120)
                    UNITS "°C/°F x10"
                    MAX-ACCESS read-only
                    STATUS current
                    DESCRIPTION "Probe outlet B2 calibration"
                    DEFVAL { 0 }
                    ::= { analogObjects 8 }

        -- 1.3.6.1.4.1.9839.2.1.2.9
        calibra-b3 OBJECT-TYPE
                    SYNTAX Integer32 (-120..120)
                    UNITS "°C/°F x10"
                    MAX-ACCESS read-only
                    STATUS current
                    DESCRIPTION "Defrosting probe B3 calibration"
                    DEFVAL { 0 }
                    ::= { analogObjects 9 }

        -- 1.3.6.1.4.1.9839.2.1.2.10
        setp-estate OBJECT-TYPE
                    SYNTAX Integer32 (-32767..32767)
                    UNITS "°C/°F x10"
                    MAX-ACCESS read-write
                    STATUS current
                    DESCRIPTION "Cooling Set-Point"
                    DEFVAL { 120 }
                    ::= { analogObjects 10 }

        -- 1.3.6.1.4.1.9839.2.1.2.11
        diff-estate OBJECT-TYPE
                    SYNTAX Integer32 (3..199)
                    UNITS "°C/°F x10"
                    MAX-ACCESS read-write
                    STATUS current
                    DESCRIPTION "Cooling differential"
                    DEFVAL { 30 }
                    ::= { analogObjects 11 }

        -- 1.3.6.1.4.1.9839.2.1.2.12
        setp-inverno OBJECT-TYPE
                    SYNTAX Integer32 (-32767..32767)
                    UNITS "°C/°F x10"
                    MAX-ACCESS read-write
                    STATUS current
                    DESCRIPTION "Heating set-point"
                    DEFVAL { 400 }
                    ::= { analogObjects 12 }

        -- 1.3.6.1.4.1.9839.2.1.2.13
        diff-inverno OBJECT-TYPE
                    SYNTAX Integer32 (3..199)
                    UNITS "°C/°F x10"
                    MAX-ACCESS read-write
                    STATUS current
                    DESCRIPTION "Heating differential"
                    DEFVAL { 30 }
                    ::= { analogObjects 13 }

        -- 1.3.6.1.4.1.9839.2.1.2.14
        min-set-est OBJECT-TYPE
                    SYNTAX Integer32 (-400..32767)
                    UNITS "°C/°F x10"
                    MAX-ACCESS read-write
                    STATUS current
                    DESCRIPTION "Min. Cooling set-point"
                    DEFVAL { -400 }
                    ::= { analogObjects 14 }

        -- 1.3.6.1.4.1.9839.2.1.2.15
        max-set-est OBJECT-TYPE
                    SYNTAX Integer32 (-32767..1990)
                    UNITS "°C/°F x10"
                    MAX-ACCESS read-write
                    STATUS current
                    DESCRIPTION "Max. Cooling set-point"
                    DEFVAL { 900 }
                    ::= { analogObjects 15 }

        -- 1.3.6.1.4.1.9839.2.1.2.16
        min-set-inv OBJECT-TYPE
                    SYNTAX Integer32 (-400..32767)
                    UNITS "°C/°F x10"
                    MAX-ACCESS read-write
                    STATUS current
                    DESCRIPTION "Min. Heating set-point"
                    DEFVAL { -400 }
                    ::= { analogObjects 16 }

        -- 1.3.6.1.4.1.9839.2.1.2.17
        max-set-inv OBJECT-TYPE
                    SYNTAX Integer32 (-32767..1990)
                    UNITS "°C/°F x10"
                    MAX-ACCESS read-write
                    STATUS current
                    DESCRIPTION "Max. Heating set-point"
                    DEFVAL { 900 }
                    ::= { analogObjects 17 }

        -- 1.3.6.1.4.1.9839.2.1.2.18
        tmin-vel-est-f5 OBJECT-TYPE
                    SYNTAX Integer32 (-32767..32767)
                    UNITS "°C/°F bar x10"
                    MAX-ACCESS read-write
                    STATUS current
                    DESCRIPTION "Temperature value for min Cooling speed .Pressure"
                    DEFVAL { 130 }
                    ::= { analogObjects 18 }

        -- 1.3.6.1.4.1.9839.2.1.2.19
        tmax-vel-est-f6 OBJECT-TYPE
                    SYNTAX Integer32 (-32767..32767)
                    UNITS "°C/°F bar x10"
                    MAX-ACCESS read-write
                    STATUS current
                    DESCRIPTION "Temperature value for max Cooling speed. Pressure"
                    DEFVAL { 160 }
                    ::= { analogObjects 19 }

        -- 1.3.6.1.4.1.9839.2.1.2.20
        tmin-vel-inv-f7 OBJECT-TYPE
                    SYNTAX Integer32 (-32767..32767)
                    UNITS "°C/°F bar x10"
                    MAX-ACCESS read-write
                    STATUS current
                    DESCRIPTION "Temperature value for min Heating speed. Pressure"
                    DEFVAL { 130 }
                    ::= { analogObjects 20 }

        -- 1.3.6.1.4.1.9839.2.1.2.21
        tmax-vel-inv-f8 OBJECT-TYPE
                    SYNTAX Integer32 (-32767..32767)
                    UNITS "°C/°F bar x10"
                    MAX-ACCESS read-write
                    STATUS current
                    DESCRIPTION "Temperature value for max Heating speed.Pressure"
                    DEFVAL { 90 }
                    ::= { analogObjects 21 }

        -- 1.3.6.1.4.1.9839.2.1.2.22
        toff-fan-est-f9 OBJECT-TYPE
                    SYNTAX Integer32 (-32767..32767)
                    UNITS "°C/°F bar x10"
                    MAX-ACCESS read-write
                    STATUS current
                    DESCRIPTION "Temperature to turn OFF the fan in Cooling .Pressure"
                    DEFVAL { 80 }
                    ::= { analogObjects 22 }

        -- 1.3.6.1.4.1.9839.2.1.2.23
        toff-fan-inv-fa OBJECT-TYPE
                    SYNTAX Integer32 (-32767..32767)
                    UNITS "°C/°F bar x10"
                    MAX-ACCESS read-write
                    STATUS current
                    DESCRIPTION "Temperature to turn OFF the fan in Winter. Pressure"
                    DEFVAL { 160 }
                    ::= { analogObjects 23 }

        -- 1.3.6.1.4.1.9839.2.1.2.24
        parametro-d3 OBJECT-TYPE
                    SYNTAX Integer32 (-32767..32767)
                    UNITS "°C/°F bar x10"
                    MAX-ACCESS read-write
                    STATUS current
                    DESCRIPTION "Temperat./pressure starting the defrost.cycle"
                    DEFVAL { 35 }
                    ::= { analogObjects 24 }

        -- 1.3.6.1.4.1.9839.2.1.2.25
        parametro-d4 OBJECT-TYPE
                    SYNTAX Integer32 (-32767..32767)
                    UNITS "°C/°F bar x10"
                    MAX-ACCESS read-write
                    STATUS current
                    DESCRIPTION "End-defrosting temperature/pressure"
                    DEFVAL { 140 }
                    ::= { analogObjects 25 }

        -- 1.3.6.1.4.1.9839.2.1.2.26
        set-al-agelo-a1 OBJECT-TYPE
                    SYNTAX Integer32 (-32767..32767)
                    UNITS "°C/°F x10"
                    MAX-ACCESS read-write
                    STATUS current
                    DESCRIPTION "Antifreeze"
                    DEFVAL { 30 }
                    ::= { analogObjects 26 }

        -- 1.3.6.1.4.1.9839.2.1.2.27
        dif-al-agelo-a2 OBJECT-TYPE
                    SYNTAX Integer32 (3..199)
                    UNITS "°C/°F x10"
                    MAX-ACCESS read-write
                    STATUS current
                    DESCRIPTION "Differential for antifreeze/low ambient temperatur"
                    DEFVAL { 50 }
                    ::= { analogObjects 27 }

        -- 1.3.6.1.4.1.9839.2.1.2.28
        set-res-gelo-a4 OBJECT-TYPE
                    SYNTAX Integer32 (-32767..32767)
                    UNITS "°C/°F x10"
                    MAX-ACCESS read-write
                    STATUS current
                    DESCRIPTION "Setpoint for the activation of antifreeze supp."
                    DEFVAL { 50 }
                    ::= { analogObjects 28 }

        -- 1.3.6.1.4.1.9839.2.1.2.29
        dif-res-gelo-a5 OBJECT-TYPE
                    SYNTAX Integer32 (3..199)
                    UNITS "°C/°F x10"
                    MAX-ACCESS read-write
                    STATUS current
                    DESCRIPTION "Antifreeze/Support heaters differential"
                    DEFVAL { 10 }
                    ::= { analogObjects 29 }

        -- 1.3.6.1.4.1.9839.2.1.2.30
        lim-set-gelo-a7 OBJECT-TYPE
                    SYNTAX Integer32 (-400..1220)
                    UNITS "°C/°F x10"
                    MAX-ACCESS read-write
                    STATUS current
                    DESCRIPTION "Antifreeze-alarm set"
                    DEFVAL { -400 }
                    ::= { analogObjects 30 }

        -- 1.3.6.1.4.1.9839.2.1.2.31
        set-res-risc-a8 OBJECT-TYPE
                    SYNTAX Integer32 (-32767..32767)
                    UNITS "°C/°F x10"
                    MAX-ACCESS read-write
                    STATUS current
                    DESCRIPTION "Heating support-resistance set"
                    DEFVAL { 250 }
                    ::= { analogObjects 31 }

        -- 1.3.6.1.4.1.9839.2.1.2.32
        dif-res-risc-a9 OBJECT-TYPE
                    SYNTAX Integer32 (3..199)
                    UNITS "°C/°F x10"
                    MAX-ACCESS read-write
                    STATUS current
                    DESCRIPTION "Heating support-resistance differential"
                    DEFVAL { 30 }
                    ::= { analogObjects 32 }

        -- 1.3.6.1.4.1.9839.2.1.2.33
        set-all-at-pb OBJECT-TYPE
                    SYNTAX Integer32 (-400..1990)
                    UNITS "/d x10"
                    MAX-ACCESS read-write
                    STATUS current
                    DESCRIPTION "High temperature alarm set"
                    DEFVAL { 900 }
                    ::= { analogObjects 33 }

        -- 1.3.6.1.4.1.9839.2.1.2.34
        sonda-b4 OBJECT-TYPE
                    SYNTAX Integer32 (-32767..32767)
                    UNITS "N/A"
                    MAX-ACCESS read-only
                    STATUS current
                    DESCRIPTION "Probe B4"
                    ::= { analogObjects 34 }



        -- 1.3.6.1.4.1.9839.2.1.3
        integerObjects OBJECT IDENTIFIER ::= { uchiller-cmpMIB 3 }

        -- 1.3.6.1.4.1.9839.2.1.3.1
        tipo-sonda-cond OBJECT-TYPE
                    SYNTAX Integer32 (0..2)
                    UNITS "flag"
                    MAX-ACCESS read-write
                    STATUS current
                    DESCRIPTION "Type of condensation probe"
                    DEFVAL { 1 }
                    ::= { integerObjects 1 }

        -- 1.3.6.1.4.1.9839.2.1.3.1
        velocita-vent OBJECT-TYPE
                    SYNTAX Integer32 (-32767..32767)
                    UNITS "N/A"
                    MAX-ACCESS read-only
                    STATUS current
                    DESCRIPTION "Fan speed 0-100%"
                    ::= { integerObjects 1 }

        -- 1.3.6.1.4.1.9839.2.1.3.6
        filtro-digitale OBJECT-TYPE
                    SYNTAX Integer32 (1..15)
                    UNITS "N/A"
                    MAX-ACCESS read-write
                    STATUS current
                    DESCRIPTION "Digital filter"
                    DEFVAL { 4 }
                    ::= { integerObjects 6 }

        -- 1.3.6.1.4.1.9839.2.1.3.6
        limitaz-input OBJECT-TYPE
                    SYNTAX Integer32 (1..15)
                    UNITS "N/A"
                    MAX-ACCESS read-write
                    STATUS current
                    DESCRIPTION "Input limitation"
                    DEFVAL { 8 }
                    ::= { integerObjects 6 }

        -- 1.3.6.1.4.1.9839.2.1.3.8
        tmin-on-comp-c1 OBJECT-TYPE
                    SYNTAX Integer32 (0..150)
                    UNITS "sec"
                    MAX-ACCESS read-write
                    STATUS current
                    DESCRIPTION "Min. running time"
                    DEFVAL { 60 }
                    ::= { integerObjects 8 }

        -- 1.3.6.1.4.1.9839.2.1.3.9
        tmin-sp-comp-c2 OBJECT-TYPE
                    SYNTAX Integer32 (0..90)
                    UNITS "10 sec"
                    MAX-ACCESS read-write
                    STATUS current
                    DESCRIPTION "Min. stopping time"
                    DEFVAL { 6 }
                    ::= { integerObjects 9 }

        -- 1.3.6.1.4.1.9839.2.1.3.10
        time-2-acc-c3 OBJECT-TYPE
                    SYNTAX Integer32 (0..90)
                    UNITS "10 sec"
                    MAX-ACCESS read-write
                    STATUS current
                    DESCRIPTION "Time interval between 2 starts"
                    DEFVAL { 36 }
                    ::= { integerObjects 10 }

        -- 1.3.6.1.4.1.9839.2.1.3.11
        rit-on-comp-c6 OBJECT-TYPE
                    SYNTAX Integer32 (0..150)
                    UNITS "sec"
                    MAX-ACCESS read-write
                    STATUS current
                    DESCRIPTION "Delay at start-up"
                    DEFVAL { 0 }
                    ::= { integerObjects 11 }

        -- 1.3.6.1.4.1.9839.2.1.3.12
        rit-c-on-pmp-c7 OBJECT-TYPE
                    SYNTAX Integer32 (0..150)
                    UNITS "sec"
                    MAX-ACCESS read-write
                    STATUS current
                    DESCRIPTION "Delay in switching on compressor after switch. On"
                    DEFVAL { 20 }
                    ::= { integerObjects 12 }

        -- 1.3.6.1.4.1.9839.2.1.3.13
        off-p-off-v-c8 OBJECT-TYPE
                    SYNTAX Integer32 (0..150)
                    UNITS "min"
                    MAX-ACCESS read-write
                    STATUS current
                    DESCRIPTION "Delay in switching off compress. After switc.off"
                    DEFVAL { 20 }
                    ::= { integerObjects 13 }

        -- 1.3.6.1.4.1.9839.2.1.3.14
        contaore-c1-c9 OBJECT-TYPE
                    SYNTAX Integer32 (0..19900)
                    UNITS "hours"
                    MAX-ACCESS read-only
                    STATUS current
                    DESCRIPTION "Hour counter comp. 1"
                    DEFVAL { 0 }
                    ::= { integerObjects 14 }

        -- 1.3.6.1.4.1.9839.2.1.3.15
        max-ore-comp-cb OBJECT-TYPE
                    SYNTAX Integer32 (0..100)
                    UNITS "100 hours"
                    MAX-ACCESS read-write
                    STATUS current
                    DESCRIPTION "Timer threshold during normal operation"
                    DEFVAL { 0 }
                    ::= { integerObjects 15 }

        -- 1.3.6.1.4.1.9839.2.1.3.16
        ore-pmp-vent-cc OBJECT-TYPE
                    SYNTAX Integer32 (0..19900)
                    UNITS "hours"
                    MAX-ACCESS read-only
                    STATUS current
                    DESCRIPTION "Pump/inlet fan timer"
                    DEFVAL { 0 }
                    ::= { integerObjects 16 }

        -- 1.3.6.1.4.1.9839.2.1.3.17
        modo-vent-f2 OBJECT-TYPE
                    SYNTAX Integer32 (0..3)
                    UNITS "flags"
                    MAX-ACCESS read-write
                    STATUS current
                    DESCRIPTION "Operating logic of the fans"
                    DEFVAL { 0 }
                    ::= { integerObjects 17 }

        -- 1.3.6.1.4.1.9839.2.1.3.18
        min-volt-f3 OBJECT-TYPE
                    SYNTAX Integer32 (0..32767)
                    UNITS "step"
                    MAX-ACCESS read-write
                    STATUS current
                    DESCRIPTION "Minimum tension threshold for Triac"
                    DEFVAL { 35 }
                    ::= { integerObjects 18 }

        -- 1.3.6.1.4.1.9839.2.1.3.19
        max-volt-f4 OBJECT-TYPE
                    SYNTAX Integer32 (-32767..100)
                    UNITS "step"
                    MAX-ACCESS read-write
                    STATUS current
                    DESCRIPTION "Max.tension threshold for Triac"
                    DEFVAL { 75 }
                    ::= { integerObjects 19 }

        -- 1.3.6.1.4.1.9839.2.1.3.20
        t-spunto-v-fb OBJECT-TYPE
                    SYNTAX Integer32 (0..99)
                    UNITS "sec"
                    MAX-ACCESS read-write
                    STATUS current
                    DESCRIPTION "Starting time of fans"
                    DEFVAL { 4 }
                    ::= { integerObjects 20 }

        -- 1.3.6.1.4.1.9839.2.1.3.21
        t-imp-triac-fc OBJECT-TYPE
                    SYNTAX Integer32 (0..15)
                    UNITS "msec"
                    MAX-ACCESS read-write
                    STATUS current
                    DESCRIPTION "Triac impulse duration"
                    DEFVAL { 2 }
                    ::= { integerObjects 21 }

        -- 1.3.6.1.4.1.9839.2.1.3.22
        t-min-on-def-d5 OBJECT-TYPE
                    SYNTAX Integer32 (10..150)
                    UNITS "sec"
                    MAX-ACCESS read-write
                    STATUS current
                    DESCRIPTION "Minimum time interval before starting a defr. Cycl"
                    DEFVAL { 10 }
                    ::= { integerObjects 22 }

        -- 1.3.6.1.4.1.9839.2.1.3.23
        t-min-def-d6 OBJECT-TYPE
                    SYNTAX Integer32 (0..150)
                    UNITS "sec"
                    MAX-ACCESS read-write
                    STATUS current
                    DESCRIPTION "Min. duration of a defrosting cycle"
                    DEFVAL { 0 }
                    ::= { integerObjects 23 }

        -- 1.3.6.1.4.1.9839.2.1.3.24
        t-max-def-d7 OBJECT-TYPE
                    SYNTAX Integer32 (1..15)
                    UNITS "min"
                    MAX-ACCESS read-write
                    STATUS current
                    DESCRIPTION "Max. duration of a defrosting cycle"
                    DEFVAL { 5 }
                    ::= { integerObjects 24 }

        -- 1.3.6.1.4.1.9839.2.1.3.25
        rit-tra-2def-d8 OBJECT-TYPE
                    SYNTAX Integer32 (10..150)
                    UNITS "min"
                    MAX-ACCESS read-write
                    STATUS current
                    DESCRIPTION "Time-delay between 2 defrosting"
                    DEFVAL { 30 }
                    ::= { integerObjects 25 }

        -- 1.3.6.1.4.1.9839.2.1.3.26
        wait-on-def-dc OBJECT-TYPE
                    SYNTAX Integer32 (0..3)
                    UNITS "min"
                    MAX-ACCESS read-write
                    STATUS current
                    DESCRIPTION "Delay before defrosting"
                    DEFVAL { 0 }
                    ::= { integerObjects 26 }

        -- 1.3.6.1.4.1.9839.2.1.3.27
        wait-end-def-dd OBJECT-TYPE
                    SYNTAX Integer32 (0..3)
                    UNITS "min"
                    MAX-ACCESS read-write
                    STATUS current
                    DESCRIPTION "Delay after defrosting"
                    DEFVAL { 0 }
                    ::= { integerObjects 27 }

        -- 1.3.6.1.4.1.9839.2.1.3.28
        rit-all-ag-a3 OBJECT-TYPE
                    SYNTAX Integer32 (0..150)
                    UNITS "sec"
                    MAX-ACCESS read-write
                    STATUS current
                    DESCRIPTION "Time to bypass the antfreeze/low amb. Temp. allarm"
                    DEFVAL { 0 }
                    ::= { integerObjects 28 }

        -- 1.3.6.1.4.1.9839.2.1.3.29
        r-al-on-flux-p1 OBJECT-TYPE
                    SYNTAX Integer32 (0..150)
                    UNITS "sec"
                    MAX-ACCESS read-write
                    STATUS current
                    DESCRIPTION "Flowmeter down delayed when starting the pump"
                    DEFVAL { 20 }
                    ::= { integerObjects 29 }

        -- 1.3.6.1.4.1.9839.2.1.3.30
        r-al-rg-flux-p2 OBJECT-TYPE
                    SYNTAX Integer32 (0..90)
                    UNITS "sec"
                    MAX-ACCESS read-write
                    STATUS current
                    DESCRIPTION "Flowswitch alarm delayed during normal operating"
                    DEFVAL { 5 }
                    ::= { integerObjects 30 }

        -- 1.3.6.1.4.1.9839.2.1.3.31
        rit-all-lp-p3 OBJECT-TYPE
                    SYNTAX Integer32 (0..199)
                    UNITS "sec"
                    MAX-ACCESS read-write
                    STATUS current
                    DESCRIPTION "Low pressure alarm delayed at compr. start-up"
                    DEFVAL { 40 }
                    ::= { integerObjects 31 }

        -- 1.3.6.1.4.1.9839.2.1.3.32
        t-buzzer-p4 OBJECT-TYPE
                    SYNTAX Integer32 (0..15)
                    UNITS "min"
                    MAX-ACCESS read-write
                    STATUS current
                    DESCRIPTION "Buzzer ON"
                    DEFVAL { 0 }
                    ::= { integerObjects 32 }

        -- 1.3.6.1.4.1.9839.2.1.3.33
        riprist-all-p5 OBJECT-TYPE
                    SYNTAX Integer32 (0..4)
                    UNITS "flag"
                    MAX-ACCESS read-write
                    STATUS current
                    DESCRIPTION "Reset of alarms"
                    DEFVAL { 0 }
                    ::= { integerObjects 33 }

        -- 1.3.6.1.4.1.9839.2.1.3.34
        selez-id1-p8 OBJECT-TYPE
                    SYNTAX Integer32 (0..7)
                    UNITS "flag"
                    MAX-ACCESS read-write
                    STATUS current
                    DESCRIPTION "Sel. of the digital input"
                    DEFVAL { 0 }
                    ::= { integerObjects 34 }

        -- 1.3.6.1.4.1.9839.2.1.3.35
        selez-id2-p9 OBJECT-TYPE
                    SYNTAX Integer32 (-32767..32767)
                    UNITS "N/A"
                    MAX-ACCESS read-write
                    STATUS current
                    DESCRIPTION "Sel. of the digital input n.2"
                    ::= { integerObjects 35 }

        -- 1.3.6.1.4.1.9839.2.1.3.36
        modello-mac-h1 OBJECT-TYPE
                    SYNTAX Integer32 (0..8)
                    UNITS "flag"
                    MAX-ACCESS read-only
                    STATUS current
                    DESCRIPTION "Unit model"
                    DEFVAL { 2 }
                    ::= { integerObjects 36 }

        -- 1.3.6.1.4.1.9839.2.1.3.37
        modo-pmp-vnt-h5 OBJECT-TYPE
                    SYNTAX Integer32 (0..2)
                    UNITS "flag"
                    MAX-ACCESS read-write
                    STATUS current
                    DESCRIPTION "Operating logic of the Pump/Inlet fan"
                    DEFVAL { 1 }
                    ::= { integerObjects 37 }

        -- 1.3.6.1.4.1.9839.2.1.3.38
        blocca-tasti-h9 OBJECT-TYPE
                    SYNTAX Integer32 (0..3)
                    UNITS "flag"
                    MAX-ACCESS read-write
                    STATUS current
                    DESCRIPTION "Keyboard lock-up"
                    DEFVAL { 1 }
                    ::= { integerObjects 38 }

        -- 1.3.6.1.4.1.9839.2.1.3.39
        seradd OBJECT-TYPE
                    SYNTAX Integer32 (1..199)
                    UNITS "N/A"
                    MAX-ACCESS read-write
                    STATUS current
                    DESCRIPTION "Serial address"
                    DEFVAL { 1 }
                    ::= { integerObjects 39 }

        -- 1.3.6.1.4.1.9839.2.1.3.40
        passw-telec-hb OBJECT-TYPE
                    SYNTAX Integer32 (0..15)
                    UNITS "N/A"
                    MAX-ACCESS read-write
                    STATUS current
                    DESCRIPTION "Infrared remote unit password"
                    DEFVAL { 0 }
                    ::= { integerObjects 40 }

        -- 1.3.6.1.4.1.9839.2.1.3.41
        valv-inv-ch-he OBJECT-TYPE
                    SYNTAX Integer32 (0..2)
                    UNITS "flag"
                    MAX-ACCESS read-write
                    STATUS current
                    DESCRIPTION "Valve status cooling"
                    DEFVAL { 0 }
                    ::= { integerObjects 41 }

        -- 1.3.6.1.4.1.9839.2.1.3.42
        numero-term-h8 OBJECT-TYPE
                    SYNTAX Integer32 (0..1)
                    UNITS "flag"
                    MAX-ACCESS read-write
                    STATUS current
                    DESCRIPTION "Number of terminals"
                    DEFVAL { 0 }
                    ::= { integerObjects 42 }

        -- 1.3.6.1.4.1.9839.2.1.3.43
        high-temp-all-pc OBJECT-TYPE
                    SYNTAX Integer32 (0..150)
                    UNITS "min"
                    MAX-ACCESS read-write
                    STATUS current
                    DESCRIPTION "High temperature alarm delayed at start-up"
                    DEFVAL { 30 }
                    ::= { integerObjects 43 }

        -- 1.3.6.1.4.1.9839.2.1.3.51
        versione-sw-hg OBJECT-TYPE
                    SYNTAX Integer32 (-32767..32767)
                    UNITS "N/A"
                    MAX-ACCESS read-only
                    STATUS current
                    DESCRIPTION "SW Release"
                    DEFVAL { 1.3 }
                    ::= { integerObjects 51 }

        -- 1.3.6.1.4.1.9839.2.1.3.52
        rit-acc-comp OBJECT-TYPE
                    SYNTAX Integer32 (-32767..32767)
                    UNITS "sec"
                    MAX-ACCESS read-only
                    STATUS current
                    DESCRIPTION "Start delay between the two compressors"
                    ::= { integerObjects 52 }

        -- 1.3.6.1.4.1.9839.2.1.3.53
        rit-spegn-comp OBJECT-TYPE
                    SYNTAX Integer32 (0..15)
                    UNITS "sec"
                    MAX-ACCESS read-only
                    STATUS current
                    DESCRIPTION "Stop delay between the two compressors"
                    DEFVAL { 0 }
                    ::= { integerObjects 53 }

        -- 1.3.6.1.4.1.9839.2.1.3.56
        tempo-acc-pompa OBJECT-TYPE
                    SYNTAX Integer32 (1..150)
                    UNITS "min"
                    MAX-ACCESS read-only
                    STATUS current
                    DESCRIPTION "Minimum time between two pump starts"
                    DEFVAL { 30 }
                    ::= { integerObjects 56 }


	
	END

--
-- CAREL-uchiller-cmp.MIB
--
