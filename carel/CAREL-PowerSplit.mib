--
-- CAREL-powersplit.MIB
-- MIB generated by CAREL
-- Friday, 14 March 2003
--

    CAREL-powersplit-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        powersplitMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the powersplit device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- powersplitMIB OBJECT IDENTIFIER ::= { instruments 1 }
		
        -- 1.3.6.1.4.1.9839.2.1.1
        digitalObjects OBJECT IDENTIFIER ::= { powersplitMIB 1 }

        -- 1.3.6.1.4.1.9839.2.1.1.1
        cent-fhren-flag OBJECT-TYPE
                    SYNTAX Integer32 (0..1)
                    UNITS "N/A"
                    MAX-ACCESS read-write
                    STATUS current
                    DESCRIPTION "°C/°F selection"
                    DEFVAL { 0 }
                    ::= { digitalObjects 1 }

        -- 1.3.6.1.4.1.9839.2.1.1.2
        autoscale OBJECT-TYPE
                    SYNTAX Integer32 (0..1)
                    UNITS "N/A"
                    MAX-ACCESS read-write
                    STATUS current
                    DESCRIPTION "Decimal point"
                    DEFVAL { 0 }
                    ::= { digitalObjects 2 }

        -- 1.3.6.1.4.1.9839.2.1.1.3
        defrostprobeselect OBJECT-TYPE
                    SYNTAX Integer32 (0..1)
                    UNITS "N/A"
                    MAX-ACCESS read-write
                    STATUS current
                    DESCRIPTION "Defrost with probe 3"
                    DEFVAL { 0 }
                    ::= { digitalObjects 3 }

        -- 1.3.6.1.4.1.9839.2.1.1.4
        defrost-cmd OBJECT-TYPE
                    SYNTAX Integer32 (0..1)
                    UNITS "flag"
                    MAX-ACCESS read-write
                    STATUS current
                    DESCRIPTION "Type of network control"
                    DEFVAL { 0 }
                    ::= { digitalObjects 4 }

        -- 1.3.6.1.4.1.9839.2.1.1.5
        defrost-at-startup OBJECT-TYPE
                    SYNTAX Integer32 (0..1)
                    UNITS "flag"
                    MAX-ACCESS read-write
                    STATUS current
                    DESCRIPTION "Defrost at startup"
                    DEFVAL { 0 }
                    ::= { digitalObjects 5 }

        -- 1.3.6.1.4.1.9839.2.1.1.6
        defrost-show OBJECT-TYPE
                    SYNTAX Integer32 (0..1)
                    UNITS "flag"
                    MAX-ACCESS read-write
                    STATUS current
                    DESCRIPTION "Management of main and remote display during defrost"
                    DEFVAL { 1 }
                    ::= { digitalObjects 6 }

        -- 1.3.6.1.4.1.9839.2.1.1.7
        defrost-priority OBJECT-TYPE
                    SYNTAX Integer32 (0..1)
                    UNITS "flag"
                    MAX-ACCESS read-write
                    STATUS current
                    DESCRIPTION "Priority of defrost over compressor protection"
                    DEFVAL { 0 }
                    ::= { digitalObjects 7 }

        -- 1.3.6.1.4.1.9839.2.1.1.8
        fan-cfg OBJECT-TYPE
                    SYNTAX Integer32 (0..1)
                    UNITS "N/A"
                    MAX-ACCESS read-write
                    STATUS current
                    DESCRIPTION "Fan management"
                    DEFVAL { 0 }
                    ::= { digitalObjects 8 }

        -- 1.3.6.1.4.1.9839.2.1.1.9
        fan-off-ctrl OBJECT-TYPE
                    SYNTAX Integer32 (0..1)
                    UNITS "N/A"
                    MAX-ACCESS read-write
                    STATUS current
                    DESCRIPTION "Fans off when compressor off"
                    DEFVAL { 1 }
                    ::= { digitalObjects 9 }

        -- 1.3.6.1.4.1.9839.2.1.1.10
        fan-defrost-ctrl OBJECT-TYPE
                    SYNTAX Integer32 (0..1)
                    UNITS "N/A"
                    MAX-ACCESS read-write
                    STATUS current
                    DESCRIPTION "Fans off during defrost"
                    DEFVAL { 1 }
                    ::= { digitalObjects 10 }

        -- 1.3.6.1.4.1.9839.2.1.1.11
        keyb-disabled OBJECT-TYPE
                    SYNTAX Integer32 (0..1)
                    UNITS "N/A"
                    MAX-ACCESS read-write
                    STATUS current
                    DESCRIPTION "Disable keypad"
                    DEFVAL { 0 }
                    ::= { digitalObjects 11 }

        -- 1.3.6.1.4.1.9839.2.1.1.12
        loc-on-off-ena OBJECT-TYPE
                    SYNTAX Integer32 (0..1)
                    UNITS "N/A"
                    MAX-ACCESS read-write
                    STATUS current
                    DESCRIPTION "Enable on/off button"
                    DEFVAL { 0 }
                    ::= { digitalObjects 12 }

        -- 1.3.6.1.4.1.9839.2.1.1.13
        lan-on-off-ena OBJECT-TYPE
                    SYNTAX Integer32 (0..1)
                    UNITS "N/A"
                    MAX-ACCESS read-write
                    STATUS current
                    DESCRIPTION "Enable network on/off"
                    DEFVAL { 0 }
                    ::= { digitalObjects 13 }

        -- 1.3.6.1.4.1.9839.2.1.1.14
        lan-din OBJECT-TYPE
                    SYNTAX Integer32 (0..1)
                    UNITS "N/A"
                    MAX-ACCESS read-write
                    STATUS current
                    DESCRIPTION "DIN2 status propagation"
                    DEFVAL { 0 }
                    ::= { digitalObjects 14 }

        -- 1.3.6.1.4.1.9839.2.1.1.15
        defrost-tout-alarm-ena OBJECT-TYPE
                    SYNTAX Integer32 (0..1)
                    UNITS "N/A"
                    MAX-ACCESS read-write
                    STATUS current
                    DESCRIPTION "Enable alarm Ed"
                    DEFVAL { 0 }
                    ::= { digitalObjects 15 }

        -- 1.3.6.1.4.1.9839.2.1.1.16
        minmax-store-enable OBJECT-TYPE
                    SYNTAX Integer32 (0..1)
                    UNITS "N/A"
                    MAX-ACCESS read-write
                    STATUS current
                    DESCRIPTION "Enable min and max temperature monitoring"
                    DEFVAL { 0 }
                    ::= { digitalObjects 16 }

        -- 1.3.6.1.4.1.9839.2.1.1.17
        night-reg-probe OBJECT-TYPE
                    SYNTAX Integer32 (0..1)
                    UNITS "N/A"
                    MAX-ACCESS read-write
                    STATUS current
                    DESCRIPTION "Night-time control with 3rd probe"
                    DEFVAL { 0 }
                    ::= { digitalObjects 17 }

        -- 1.3.6.1.4.1.9839.2.1.1.18
        haccp-reset OBJECT-TYPE
                    SYNTAX Integer32 (0..1)
                    UNITS "N/A"
                    MAX-ACCESS read-write
                    STATUS current
                    DESCRIPTION "HACCP alarm indicator / reset"
                    DEFVAL { 0 }
                    ::= { digitalObjects 18 }

        -- 1.3.6.1.4.1.9839.2.1.1.29
        dig-in-1 OBJECT-TYPE
                    SYNTAX Integer32 (0..1)
                    UNITS "N/A"
                    MAX-ACCESS read-only
                    STATUS current
                    DESCRIPTION "Digital input 1"
                    ::= { digitalObjects 29 }

        -- 1.3.6.1.4.1.9839.2.1.1.30
        dig-in-2 OBJECT-TYPE
                    SYNTAX Integer32 (0..1)
                    UNITS "N/A"
                    MAX-ACCESS read-only
                    STATUS current
                    DESCRIPTION "Digital input 2"
                    ::= { digitalObjects 30 }

        -- 1.3.6.1.4.1.9839.2.1.1.33
        s-comp OBJECT-TYPE
                    SYNTAX Integer32 (0..1)
                    UNITS "N/A"
                    MAX-ACCESS read-only
                    STATUS current
                    DESCRIPTION "Compressor status"
                    ::= { digitalObjects 33 }

        -- 1.3.6.1.4.1.9839.2.1.1.34
        s-fan OBJECT-TYPE
                    SYNTAX Integer32 (0..1)
                    UNITS "N/A"
                    MAX-ACCESS read-only
                    STATUS current
                    DESCRIPTION "Fan status"
                    ::= { digitalObjects 34 }

        -- 1.3.6.1.4.1.9839.2.1.1.35
        s-defrost OBJECT-TYPE
                    SYNTAX Integer32 (0..1)
                    UNITS "N/A"
                    MAX-ACCESS read-only
                    STATUS current
                    DESCRIPTION "Defrost status"
                    ::= { digitalObjects 35 }

        -- 1.3.6.1.4.1.9839.2.1.1.36
        s-aux-2 OBJECT-TYPE
                    SYNTAX Integer32 (0..1)
                    UNITS "N/A"
                    MAX-ACCESS read-only
                    STATUS current
                    DESCRIPTION "Auxiliary status"
                    ::= { digitalObjects 36 }

        -- 1.3.6.1.4.1.9839.2.1.1.37
        s-alarm OBJECT-TYPE
                    SYNTAX Integer32 (0..1)
                    UNITS "N/A"
                    MAX-ACCESS read-only
                    STATUS current
                    DESCRIPTION "Alarm status"
                    ::= { digitalObjects 37 }

        -- 1.3.6.1.4.1.9839.2.1.1.39
        s-light OBJECT-TYPE
                    SYNTAX Integer32 (0..1)
                    UNITS "N/A"
                    MAX-ACCESS read-only
                    STATUS current
                    DESCRIPTION "Light status"
                    ::= { digitalObjects 39 }

        -- 1.3.6.1.4.1.9839.2.1.1.40
        dr-supervisor OBJECT-TYPE
                    SYNTAX Integer32 (0..1)
                    UNITS "N/A"
                    MAX-ACCESS read-write
                    STATUS current
                    DESCRIPTION "Start defrost request"
                    ::= { digitalObjects 40 }

        -- 1.3.6.1.4.1.9839.2.1.1.41
        dr-svendreq OBJECT-TYPE
                    SYNTAX Integer32 (0..1)
                    UNITS "N/A"
                    MAX-ACCESS read-write
                    STATUS current
                    DESCRIPTION "Stop defrost request"
                    ::= { digitalObjects 41 }

        -- 1.3.6.1.4.1.9839.2.1.1.44
        a1-e1 OBJECT-TYPE
                    SYNTAX Integer32 (0..1)
                    UNITS "N/A"
                    MAX-ACCESS read-only
                    STATUS current
                    DESCRIPTION "Probe 1 error"
                    ::= { digitalObjects 44 }

        -- 1.3.6.1.4.1.9839.2.1.1.45
        a1-e2 OBJECT-TYPE
                    SYNTAX Integer32 (0..1)
                    UNITS "N/A"
                    MAX-ACCESS read-only
                    STATUS current
                    DESCRIPTION "Probe 2 error"
                    ::= { digitalObjects 45 }

        -- 1.3.6.1.4.1.9839.2.1.1.46
        a1-e3 OBJECT-TYPE
                    SYNTAX Integer32 (0..1)
                    UNITS "N/A"
                    MAX-ACCESS read-only
                    STATUS current
                    DESCRIPTION "Probe 3 error"
                    ::= { digitalObjects 46 }

        -- 1.3.6.1.4.1.9839.2.1.1.47
        a1-ia OBJECT-TYPE
                    SYNTAX Integer32 (0..1)
                    UNITS "N/A"
                    MAX-ACCESS read-only
                    STATUS current
                    DESCRIPTION "Immediate external alarm"
                    ::= { digitalObjects 47 }

        -- 1.3.6.1.4.1.9839.2.1.1.48
        a1-da OBJECT-TYPE
                    SYNTAX Integer32 (0..1)
                    UNITS "N/A"
                    MAX-ACCESS read-only
                    STATUS current
                    DESCRIPTION "Delayed external alarm"
                    ::= { digitalObjects 48 }

        -- 1.3.6.1.4.1.9839.2.1.1.49
        a1-ea OBJECT-TYPE
                    SYNTAX Integer32 (0..1)
                    UNITS "N/A"
                    MAX-ACCESS read-only
                    STATUS current
                    DESCRIPTION "E2P/Clock alarm"
                    ::= { digitalObjects 49 }

        -- 1.3.6.1.4.1.9839.2.1.1.50
        a1-re OBJECT-TYPE
                    SYNTAX Integer32 (0..1)
                    UNITS "N/A"
                    MAX-ACCESS read-only
                    STATUS current
                    DESCRIPTION "Control probe error"
                    ::= { digitalObjects 50 }

        -- 1.3.6.1.4.1.9839.2.1.1.51
        a1-id OBJECT-TYPE
                    SYNTAX Integer32 (0..1)
                    UNITS "N/A"
                    MAX-ACCESS read-only
                    STATUS current
                    DESCRIPTION "Duty setting from external contact"
                    ::= { digitalObjects 51 }

        -- 1.3.6.1.4.1.9839.2.1.1.52
        a2-hi OBJECT-TYPE
                    SYNTAX Integer32 (0..1)
                    UNITS "N/A"
                    MAX-ACCESS read-only
                    STATUS current
                    DESCRIPTION "High temperature alarm"
                    ::= { digitalObjects 52 }

        -- 1.3.6.1.4.1.9839.2.1.1.53
        a2-lo OBJECT-TYPE
                    SYNTAX Integer32 (0..1)
                    UNITS "N/A"
                    MAX-ACCESS read-only
                    STATUS current
                    DESCRIPTION "Low temperature alarm"
                    ::= { digitalObjects 53 }

        -- 1.3.6.1.4.1.9839.2.1.1.54
        a2-ha OBJECT-TYPE
                    SYNTAX Integer32 (0..1)
                    UNITS "N/A"
                    MAX-ACCESS read-only
                    STATUS current
                    DESCRIPTION "HACCP alarm, time exceeded"
                    ::= { digitalObjects 54 }

        -- 1.3.6.1.4.1.9839.2.1.1.55
        a2-hf OBJECT-TYPE
                    SYNTAX Integer32 (0..1)
                    UNITS "N/A"
                    MAX-ACCESS read-only
                    STATUS current
                    DESCRIPTION "HACCP alarm"
                    ::= { digitalObjects 55 }

        -- 1.3.6.1.4.1.9839.2.1.1.56
        a2-ed OBJECT-TYPE
                    SYNTAX Integer32 (0..1)
                    UNITS "N/A"
                    MAX-ACCESS read-only
                    STATUS current
                    DESCRIPTION "Defrost ended by time-out"
                    ::= { digitalObjects 56 }



        -- 1.3.6.1.4.1.9839.2.1.2
        analogObjects OBJECT IDENTIFIER ::= { powersplitMIB 2 }

        -- 1.3.6.1.4.1.9839.2.1.2.1
        probeoffset-3 OBJECT-TYPE
                    SYNTAX Integer32 (-199..199)
                    UNITS "°C/°F x10"
                    MAX-ACCESS read-write
                    STATUS current
                    DESCRIPTION "Probe 3 calibration"
                    DEFVAL { 0 }
                    ::= { analogObjects 1 }

        -- 1.3.6.1.4.1.9839.2.1.2.2
        probeoffset-1 OBJECT-TYPE
                    SYNTAX Integer32 (-199..199)
                    UNITS "°C/°F x10"
                    MAX-ACCESS read-write
                    STATUS current
                    DESCRIPTION "Probe 1 calibration"
                    DEFVAL { 0 }
                    ::= { analogObjects 2 }

        -- 1.3.6.1.4.1.9839.2.1.2.3
        probeoffset-2 OBJECT-TYPE
                    SYNTAX Integer32 (-199..199)
                    UNITS "°C/°F x10"
                    MAX-ACCESS read-write
                    STATUS current
                    DESCRIPTION "Probe 2 calibration"
                    DEFVAL { 0 }
                    ::= { analogObjects 3 }

        -- 1.3.6.1.4.1.9839.2.1.2.4
        fan-alarm-hyst OBJECT-TYPE
                    SYNTAX Integer32 (1..199)
                    UNITS "°C/°F x10"
                    MAX-ACCESS read-write
                    STATUS current
                    DESCRIPTION "Alarm and fan differential"
                    DEFVAL { 2 }
                    ::= { analogObjects 4 }

        -- 1.3.6.1.4.1.9839.2.1.2.5
        alarm-max-delta OBJECT-TYPE
                    SYNTAX Integer32 (0..1990)
                    UNITS "°C/°F x10"
                    MAX-ACCESS read-write
                    STATUS current
                    DESCRIPTION "High temperature alarm delta"
                    DEFVAL { 0 }
                    ::= { analogObjects 5 }

        -- 1.3.6.1.4.1.9839.2.1.2.6
        alarm-min-delta OBJECT-TYPE
                    SYNTAX Integer32 (0..1990)
                    UNITS "°C/°F x10"
                    MAX-ACCESS read-write
                    STATUS current
                    DESCRIPTION "Low temperature alarm delta"
                    DEFVAL { 0 }
                    ::= { analogObjects 6 }

        -- 1.3.6.1.4.1.9839.2.1.2.7
        defrost-end-temp OBJECT-TYPE
                    SYNTAX Integer32 (-500..199)
                    UNITS "°C/°F x10"
                    MAX-ACCESS read-write
                    STATUS current
                    DESCRIPTION "End defrost temperature"
                    DEFVAL { 40 }
                    ::= { analogObjects 7 }

        -- 1.3.6.1.4.1.9839.2.1.2.8
        fan-on-temp OBJECT-TYPE
                    SYNTAX Integer32 (-400..500)
                    UNITS "°C/°F x10"
                    MAX-ACCESS read-write
                    STATUS current
                    DESCRIPTION "Absolute fan start Set Point"
                    DEFVAL { 50 }
                    ::= { analogObjects 8 }

        -- 1.3.6.1.4.1.9839.2.1.2.9
        setpoint-min OBJECT-TYPE
                    SYNTAX Integer32 (-500..32767)
                    UNITS "°C/°F x10"
                    MAX-ACCESS read-write
                    STATUS current
                    DESCRIPTION "Miminum setpoint"
                    DEFVAL { -500 }
                    ::= { analogObjects 9 }

        -- 1.3.6.1.4.1.9839.2.1.2.10
        setpoint-max OBJECT-TYPE
                    SYNTAX Integer32 (-32767..1990)
                    UNITS "°C/°F x10"
                    MAX-ACCESS read-write
                    STATUS current
                    DESCRIPTION "Maximum setpoint"
                    DEFVAL { 900 }
                    ::= { analogObjects 10 }

        -- 1.3.6.1.4.1.9839.2.1.2.11
        setpoint-night OBJECT-TYPE
                    SYNTAX Integer32 (-200..200)
                    UNITS "°C/°F x10"
                    MAX-ACCESS read-write
                    STATUS current
                    DESCRIPTION "Automatic variation of night-time set point"
                    DEFVAL { 30 }
                    ::= { analogObjects 11 }

        -- 1.3.6.1.4.1.9839.2.1.2.12
        reghyst OBJECT-TYPE
                    SYNTAX Integer32 (0..199)
                    UNITS "°C/°F x10"
                    MAX-ACCESS read-write
                    STATUS current
                    DESCRIPTION "Control differential"
                    DEFVAL { 20 }
                    ::= { analogObjects 12 }

        -- 1.3.6.1.4.1.9839.2.1.2.13
        max-store-value OBJECT-TYPE
                    SYNTAX Integer32 (-32767..32767)
                    UNITS "°C/°F x10"
                    MAX-ACCESS read-only
                    STATUS current
                    DESCRIPTION "Maximum temperature measured in interval (rt)"
                    DEFVAL { 0 }
                    ::= { analogObjects 13 }

        -- 1.3.6.1.4.1.9839.2.1.2.14
        min-store-value OBJECT-TYPE
                    SYNTAX Integer32 (-32767..32767)
                    UNITS "°C/°F x10"
                    MAX-ACCESS read-only
                    STATUS current
                    DESCRIPTION "Minimum temperature measured in interval (rt)"
                    DEFVAL { 0 }
                    ::= { analogObjects 14 }

        -- 1.3.6.1.4.1.9839.2.1.2.15
        setpoint OBJECT-TYPE
                    SYNTAX Integer32 (-32767..32767)
                    UNITS "°C/°F x10"
                    MAX-ACCESS read-write
                    STATUS current
                    DESCRIPTION "Temperature setpoint"
                    ::= { analogObjects 15 }

        -- 1.3.6.1.4.1.9839.2.1.2.26
        probe-1 OBJECT-TYPE
                    SYNTAX Integer32 (-32767..32767)
                    UNITS "°C/°F x10"
                    MAX-ACCESS read-only
                    STATUS current
                    DESCRIPTION "Probe 1"
                    ::= { analogObjects 26 }

        -- 1.3.6.1.4.1.9839.2.1.2.27
        probe-2 OBJECT-TYPE
                    SYNTAX Integer32 (-32767..32767)
                    UNITS "°C/°F x10"
                    MAX-ACCESS read-only
                    STATUS current
                    DESCRIPTION "Probe 2"
                    ::= { analogObjects 27 }

        -- 1.3.6.1.4.1.9839.2.1.2.28
        probe-3 OBJECT-TYPE
                    SYNTAX Integer32 (-32767..32767)
                    UNITS "°C/°F x10"
                    MAX-ACCESS read-only
                    STATUS current
                    DESCRIPTION "Probe 3"
                    ::= { analogObjects 28 }

        -- 1.3.6.1.4.1.9839.2.1.2.29
        probe-virtual OBJECT-TYPE
                    SYNTAX Integer32 (-32767..32767)
                    UNITS "°C/°F x10"
                    MAX-ACCESS read-only
                    STATUS current
                    DESCRIPTION "Virtual probe"
                    ::= { analogObjects 29 }

        -- 1.3.6.1.4.1.9839.2.1.2.30
        power-supply-voltage OBJECT-TYPE
                    SYNTAX Integer32 (-32767..32767)
                    UNITS "V x10"
                    MAX-ACCESS read-only
                    STATUS current
                    DESCRIPTION "Power supply voltage"
                    ::= { analogObjects 30 }



        -- 1.3.6.1.4.1.9839.2.1.3
        integerObjects OBJECT IDENTIFIER ::= { powersplitMIB 3 }

        -- 1.3.6.1.4.1.9839.2.1.3.1
        probe-stability OBJECT-TYPE
                    SYNTAX Integer32 (1..15)
                    UNITS "N/A"
                    MAX-ACCESS read-write
                    STATUS current
                    DESCRIPTION "Measurement stability"
                    DEFVAL { 4 }
                    ::= { integerObjects 1 }

        -- 1.3.6.1.4.1.9839.2.1.3.2
        virt-probe OBJECT-TYPE
                    SYNTAX Integer32 (0..100)
                    UNITS "N/A"
                    MAX-ACCESS read-write
                    STATUS current
                    DESCRIPTION "Virtual probe settings"
                    DEFVAL { 0 }
                    ::= { integerObjects 2 }

        -- 1.3.6.1.4.1.9839.2.1.3.3
        showprobe OBJECT-TYPE
                    SYNTAX Integer32 (0..4)
                    UNITS "N/A"
                    MAX-ACCESS read-write
                    STATUS current
                    DESCRIPTION "Display configuration"
                    DEFVAL { 0 }
                    ::= { integerObjects 3 }

        -- 1.3.6.1.4.1.9839.2.1.3.4
        showprobe-t OBJECT-TYPE
                    SYNTAX Integer32 (0..4)
                    UNITS "N/A"
                    MAX-ACCESS read-write
                    STATUS current
                    DESCRIPTION "Terminal configuration"
                    DEFVAL { 4 }
                    ::= { integerObjects 4 }

        -- 1.3.6.1.4.1.9839.2.1.3.5
        defrostprobepresence OBJECT-TYPE
                    SYNTAX Integer32 (0..3)
                    UNITS "N/A"
                    MAX-ACCESS read-write
                    STATUS current
                    DESCRIPTION "Existence of probes S2 and S3"
                    DEFVAL { 2 }
                    ::= { integerObjects 5 }

        -- 1.3.6.1.4.1.9839.2.1.3.6
        dig-in-cfg-1 OBJECT-TYPE
                    SYNTAX Integer32 (0..7)
                    UNITS "N/A"
                    MAX-ACCESS read-write
                    STATUS current
                    DESCRIPTION "Digital input 1 configuration"
                    DEFVAL { 0 }
                    ::= { integerObjects 6 }

        -- 1.3.6.1.4.1.9839.2.1.3.7
        dig-in-cfg-2 OBJECT-TYPE
                    SYNTAX Integer32 (0..7)
                    UNITS "N/A"
                    MAX-ACCESS read-write
                    STATUS current
                    DESCRIPTION "Digital input 2 configuration"
                    DEFVAL { 0 }
                    ::= { integerObjects 7 }

        -- 1.3.6.1.4.1.9839.2.1.3.8
        alarm-input-delay OBJECT-TYPE
                    SYNTAX Integer32 (0..199)
                    UNITS "min"
                    MAX-ACCESS read-write
                    STATUS current
                    DESCRIPTION "Delay time for the delayed alarm input"
                    DEFVAL { 0 }
                    ::= { integerObjects 8 }

        -- 1.3.6.1.4.1.9839.2.1.3.9
        alarm-delay OBJECT-TYPE
                    SYNTAX Integer32 (0..199)
                    UNITS "min"
                    MAX-ACCESS read-write
                    STATUS current
                    DESCRIPTION "Temperature alarm delay"
                    DEFVAL { 120 }
                    ::= { integerObjects 9 }

        -- 1.3.6.1.4.1.9839.2.1.3.10
        comp-startup-delay OBJECT-TYPE
                    SYNTAX Integer32 (0..15)
                    UNITS "min."
                    MAX-ACCESS read-write
                    STATUS current
                    DESCRIPTION "Compressor and fan start delay at startup"
                    DEFVAL { 0 }
                    ::= { integerObjects 10 }

        -- 1.3.6.1.4.1.9839.2.1.3.11
        comp-s2s-delay OBJECT-TYPE
                    SYNTAX Integer32 (0..15)
                    UNITS "min."
                    MAX-ACCESS read-write
                    STATUS current
                    DESCRIPTION "Minimum time between 2 start of compressor"
                    DEFVAL { 0 }
                    ::= { integerObjects 11 }

        -- 1.3.6.1.4.1.9839.2.1.3.12
        comp-min-off-time OBJECT-TYPE
                    SYNTAX Integer32 (0..15)
                    UNITS "min."
                    MAX-ACCESS read-write
                    STATUS current
                    DESCRIPTION "Mimimum compressor off time"
                    DEFVAL { 0 }
                    ::= { integerObjects 12 }

        -- 1.3.6.1.4.1.9839.2.1.3.13
        comp-min-on-time OBJECT-TYPE
                    SYNTAX Integer32 (0..15)
                    UNITS "min."
                    MAX-ACCESS read-write
                    STATUS current
                    DESCRIPTION "Minimum compressor on time"
                    DEFVAL { 0 }
                    ::= { integerObjects 13 }

        -- 1.3.6.1.4.1.9839.2.1.3.14
        rele-safety-cycle OBJECT-TYPE
                    SYNTAX Integer32 (0..100)
                    UNITS "min."
                    MAX-ACCESS read-write
                    STATUS current
                    DESCRIPTION "Duty setting or safety function"
                    DEFVAL { 0 }
                    ::= { integerObjects 14 }

        -- 1.3.6.1.4.1.9839.2.1.3.15
        cc-alarm-delay OBJECT-TYPE
                    SYNTAX Integer32 (0..15)
                    UNITS "Hours"
                    MAX-ACCESS read-write
                    STATUS current
                    DESCRIPTION "Alarm bypass after continuous cycle"
                    DEFVAL { 2 }
                    ::= { integerObjects 15 }

        -- 1.3.6.1.4.1.9839.2.1.3.16
        comp-cc OBJECT-TYPE
                    SYNTAX Integer32 (0..15)
                    UNITS "Hours"
                    MAX-ACCESS read-write
                    STATUS current
                    DESCRIPTION "Continuous cycle duration"
                    DEFVAL { 4 }
                    ::= { integerObjects 16 }

        -- 1.3.6.1.4.1.9839.2.1.3.17
        defrost-type OBJECT-TYPE
                    SYNTAX Integer32 (0..3)
                    UNITS "N/A"
                    MAX-ACCESS read-write
                    STATUS current
                    DESCRIPTION "Type of defrost"
                    DEFVAL { 0 }
                    ::= { integerObjects 17 }

        -- 1.3.6.1.4.1.9839.2.1.3.18
        defrost-delay OBJECT-TYPE
                    SYNTAX Integer32 (0..199)
                    UNITS "min"
                    MAX-ACCESS read-write
                    STATUS current
                    DESCRIPTION "Defrost delay at startup or dig. input"
                    DEFVAL { 0 }
                    ::= { integerObjects 18 }

        -- 1.3.6.1.4.1.9839.2.1.3.19
        alarm-delay-df-door OBJECT-TYPE
                    SYNTAX Integer32 (0..15)
                    UNITS "ore"
                    MAX-ACCESS read-write
                    STATUS current
                    DESCRIPTION "High temperature alarm bypass time after defrost"
                    DEFVAL { 1 }
                    ::= { integerObjects 19 }

        -- 1.3.6.1.4.1.9839.2.1.3.20
        dripping-interval OBJECT-TYPE
                    SYNTAX Integer32 (0..15)
                    UNITS "min"
                    MAX-ACCESS read-write
                    STATUS current
                    DESCRIPTION "Dripping time after defrosting"
                    DEFVAL { 2 }
                    ::= { integerObjects 20 }

        -- 1.3.6.1.4.1.9839.2.1.3.21
        defrost-interval OBJECT-TYPE
                    SYNTAX Integer32 (0..199)
                    UNITS "ore"
                    MAX-ACCESS read-write
                    STATUS current
                    DESCRIPTION "Interval between 2 defrosts"
                    DEFVAL { 8 }
                    ::= { integerObjects 21 }

        -- 1.3.6.1.4.1.9839.2.1.3.22
        defrost-max-time OBJECT-TYPE
                    SYNTAX Integer32 (1..199)
                    UNITS "min"
                    MAX-ACCESS read-write
                    STATUS current
                    DESCRIPTION "Maximum defrost duration"
                    DEFVAL { 30 }
                    ::= { integerObjects 22 }

        -- 1.3.6.1.4.1.9839.2.1.3.23
        fan-drip-interval OBJECT-TYPE
                    SYNTAX Integer32 (0..15)
                    UNITS "min"
                    MAX-ACCESS read-write
                    STATUS current
                    DESCRIPTION "Fans off during post-dripping"
                    DEFVAL { 1 }
                    ::= { integerObjects 23 }

        -- 1.3.6.1.4.1.9839.2.1.3.24
        aux1-cfg OBJECT-TYPE
                    SYNTAX Integer32 (0..7)
                    UNITS "N/A"
                    MAX-ACCESS read-write
                    STATUS current
                    DESCRIPTION "Set operation of AUX1 relay"
                    DEFVAL { 5 }
                    ::= { integerObjects 24 }

        -- 1.3.6.1.4.1.9839.2.1.3.25
        aux2-cfg OBJECT-TYPE
                    SYNTAX Integer32 (0..7)
                    UNITS "N/A"
                    MAX-ACCESS read-write
                    STATUS current
                    DESCRIPTION "Set operation of AUX2 relay"
                    DEFVAL { 6 }
                    ::= { integerObjects 25 }

        -- 1.3.6.1.4.1.9839.2.1.3.26
        light-sens-1 OBJECT-TYPE
                    SYNTAX Integer32 (0..2)
                    UNITS "N/A"
                    MAX-ACCESS read-write
                    STATUS current
                    DESCRIPTION "Photocell sensitivity"
                    DEFVAL { 0 }
                    ::= { integerObjects 26 }

        -- 1.3.6.1.4.1.9839.2.1.3.27
        light-timer OBJECT-TYPE
                    SYNTAX Integer32 (1..15)
                    UNITS "min"
                    MAX-ACCESS read-write
                    STATUS current
                    DESCRIPTION "Light on time from photocell input"
                    DEFVAL { 10 }
                    ::= { integerObjects 27 }

        -- 1.3.6.1.4.1.9839.2.1.3.28
        minmax-acq-time OBJECT-TYPE
                    SYNTAX Integer32 (0..199)
                    UNITS "ore"
                    MAX-ACCESS read-only
                    STATUS current
                    DESCRIPTION "Min and max temperature measurement interval"
                    DEFVAL { 0 }
                    ::= { integerObjects 28 }

        -- 1.3.6.1.4.1.9839.2.1.3.29
        haccp-ha-day OBJECT-TYPE
                    SYNTAX Integer32 (1..7)
                    UNITS "N/A"
                    MAX-ACCESS read-only
                    STATUS current
                    DESCRIPTION "Weekday on which the HA event occurred"
                    DEFVAL { 0 }
                    ::= { integerObjects 29 }

        -- 1.3.6.1.4.1.9839.2.1.3.30
        haccp-ha-hour OBJECT-TYPE
                    SYNTAX Integer32 (0..23)
                    UNITS "ore"
                    MAX-ACCESS read-only
                    STATUS current
                    DESCRIPTION "Hours at which the HA event occurred"
                    DEFVAL { 0 }
                    ::= { integerObjects 30 }

        -- 1.3.6.1.4.1.9839.2.1.3.31
        haccp-ha-min OBJECT-TYPE
                    SYNTAX Integer32 (0..59)
                    UNITS "min."
                    MAX-ACCESS read-only
                    STATUS current
                    DESCRIPTION "Minutes at which the HA event occurred"
                    DEFVAL { 0 }
                    ::= { integerObjects 31 }

        -- 1.3.6.1.4.1.9839.2.1.3.32
        haccp-hf-day OBJECT-TYPE
                    SYNTAX Integer32 (1..7)
                    UNITS "N/A"
                    MAX-ACCESS read-only
                    STATUS current
                    DESCRIPTION "Weekday on which the HF event occurred"
                    DEFVAL { 0 }
                    ::= { integerObjects 32 }

        -- 1.3.6.1.4.1.9839.2.1.3.33
        haccp-hf-hour OBJECT-TYPE
                    SYNTAX Integer32 (0..23)
                    UNITS "ore"
                    MAX-ACCESS read-only
                    STATUS current
                    DESCRIPTION "Hours at which the HF event occurred"
                    DEFVAL { 0 }
                    ::= { integerObjects 33 }

        -- 1.3.6.1.4.1.9839.2.1.3.34
        haccp-hf-min OBJECT-TYPE
                    SYNTAX Integer32 (0..59)
                    UNITS "min."
                    MAX-ACCESS read-only
                    STATUS current
                    DESCRIPTION "Minutes at which the HF event occurred"
                    DEFVAL { 0 }
                    ::= { integerObjects 34 }

        -- 1.3.6.1.4.1.9839.2.1.3.35
        haccp-alarm-delay OBJECT-TYPE
                    SYNTAX Integer32 (0..199)
                    UNITS "min."
                    MAX-ACCESS read-write
                    STATUS current
                    DESCRIPTION "HACCP alarm delay"
                    DEFVAL { 0 }
                    ::= { integerObjects 35 }

        -- 1.3.6.1.4.1.9839.2.1.3.36
        defrost-t1-dd OBJECT-TYPE
                    SYNTAX Integer32 (0..23)
                    UNITS "ore"
                    MAX-ACCESS read-write
                    STATUS current
                    DESCRIPTION "Defrost event 1st day"
                    ::= { integerObjects 36 }

        -- 1.3.6.1.4.1.9839.2.1.3.37
        defrost-t1-hh OBJECT-TYPE
                    SYNTAX Integer32 (-32767..32767)
                    UNITS "N/A"
                    MAX-ACCESS read-only
                    STATUS current
                    DESCRIPTION "Defrost event 1 hour"
                    ::= { integerObjects 37 }

        -- 1.3.6.1.4.1.9839.2.1.3.38
        defrost-t1-mm OBJECT-TYPE
                    SYNTAX Integer32 (0..59)
                    UNITS "min."
                    MAX-ACCESS read-write
                    STATUS current
                    DESCRIPTION "Defrost event 1 min"
                    ::= { integerObjects 38 }

        -- 1.3.6.1.4.1.9839.2.1.3.39
        defrost-t2-dd OBJECT-TYPE
                    SYNTAX Integer32 (0..10)
                    UNITS "gg"
                    MAX-ACCESS read-write
                    STATUS current
                    DESCRIPTION "Defrost event 2nd day"
                    ::= { integerObjects 39 }

        -- 1.3.6.1.4.1.9839.2.1.3.40
        defrost-t2-hh OBJECT-TYPE
                    SYNTAX Integer32 (0..23)
                    UNITS "ore"
                    MAX-ACCESS read-write
                    STATUS current
                    DESCRIPTION "Defrost event 2 hour"
                    ::= { integerObjects 40 }

        -- 1.3.6.1.4.1.9839.2.1.3.41
        defrost-t2-mm OBJECT-TYPE
                    SYNTAX Integer32 (0..59)
                    UNITS "min"
                    MAX-ACCESS read-write
                    STATUS current
                    DESCRIPTION "Defrost event 2nd min"
                    ::= { integerObjects 41 }

        -- 1.3.6.1.4.1.9839.2.1.3.42
        defrost-t3-dd OBJECT-TYPE
                    SYNTAX Integer32 (0..10)
                    UNITS "gg"
                    MAX-ACCESS read-write
                    STATUS current
                    DESCRIPTION "Defrost event 3 day"
                    ::= { integerObjects 42 }

        -- 1.3.6.1.4.1.9839.2.1.3.43
        defrost-t3-hh OBJECT-TYPE
                    SYNTAX Integer32 (0..23)
                    UNITS "ore"
                    MAX-ACCESS read-write
                    STATUS current
                    DESCRIPTION "Defrost event 3 hour"
                    ::= { integerObjects 43 }

        -- 1.3.6.1.4.1.9839.2.1.3.44
        defrost-t3-mm OBJECT-TYPE
                    SYNTAX Integer32 (0..59)
                    UNITS "min"
                    MAX-ACCESS read-write
                    STATUS current
                    DESCRIPTION "Defrost event 3 min"
                    ::= { integerObjects 44 }

        -- 1.3.6.1.4.1.9839.2.1.3.45
        defrost-t4-dd OBJECT-TYPE
                    SYNTAX Integer32 (0..10)
                    UNITS "gg"
                    MAX-ACCESS read-write
                    STATUS current
                    DESCRIPTION "Defrost event 4th day"
                    ::= { integerObjects 45 }

        -- 1.3.6.1.4.1.9839.2.1.3.46
        defrost-t4-hh OBJECT-TYPE
                    SYNTAX Integer32 (0..23)
                    UNITS "ore"
                    MAX-ACCESS read-write
                    STATUS current
                    DESCRIPTION "Defrost event 4 hour"
                    ::= { integerObjects 46 }

        -- 1.3.6.1.4.1.9839.2.1.3.47
        defrost-t4-mm OBJECT-TYPE
                    SYNTAX Integer32 (0..59)
                    UNITS "min"
                    MAX-ACCESS read-write
                    STATUS current
                    DESCRIPTION "Defrost event 4th min"
                    ::= { integerObjects 47 }

        -- 1.3.6.1.4.1.9839.2.1.3.48
        defrost-t5-dd OBJECT-TYPE
                    SYNTAX Integer32 (0..10)
                    UNITS "gg"
                    MAX-ACCESS read-write
                    STATUS current
                    DESCRIPTION "Defrost event 5 day"
                    ::= { integerObjects 48 }

        -- 1.3.6.1.4.1.9839.2.1.3.49
        defrost-t5-hh OBJECT-TYPE
                    SYNTAX Integer32 (0..23)
                    UNITS "ore"
                    MAX-ACCESS read-write
                    STATUS current
                    DESCRIPTION "Defrost event 5 hour"
                    ::= { integerObjects 49 }

        -- 1.3.6.1.4.1.9839.2.1.3.50
        defrost-t5-mm OBJECT-TYPE
                    SYNTAX Integer32 (0..59)
                    UNITS "min"
                    MAX-ACCESS read-write
                    STATUS current
                    DESCRIPTION "Defrost event 5 min"
                    ::= { integerObjects 50 }

        -- 1.3.6.1.4.1.9839.2.1.3.51
        defrost-t6-dd OBJECT-TYPE
                    SYNTAX Integer32 (0..10)
                    UNITS "gg"
                    MAX-ACCESS read-write
                    STATUS current
                    DESCRIPTION "Defrost event 6th day"
                    ::= { integerObjects 51 }

        -- 1.3.6.1.4.1.9839.2.1.3.52
        defrost-t6-hh OBJECT-TYPE
                    SYNTAX Integer32 (0..23)
                    UNITS "ore"
                    MAX-ACCESS read-write
                    STATUS current
                    DESCRIPTION "Defrost event 6 hour"
                    ::= { integerObjects 52 }

        -- 1.3.6.1.4.1.9839.2.1.3.53
        defrost-t6-mm OBJECT-TYPE
                    SYNTAX Integer32 (0..59)
                    UNITS "min"
                    MAX-ACCESS read-write
                    STATUS current
                    DESCRIPTION "Defrost event 6th min"
                    ::= { integerObjects 53 }

        -- 1.3.6.1.4.1.9839.2.1.3.54
        tm OBJECT-TYPE
                    SYNTAX Integer32 (0..59)
                    UNITS "min"
                    MAX-ACCESS read-only
                    STATUS current
                    DESCRIPTION "Current minutes"
                    ::= { integerObjects 54 }

        -- 1.3.6.1.4.1.9839.2.1.3.55
        th OBJECT-TYPE
                    SYNTAX Integer32 (0..23)
                    UNITS "ore"
                    MAX-ACCESS read-only
                    STATUS current
                    DESCRIPTION "Current hours"
                    ::= { integerObjects 55 }

        -- 1.3.6.1.4.1.9839.2.1.3.56
        td OBJECT-TYPE
                    SYNTAX Integer32 (1..7)
                    UNITS "N/A"
                    MAX-ACCESS read-only
                    STATUS current
                    DESCRIPTION "Current day of the week"
                    ::= { integerObjects 56 }


	
	END

--
-- CAREL-powersplit.MIB
--
