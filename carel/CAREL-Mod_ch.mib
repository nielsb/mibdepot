--
-- CAREL-mod-ch.MIB
-- MIB generated by CAREL
-- Friday, 14 March 2003
--

    CAREL-mod-ch-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        mod-chMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the mod-ch device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- mod-chMIB OBJECT IDENTIFIER ::= { instruments 1 }
		
        -- 1.3.6.1.4.1.9839.2.1.1
        digitalObjects OBJECT IDENTIFIER ::= { mod-chMIB 1 }

        -- 1.3.6.1.4.1.9839.2.1.1.1
        syson-s OBJECT-TYPE
                    SYNTAX Integer32 (0..1)
                    UNITS "N/A"
                    MAX-ACCESS read-only
                    STATUS current
                    DESCRIPTION "Unit On / Off.On the master starts all connected units."
                    ::= { digitalObjects 1 }

        -- 1.3.6.1.4.1.9839.2.1.1.10
        dout-1 OBJECT-TYPE
                    SYNTAX Integer32 (0..1)
                    UNITS "N/A"
                    MAX-ACCESS read-only
                    STATUS current
                    DESCRIPTION "Digital output n.1"
                    ::= { digitalObjects 10 }

        -- 1.3.6.1.4.1.9839.2.1.1.11
        dout-2 OBJECT-TYPE
                    SYNTAX Integer32 (0..1)
                    UNITS "N/A"
                    MAX-ACCESS read-only
                    STATUS current
                    DESCRIPTION "Digital output n.2"
                    ::= { digitalObjects 11 }

        -- 1.3.6.1.4.1.9839.2.1.1.12
        dout-3 OBJECT-TYPE
                    SYNTAX Integer32 (0..1)
                    UNITS "N/A"
                    MAX-ACCESS read-only
                    STATUS current
                    DESCRIPTION "Digital output n.3"
                    ::= { digitalObjects 12 }

        -- 1.3.6.1.4.1.9839.2.1.1.13
        dout-4 OBJECT-TYPE
                    SYNTAX Integer32 (0..1)
                    UNITS "N/A"
                    MAX-ACCESS read-only
                    STATUS current
                    DESCRIPTION "Digital output n.4"
                    ::= { digitalObjects 13 }

        -- 1.3.6.1.4.1.9839.2.1.1.14
        dout-5 OBJECT-TYPE
                    SYNTAX Integer32 (0..1)
                    UNITS "N/A"
                    MAX-ACCESS read-only
                    STATUS current
                    DESCRIPTION "Digital output n.5"
                    ::= { digitalObjects 14 }

        -- 1.3.6.1.4.1.9839.2.1.1.15
        dout-6 OBJECT-TYPE
                    SYNTAX Integer32 (0..1)
                    UNITS "N/A"
                    MAX-ACCESS read-only
                    STATUS current
                    DESCRIPTION "Digital output n.6"
                    ::= { digitalObjects 15 }

        -- 1.3.6.1.4.1.9839.2.1.1.16
        dout-7 OBJECT-TYPE
                    SYNTAX Integer32 (0..1)
                    UNITS "N/A"
                    MAX-ACCESS read-only
                    STATUS current
                    DESCRIPTION "Digital output n.7"
                    ::= { digitalObjects 16 }

        -- 1.3.6.1.4.1.9839.2.1.1.17
        dout-8 OBJECT-TYPE
                    SYNTAX Integer32 (0..1)
                    UNITS "N/A"
                    MAX-ACCESS read-only
                    STATUS current
                    DESCRIPTION "Digital output n.8"
                    ::= { digitalObjects 17 }

        -- 1.3.6.1.4.1.9839.2.1.1.18
        dout-9 OBJECT-TYPE
                    SYNTAX Integer32 (0..1)
                    UNITS "N/A"
                    MAX-ACCESS read-only
                    STATUS current
                    DESCRIPTION "Digital output n.9"
                    ::= { digitalObjects 18 }

        -- 1.3.6.1.4.1.9839.2.1.1.19
        dout-10 OBJECT-TYPE
                    SYNTAX Integer32 (0..1)
                    UNITS "N/A"
                    MAX-ACCESS read-only
                    STATUS current
                    DESCRIPTION "Digital output n.10"
                    ::= { digitalObjects 19 }

        -- 1.3.6.1.4.1.9839.2.1.1.20
        dout-11 OBJECT-TYPE
                    SYNTAX Integer32 (0..1)
                    UNITS "N/A"
                    MAX-ACCESS read-only
                    STATUS current
                    DESCRIPTION "Digital output n.11"
                    ::= { digitalObjects 20 }

        -- 1.3.6.1.4.1.9839.2.1.1.21
        dout-12 OBJECT-TYPE
                    SYNTAX Integer32 (0..1)
                    UNITS "N/A"
                    MAX-ACCESS read-only
                    STATUS current
                    DESCRIPTION "Digital output n.12"
                    ::= { digitalObjects 21 }

        -- 1.3.6.1.4.1.9839.2.1.1.22
        dout-13 OBJECT-TYPE
                    SYNTAX Integer32 (0..1)
                    UNITS "N/A"
                    MAX-ACCESS read-only
                    STATUS current
                    DESCRIPTION "Digital output n.13"
                    ::= { digitalObjects 22 }

        -- 1.3.6.1.4.1.9839.2.1.1.28
        master OBJECT-TYPE
                    SYNTAX Integer32 (0..1)
                    UNITS "N/A"
                    MAX-ACCESS read-only
                    STATUS current
                    DESCRIPTION "Indicates if the unit is the MASTER"
                    ::= { digitalObjects 28 }

        -- 1.3.6.1.4.1.9839.2.1.1.29
        slave OBJECT-TYPE
                    SYNTAX Integer32 (0..1)
                    UNITS "N/A"
                    MAX-ACCESS read-only
                    STATUS current
                    DESCRIPTION "Indicates if the unit is a SLAVE"
                    ::= { digitalObjects 29 }

        -- 1.3.6.1.4.1.9839.2.1.1.30
        en-b1 OBJECT-TYPE
                    SYNTAX Integer32 (0..1)
                    UNITS "flag"
                    MAX-ACCESS read-write
                    STATUS current
                    DESCRIPTION "Enable probe B1"
                    DEFVAL { 1 }
                    ::= { digitalObjects 30 }

        -- 1.3.6.1.4.1.9839.2.1.1.31
        en-b2 OBJECT-TYPE
                    SYNTAX Integer32 (0..1)
                    UNITS "flag"
                    MAX-ACCESS read-write
                    STATUS current
                    DESCRIPTION "Enable probe B2"
                    DEFVAL { 1 }
                    ::= { digitalObjects 31 }

        -- 1.3.6.1.4.1.9839.2.1.1.32
        en-b3 OBJECT-TYPE
                    SYNTAX Integer32 (0..1)
                    UNITS "flag"
                    MAX-ACCESS read-write
                    STATUS current
                    DESCRIPTION "Enable probe B3"
                    DEFVAL { 1 }
                    ::= { digitalObjects 32 }

        -- 1.3.6.1.4.1.9839.2.1.1.33
        en-b4 OBJECT-TYPE
                    SYNTAX Integer32 (0..1)
                    UNITS "flag"
                    MAX-ACCESS read-write
                    STATUS current
                    DESCRIPTION "Enable probe B4"
                    DEFVAL { 1 }
                    ::= { digitalObjects 33 }

        -- 1.3.6.1.4.1.9839.2.1.1.34
        en-b5 OBJECT-TYPE
                    SYNTAX Integer32 (0..1)
                    UNITS "flag"
                    MAX-ACCESS read-write
                    STATUS current
                    DESCRIPTION "Enable probe B5"
                    DEFVAL { 1 }
                    ::= { digitalObjects 34 }

        -- 1.3.6.1.4.1.9839.2.1.1.35
        en-b6 OBJECT-TYPE
                    SYNTAX Integer32 (0..1)
                    UNITS "flag"
                    MAX-ACCESS read-write
                    STATUS current
                    DESCRIPTION "Enable probe B6"
                    DEFVAL { 1 }
                    ::= { digitalObjects 35 }

        -- 1.3.6.1.4.1.9839.2.1.1.36
        en-b7 OBJECT-TYPE
                    SYNTAX Integer32 (0..1)
                    UNITS "flag"
                    MAX-ACCESS read-write
                    STATUS current
                    DESCRIPTION "Enable probe B7"
                    DEFVAL { 1 }
                    ::= { digitalObjects 36 }

        -- 1.3.6.1.4.1.9839.2.1.1.37
        en-b8 OBJECT-TYPE
                    SYNTAX Integer32 (0..1)
                    UNITS "flag"
                    MAX-ACCESS read-write
                    STATUS current
                    DESCRIPTION "Enable probe B8"
                    DEFVAL { 1 }
                    ::= { digitalObjects 37 }

        -- 1.3.6.1.4.1.9839.2.1.1.40
        main-pump OBJECT-TYPE
                    SYNTAX Integer32 (0..1)
                    UNITS "N/A"
                    MAX-ACCESS read-only
                    STATUS current
                    DESCRIPTION "Main pump (or main fan)"
                    ::= { digitalObjects 40 }

        -- 1.3.6.1.4.1.9839.2.1.1.41
        cond-pump OBJECT-TYPE
                    SYNTAX Integer32 (0..1)
                    UNITS "N/A"
                    MAX-ACCESS read-only
                    STATUS current
                    DESCRIPTION "Condenser pump"
                    ::= { digitalObjects 41 }

        -- 1.3.6.1.4.1.9839.2.1.1.42
        superv-onoff OBJECT-TYPE
                    SYNTAX Integer32 (0..1)
                    UNITS "N/A"
                    MAX-ACCESS read-write
                    STATUS current
                    DESCRIPTION "On / Off from supervisor"
                    DEFVAL { 1 }
                    ::= { digitalObjects 42 }

        -- 1.3.6.1.4.1.9839.2.1.1.44
        sum-win-sup OBJECT-TYPE
                    SYNTAX Integer32 (0..1)
                    UNITS "N/A"
                    MAX-ACCESS read-write
                    STATUS current
                    DESCRIPTION "Select Chiller / HP mode for supervsor"
                    ::= { digitalObjects 44 }

        -- 1.3.6.1.4.1.9839.2.1.1.46
        en-freecooling OBJECT-TYPE
                    SYNTAX Integer32 (0..1)
                    UNITS "N/A"
                    MAX-ACCESS read-only
                    STATUS current
                    DESCRIPTION "Enabed freecooling based on configuration"
                    ::= { digitalObjects 46 }

        -- 1.3.6.1.4.1.9839.2.1.1.47
        en-aa-unit OBJECT-TYPE
                    SYNTAX Integer32 (0..1)
                    UNITS "N/A"
                    MAX-ACCESS read-only
                    STATUS current
                    DESCRIPTION "AIR/AIR unit selected"
                    ::= { digitalObjects 47 }

        -- 1.3.6.1.4.1.9839.2.1.1.48
        en-ww-unit OBJECT-TYPE
                    SYNTAX Integer32 (0..1)
                    UNITS "N/A"
                    MAX-ACCESS read-only
                    STATUS current
                    DESCRIPTION "WATER/WATER unit selected: enable condenser pump"
                    ::= { digitalObjects 48 }

        -- 1.3.6.1.4.1.9839.2.1.1.49
        sum-win-sel OBJECT-TYPE
                    SYNTAX Integer32 (0..1)
                    UNITS "N/A"
                    MAX-ACCESS read-only
                    STATUS current
                    DESCRIPTION "Digital input for selecting chiller / HP mode"
                    DEFVAL { 1 }
                    ::= { digitalObjects 49 }

        -- 1.3.6.1.4.1.9839.2.1.1.50
        en-sum-win OBJECT-TYPE
                    SYNTAX Integer32 (0..1)
                    UNITS "N/A"
                    MAX-ACCESS read-only
                    STATUS current
                    DESCRIPTION "Enable digital input for selecting chiller / HP mode"
                    ::= { digitalObjects 50 }

        -- 1.3.6.1.4.1.9839.2.1.1.51
        cooling-heating OBJECT-TYPE
                    SYNTAX Integer32 (0..1)
                    UNITS "N/A"
                    MAX-ACCESS read-only
                    STATUS current
                    DESCRIPTION "Operating mode"
                    ::= { digitalObjects 51 }

        -- 1.3.6.1.4.1.9839.2.1.1.53
        cond-config OBJECT-TYPE
                    SYNTAX Integer32 (0..1)
                    UNITS "N/A"
                    MAX-ACCESS read-write
                    STATUS current
                    DESCRIPTION "Select type of condenser"
                    ::= { digitalObjects 53 }

        -- 1.3.6.1.4.1.9839.2.1.1.56
        inverter-steps OBJECT-TYPE
                    SYNTAX Integer32 (0..1)
                    UNITS "N/A"
                    MAX-ACCESS read-write
                    STATUS current
                    DESCRIPTION "Select operation, inverter or stepped"
                    ::= { digitalObjects 56 }

        -- 1.3.6.1.4.1.9839.2.1.1.57
        inverter OBJECT-TYPE
                    SYNTAX Integer32 (0..1)
                    UNITS "N/A"
                    MAX-ACCESS read-only
                    STATUS current
                    DESCRIPTION "Operating mode selected"
                    ::= { digitalObjects 57 }

        -- 1.3.6.1.4.1.9839.2.1.1.58
        fc-valve-type OBJECT-TYPE
                    SYNTAX Integer32 (0..1)
                    UNITS "N/A"
                    MAX-ACCESS read-write
                    STATUS current
                    DESCRIPTION "Select type of freecooling valve: On / Off"
                    ::= { digitalObjects 58 }

        -- 1.3.6.1.4.1.9839.2.1.1.59
        not-fc-vlv-type OBJECT-TYPE
                    SYNTAX Integer32 (0..1)
                    UNITS "N/A"
                    MAX-ACCESS read-only
                    STATUS current
                    DESCRIPTION "Select type of freecooling valve"
                    ::= { digitalObjects 59 }

        -- 1.3.6.1.4.1.9839.2.1.1.60
        unloads-logic OBJECT-TYPE
                    SYNTAX Integer32 (0..1)
                    UNITS "N/A"
                    MAX-ACCESS read-write
                    STATUS current
                    DESCRIPTION "Select capacity control logic"
                    ::= { digitalObjects 60 }

        -- 1.3.6.1.4.1.9839.2.1.1.61
        valve4way-logic OBJECT-TYPE
                    SYNTAX Integer32 (0..1)
                    UNITS "N/A"
                    MAX-ACCESS read-write
                    STATUS current
                    DESCRIPTION "Select 4-way valve logic"
                    ::= { digitalObjects 61 }

        -- 1.3.6.1.4.1.9839.2.1.1.70
        glb-al OBJECT-TYPE
                    SYNTAX Integer32 (0..1)
                    UNITS "N/A"
                    MAX-ACCESS read-only
                    STATUS current
                    DESCRIPTION "General alarm"
                    ::= { digitalObjects 70 }

        -- 1.3.6.1.4.1.9839.2.1.1.71
        man-freeze OBJECT-TYPE
                    SYNTAX Integer32 (0..1)
                    UNITS "N/A"
                    MAX-ACCESS read-only
                    STATUS current
                    DESCRIPTION "Antifreeze alarm"
                    DEFVAL { 3 }
                    ::= { digitalObjects 71 }

        -- 1.3.6.1.4.1.9839.2.1.1.72
        mal-ov1 OBJECT-TYPE
                    SYNTAX Integer32 (0..1)
                    UNITS "N/A"
                    MAX-ACCESS read-only
                    STATUS current
                    DESCRIPTION "Compressor 1 overload"
                    ::= { digitalObjects 72 }

        -- 1.3.6.1.4.1.9839.2.1.1.73
        mal-ov2 OBJECT-TYPE
                    SYNTAX Integer32 (0..1)
                    UNITS "N/A"
                    MAX-ACCESS read-only
                    STATUS current
                    DESCRIPTION "Compressor 2 overload"
                    ::= { digitalObjects 73 }

        -- 1.3.6.1.4.1.9839.2.1.1.74
        mal-ov3 OBJECT-TYPE
                    SYNTAX Integer32 (0..1)
                    UNITS "N/A"
                    MAX-ACCESS read-only
                    STATUS current
                    DESCRIPTION "Compressor 3 overload"
                    ::= { digitalObjects 74 }

        -- 1.3.6.1.4.1.9839.2.1.1.75
        mal-ov4 OBJECT-TYPE
                    SYNTAX Integer32 (0..1)
                    UNITS "N/A"
                    MAX-ACCESS read-only
                    STATUS current
                    DESCRIPTION "Compressor 4 overload"
                    ::= { digitalObjects 75 }

        -- 1.3.6.1.4.1.9839.2.1.1.76
        mal-cflow OBJECT-TYPE
                    SYNTAX Integer32 (0..1)
                    UNITS "N/A"
                    MAX-ACCESS read-only
                    STATUS current
                    DESCRIPTION "Condensator flow alarm"
                    ::= { digitalObjects 76 }

        -- 1.3.6.1.4.1.9839.2.1.1.77
        mal-eflow OBJECT-TYPE
                    SYNTAX Integer32 (0..1)
                    UNITS "N/A"
                    MAX-ACCESS read-only
                    STATUS current
                    DESCRIPTION "Evaporator flow alarm"
                    ::= { digitalObjects 77 }

        -- 1.3.6.1.4.1.9839.2.1.1.78
        mal-hp1 OBJECT-TYPE
                    SYNTAX Integer32 (0..1)
                    UNITS "N/A"
                    MAX-ACCESS read-only
                    STATUS current
                    DESCRIPTION "Circuit 1 high pressure alarm (pressurestat)"
                    ::= { digitalObjects 78 }

        -- 1.3.6.1.4.1.9839.2.1.1.79
        mal-hp2 OBJECT-TYPE
                    SYNTAX Integer32 (0..1)
                    UNITS "N/A"
                    MAX-ACCESS read-only
                    STATUS current
                    DESCRIPTION "Circuit 2 high pressure alarm (pressurestat)"
                    ::= { digitalObjects 79 }

        -- 1.3.6.1.4.1.9839.2.1.1.80
        mal-od1 OBJECT-TYPE
                    SYNTAX Integer32 (0..1)
                    UNITS "N/A"
                    MAX-ACCESS read-only
                    STATUS current
                    DESCRIPTION "Circuit 1 oil differential alarm"
                    ::= { digitalObjects 80 }

        -- 1.3.6.1.4.1.9839.2.1.1.81
        mal-od2 OBJECT-TYPE
                    SYNTAX Integer32 (0..1)
                    UNITS "N/A"
                    MAX-ACCESS read-only
                    STATUS current
                    DESCRIPTION "Circuit 2 oil differential alarm"
                    ::= { digitalObjects 81 }

        -- 1.3.6.1.4.1.9839.2.1.1.82
        mal-lp1 OBJECT-TYPE
                    SYNTAX Integer32 (0..1)
                    UNITS "N/A"
                    MAX-ACCESS read-only
                    STATUS current
                    DESCRIPTION "Circuit 1 low pressure alarm"
                    ::= { digitalObjects 82 }

        -- 1.3.6.1.4.1.9839.2.1.1.83
        mal-lp2 OBJECT-TYPE
                    SYNTAX Integer32 (0..1)
                    UNITS "N/A"
                    MAX-ACCESS read-only
                    STATUS current
                    DESCRIPTION "Circuit 2 low pressure alarm"
                    ::= { digitalObjects 83 }

        -- 1.3.6.1.4.1.9839.2.1.1.84
        mal-hpt1 OBJECT-TYPE
                    SYNTAX Integer32 (0..1)
                    UNITS "N/A"
                    MAX-ACCESS read-only
                    STATUS current
                    DESCRIPTION "Transducer 1 high pressure alarm"
                    ::= { digitalObjects 84 }

        -- 1.3.6.1.4.1.9839.2.1.1.85
        mal-hpt2 OBJECT-TYPE
                    SYNTAX Integer32 (0..1)
                    UNITS "N/A"
                    MAX-ACCESS read-only
                    STATUS current
                    DESCRIPTION "Transducer 2 high pressure alarm"
                    ::= { digitalObjects 85 }

        -- 1.3.6.1.4.1.9839.2.1.1.86
        mal-serious OBJECT-TYPE
                    SYNTAX Integer32 (0..1)
                    UNITS "N/A"
                    MAX-ACCESS read-only
                    STATUS current
                    DESCRIPTION "Serious alarm from digital input"
                    DEFVAL { 1 }
                    ::= { digitalObjects 86 }

        -- 1.3.6.1.4.1.9839.2.1.1.87
        mal-f1-overload OBJECT-TYPE
                    SYNTAX Integer32 (0..1)
                    UNITS "N/A"
                    MAX-ACCESS read-only
                    STATUS current
                    DESCRIPTION "Condensator fan 1 overload"
                    ::= { digitalObjects 87 }

        -- 1.3.6.1.4.1.9839.2.1.1.88
        mal-f2-overload OBJECT-TYPE
                    SYNTAX Integer32 (0..1)
                    UNITS "N/A"
                    MAX-ACCESS read-only
                    STATUS current
                    DESCRIPTION "Condensator fan 2 overload"
                    ::= { digitalObjects 88 }

        -- 1.3.6.1.4.1.9839.2.1.1.89
        mal-f3-overload OBJECT-TYPE
                    SYNTAX Integer32 (0..1)
                    UNITS "N/A"
                    MAX-ACCESS read-only
                    STATUS current
                    DESCRIPTION "Condensator fan 3 overload"
                    ::= { digitalObjects 89 }

        -- 1.3.6.1.4.1.9839.2.1.1.90
        mal-fan OBJECT-TYPE
                    SYNTAX Integer32 (0..1)
                    UNITS "N/A"
                    MAX-ACCESS read-only
                    STATUS current
                    DESCRIPTION "Main fan overload"
                    ::= { digitalObjects 90 }

        -- 1.3.6.1.4.1.9839.2.1.1.91
        mal-cpump OBJECT-TYPE
                    SYNTAX Integer32 (0..1)
                    UNITS "N/A"
                    MAX-ACCESS read-only
                    STATUS current
                    DESCRIPTION "Condensator pump overload"
                    ::= { digitalObjects 91 }

        -- 1.3.6.1.4.1.9839.2.1.1.92
        mal-pump OBJECT-TYPE
                    SYNTAX Integer32 (0..1)
                    UNITS "N/A"
                    MAX-ACCESS read-only
                    STATUS current
                    DESCRIPTION "Evaporator pump overload"
                    ::= { digitalObjects 92 }

        -- 1.3.6.1.4.1.9839.2.1.1.93
        mal-unit1-offl OBJECT-TYPE
                    SYNTAX Integer32 (0..1)
                    UNITS "N/A"
                    MAX-ACCESS read-only
                    STATUS current
                    DESCRIPTION "Unit 1 off-line"
                    ::= { digitalObjects 93 }

        -- 1.3.6.1.4.1.9839.2.1.1.94
        mal-unit2-offl OBJECT-TYPE
                    SYNTAX Integer32 (0..1)
                    UNITS "N/A"
                    MAX-ACCESS read-only
                    STATUS current
                    DESCRIPTION "Unit 2 off-line"
                    ::= { digitalObjects 94 }

        -- 1.3.6.1.4.1.9839.2.1.1.95
        mal-unit3-offl OBJECT-TYPE
                    SYNTAX Integer32 (0..1)
                    UNITS "N/A"
                    MAX-ACCESS read-only
                    STATUS current
                    DESCRIPTION "Unit 3 off-line"
                    ::= { digitalObjects 95 }

        -- 1.3.6.1.4.1.9839.2.1.1.96
        mal-unit4-offl OBJECT-TYPE
                    SYNTAX Integer32 (0..1)
                    UNITS "N/A"
                    MAX-ACCESS read-only
                    STATUS current
                    DESCRIPTION "Unit 4 off-line"
                    ::= { digitalObjects 96 }

        -- 1.3.6.1.4.1.9839.2.1.1.97
        mal-b1 OBJECT-TYPE
                    SYNTAX Integer32 (0..1)
                    UNITS "N/A"
                    MAX-ACCESS read-only
                    STATUS current
                    DESCRIPTION "b1 probe broken or not connected"
                    ::= { digitalObjects 97 }

        -- 1.3.6.1.4.1.9839.2.1.1.98
        mal-b2 OBJECT-TYPE
                    SYNTAX Integer32 (0..1)
                    UNITS "N/A"
                    MAX-ACCESS read-only
                    STATUS current
                    DESCRIPTION "b2 probe broken or not connected"
                    ::= { digitalObjects 98 }

        -- 1.3.6.1.4.1.9839.2.1.1.99
        mal-b3 OBJECT-TYPE
                    SYNTAX Integer32 (0..1)
                    UNITS "N/A"
                    MAX-ACCESS read-only
                    STATUS current
                    DESCRIPTION "b3 probe broken or not connected"
                    ::= { digitalObjects 99 }

        -- 1.3.6.1.4.1.9839.2.1.1.100
        mal-b4 OBJECT-TYPE
                    SYNTAX Integer32 (0..1)
                    UNITS "N/A"
                    MAX-ACCESS read-only
                    STATUS current
                    DESCRIPTION "b4 probe broken or not connected"
                    ::= { digitalObjects 100 }

        -- 1.3.6.1.4.1.9839.2.1.1.101
        mal-b5 OBJECT-TYPE
                    SYNTAX Integer32 (0..1)
                    UNITS "N/A"
                    MAX-ACCESS read-only
                    STATUS current
                    DESCRIPTION "b5 probe broken or not connected"
                    ::= { digitalObjects 101 }

        -- 1.3.6.1.4.1.9839.2.1.1.102
        mal-b6 OBJECT-TYPE
                    SYNTAX Integer32 (0..1)
                    UNITS "N/A"
                    MAX-ACCESS read-only
                    STATUS current
                    DESCRIPTION "b6 probe broken or not connected"
                    ::= { digitalObjects 102 }

        -- 1.3.6.1.4.1.9839.2.1.1.103
        mal-b7 OBJECT-TYPE
                    SYNTAX Integer32 (0..1)
                    UNITS "N/A"
                    MAX-ACCESS read-only
                    STATUS current
                    DESCRIPTION "b7 probe broken or not connected"
                    ::= { digitalObjects 103 }

        -- 1.3.6.1.4.1.9839.2.1.1.104
        mal-b8 OBJECT-TYPE
                    SYNTAX Integer32 (0..1)
                    UNITS "N/A"
                    MAX-ACCESS read-only
                    STATUS current
                    DESCRIPTION "b8 probe broken or not connected"
                    ::= { digitalObjects 104 }

        -- 1.3.6.1.4.1.9839.2.1.1.105
        mal-h-main-pump OBJECT-TYPE
                    SYNTAX Integer32 (0..1)
                    UNITS "N/A"
                    MAX-ACCESS read-only
                    STATUS current
                    DESCRIPTION "Main fun or main pump maintenance alarm"
                    ::= { digitalObjects 105 }

        -- 1.3.6.1.4.1.9839.2.1.1.106
        mal-h-comp1 OBJECT-TYPE
                    SYNTAX Integer32 (0..1)
                    UNITS "N/A"
                    MAX-ACCESS read-only
                    STATUS current
                    DESCRIPTION "Compressor 1 maintenance alarm"
                    ::= { digitalObjects 106 }

        -- 1.3.6.1.4.1.9839.2.1.1.107
        mal-h-comp2 OBJECT-TYPE
                    SYNTAX Integer32 (0..1)
                    UNITS "N/A"
                    MAX-ACCESS read-only
                    STATUS current
                    DESCRIPTION "Compressor 2 maintenance alarm"
                    ::= { digitalObjects 107 }

        -- 1.3.6.1.4.1.9839.2.1.1.108
        mal-h-comp3 OBJECT-TYPE
                    SYNTAX Integer32 (0..1)
                    UNITS "N/A"
                    MAX-ACCESS read-only
                    STATUS current
                    DESCRIPTION "Compressor 3 maintenance alarm"
                    ::= { digitalObjects 108 }

        -- 1.3.6.1.4.1.9839.2.1.1.109
        mal-h-comp4 OBJECT-TYPE
                    SYNTAX Integer32 (0..1)
                    UNITS "N/A"
                    MAX-ACCESS read-only
                    STATUS current
                    DESCRIPTION "Compressor 4 maintenance alarm"
                    ::= { digitalObjects 109 }

        -- 1.3.6.1.4.1.9839.2.1.1.110
        mal-clock32 OBJECT-TYPE
                    SYNTAX Integer32 (0..1)
                    UNITS "N/A"
                    MAX-ACCESS read-only
                    STATUS current
                    DESCRIPTION "32 clock board broken or not connected"
                    DEFVAL { 0 }
                    ::= { digitalObjects 110 }



        -- 1.3.6.1.4.1.9839.2.1.2
        analogObjects OBJECT IDENTIFIER ::= { mod-chMIB 2 }

        -- 1.3.6.1.4.1.9839.2.1.2.1
        ain-1 OBJECT-TYPE
                    SYNTAX Integer32 (-32767..32767)
                    UNITS "N/A"
                    MAX-ACCESS read-only
                    STATUS current
                    DESCRIPTION "Analogue input 1"
                    ::= { analogObjects 1 }

        -- 1.3.6.1.4.1.9839.2.1.2.2
        ain-2 OBJECT-TYPE
                    SYNTAX Integer32 (-32767..32767)
                    UNITS "N/A"
                    MAX-ACCESS read-only
                    STATUS current
                    DESCRIPTION "Analogue input 2"
                    ::= { analogObjects 2 }

        -- 1.3.6.1.4.1.9839.2.1.2.3
        ain-3 OBJECT-TYPE
                    SYNTAX Integer32 (-32767..32767)
                    UNITS "N/A"
                    MAX-ACCESS read-only
                    STATUS current
                    DESCRIPTION "Analogue input 3"
                    ::= { analogObjects 3 }

        -- 1.3.6.1.4.1.9839.2.1.2.4
        ain-4 OBJECT-TYPE
                    SYNTAX Integer32 (-32767..32767)
                    UNITS "N/A"
                    MAX-ACCESS read-only
                    STATUS current
                    DESCRIPTION "Analogue input 4"
                    ::= { analogObjects 4 }

        -- 1.3.6.1.4.1.9839.2.1.2.5
        ain-5 OBJECT-TYPE
                    SYNTAX Integer32 (-32767..32767)
                    UNITS "N/A"
                    MAX-ACCESS read-only
                    STATUS current
                    DESCRIPTION "Analogue input 5"
                    ::= { analogObjects 5 }

        -- 1.3.6.1.4.1.9839.2.1.2.6
        ain-6 OBJECT-TYPE
                    SYNTAX Integer32 (-32767..32767)
                    UNITS "N/A"
                    MAX-ACCESS read-only
                    STATUS current
                    DESCRIPTION "Analogue input 6"
                    ::= { analogObjects 6 }

        -- 1.3.6.1.4.1.9839.2.1.2.7
        ain-7 OBJECT-TYPE
                    SYNTAX Integer32 (-32767..32767)
                    UNITS "N/A"
                    MAX-ACCESS read-only
                    STATUS current
                    DESCRIPTION "Analogue input 7"
                    ::= { analogObjects 7 }

        -- 1.3.6.1.4.1.9839.2.1.2.8
        ain-8 OBJECT-TYPE
                    SYNTAX Integer32 (-32767..32767)
                    UNITS "N/A"
                    MAX-ACCESS read-only
                    STATUS current
                    DESCRIPTION "Analogue input 8"
                    ::= { analogObjects 8 }

        -- 1.3.6.1.4.1.9839.2.1.2.9
        analog-out-1 OBJECT-TYPE
                    SYNTAX Integer32 (-32767..32767)
                    UNITS "N/A"
                    MAX-ACCESS read-only
                    STATUS current
                    DESCRIPTION "Analogue output 1"
                    ::= { analogObjects 9 }

        -- 1.3.6.1.4.1.9839.2.1.2.10
        analog-out-2 OBJECT-TYPE
                    SYNTAX Integer32 (-32767..32767)
                    UNITS "N/A"
                    MAX-ACCESS read-only
                    STATUS current
                    DESCRIPTION "Analogue output 2"
                    ::= { analogObjects 10 }

        -- 1.3.6.1.4.1.9839.2.1.2.11
        s-temp-setpoint OBJECT-TYPE
                    SYNTAX Integer32 (-32767..32767)
                    UNITS "N/A"
                    MAX-ACCESS read-write
                    STATUS current
                    DESCRIPTION "Cooling set point (evaporator set point)"
                    DEFVAL { 120 }
                    ::= { analogObjects 11 }

        -- 1.3.6.1.4.1.9839.2.1.2.12
        w-temp-setpoint OBJECT-TYPE
                    SYNTAX Integer32 (-32767..32767)
                    UNITS "N/A"
                    MAX-ACCESS read-write
                    STATUS current
                    DESCRIPTION "Heating set point (condenser set point)"
                    DEFVAL { 450 }
                    ::= { analogObjects 12 }

        -- 1.3.6.1.4.1.9839.2.1.2.13
        cond-setpoint OBJECT-TYPE
                    SYNTAX Integer32 (-32767..32767)
                    UNITS "N/A"
                    MAX-ACCESS read-write
                    STATUS current
                    DESCRIPTION "Condenser control set point"
                    DEFVAL { 140 }
                    ::= { analogObjects 13 }

        -- 1.3.6.1.4.1.9839.2.1.2.14
        in-temp-setp OBJECT-TYPE
                    SYNTAX Integer32 (-32767..32767)
                    UNITS "N/A"
                    MAX-ACCESS read-only
                    STATUS current
                    DESCRIPTION "Current set point"
                    ::= { analogObjects 14 }



        -- 1.3.6.1.4.1.9839.2.1.3
        integerObjects OBJECT IDENTIFIER ::= { mod-chMIB 3 }

        -- 1.3.6.1.4.1.9839.2.1.3.10
        cu-remote-ctrl OBJECT-TYPE
                    SYNTAX Integer32 (-32767..32767)
                    UNITS "N/A"
                    MAX-ACCESS read-only
                    STATUS current
                    DESCRIPTION "Compressor remote control"
                    ::= { integerObjects 10 }

        -- 1.3.6.1.4.1.9839.2.1.3.11
        recover-mode OBJECT-TYPE
                    SYNTAX Integer32 (-32767..32767)
                    UNITS "N/A"
                    MAX-ACCESS read-only
                    STATUS current
                    DESCRIPTION "Recovery mode"
                    ::= { integerObjects 11 }

        -- 1.3.6.1.4.1.9839.2.1.3.12
        unit-status OBJECT-TYPE
                    SYNTAX Integer32 (-32767..32767)
                    UNITS "N/A"
                    MAX-ACCESS read-only
                    STATUS current
                    DESCRIPTION "Unit status"
                    ::= { integerObjects 12 }

        -- 1.3.6.1.4.1.9839.2.1.3.13
        cond-fans-mng OBJECT-TYPE
                    SYNTAX Integer32 (-32767..32767)
                    UNITS "N/A"
                    MAX-ACCESS read-write
                    STATUS current
                    DESCRIPTION "Fan control"
                    ::= { integerObjects 13 }

        -- 1.3.6.1.4.1.9839.2.1.3.20
        x-h-main-pump OBJECT-TYPE
                    SYNTAX Integer32 (-32767..32767)
                    UNITS "N/A"
                    MAX-ACCESS read-only
                    STATUS current
                    DESCRIPTION "Main pump operating hour count (high byte)"
                    ::= { integerObjects 20 }

        -- 1.3.6.1.4.1.9839.2.1.3.21
        x-l-main-pump OBJECT-TYPE
                    SYNTAX Integer32 (0..99999)
                    UNITS "N/A"
                    MAX-ACCESS read-only
                    STATUS current
                    DESCRIPTION "Main pump operating hour count (low byte)"
                    DEFVAL { 20000 }
                    ::= { integerObjects 21 }

        -- 1.3.6.1.4.1.9839.2.1.3.22
        x-h-comp1 OBJECT-TYPE
                    SYNTAX Integer32 (0..99999)
                    UNITS "N/A"
                    MAX-ACCESS read-only
                    STATUS current
                    DESCRIPTION "Compressor 1 operating hour count (high byte)"
                    DEFVAL { 10000 }
                    ::= { integerObjects 22 }

        -- 1.3.6.1.4.1.9839.2.1.3.23
        x-l-comp1 OBJECT-TYPE
                    SYNTAX Integer32 (0..99999)
                    UNITS "N/A"
                    MAX-ACCESS read-only
                    STATUS current
                    DESCRIPTION "Compressor 1 operating hour count (low byte)"
                    DEFVAL { 10000 }
                    ::= { integerObjects 23 }

        -- 1.3.6.1.4.1.9839.2.1.3.24
        x-h-comp2 OBJECT-TYPE
                    SYNTAX Integer32 (0..99999)
                    UNITS "N/A"
                    MAX-ACCESS read-only
                    STATUS current
                    DESCRIPTION "Compressor 2 operating hour count (high byte)"
                    DEFVAL { 10000 }
                    ::= { integerObjects 24 }

        -- 1.3.6.1.4.1.9839.2.1.3.25
        x-l-comp2 OBJECT-TYPE
                    SYNTAX Integer32 (0..99999)
                    UNITS "N/A"
                    MAX-ACCESS read-only
                    STATUS current
                    DESCRIPTION "Compressor 2 operating hour count (low byte)"
                    DEFVAL { 10000 }
                    ::= { integerObjects 25 }

        -- 1.3.6.1.4.1.9839.2.1.3.26
        x-h-comp3 OBJECT-TYPE
                    SYNTAX Integer32 (0..99999)
                    UNITS "N/A"
                    MAX-ACCESS read-only
                    STATUS current
                    DESCRIPTION "Compressor 3 operating hour count (high byte)"
                    DEFVAL { 10000 }
                    ::= { integerObjects 26 }

        -- 1.3.6.1.4.1.9839.2.1.3.27
        x-l-comp3 OBJECT-TYPE
                    SYNTAX Integer32 (0..99999)
                    UNITS "N/A"
                    MAX-ACCESS read-only
                    STATUS current
                    DESCRIPTION "Compressor 3 operating hour count (low byte)"
                    DEFVAL { 10000 }
                    ::= { integerObjects 27 }

        -- 1.3.6.1.4.1.9839.2.1.3.28
        x-h-comp4 OBJECT-TYPE
                    SYNTAX Integer32 (0..99999)
                    UNITS "N/A"
                    MAX-ACCESS read-only
                    STATUS current
                    DESCRIPTION "Compressor 4 operating hour count (high byte)"
                    DEFVAL { 10000 }
                    ::= { integerObjects 28 }

        -- 1.3.6.1.4.1.9839.2.1.3.29
        x-l-comp4 OBJECT-TYPE
                    SYNTAX Integer32 (0..99999)
                    UNITS "N/A"
                    MAX-ACCESS read-only
                    STATUS current
                    DESCRIPTION "Compressor 4 operating hour count (low byte)"
                    DEFVAL { 10000 }
                    ::= { integerObjects 29 }

        -- 1.3.6.1.4.1.9839.2.1.3.30
        config-unit OBJECT-TYPE
                    SYNTAX Integer32 (0..23)
                    UNITS "N/A"
                    MAX-ACCESS read-only
                    STATUS current
                    DESCRIPTION "Device configuration for all units"
                    DEFVAL { 16 }
                    ::= { integerObjects 30 }

        -- 1.3.6.1.4.1.9839.2.1.3.31
        config-type OBJECT-TYPE
                    SYNTAX Integer32 (-32767..32767)
                    UNITS "N/A"
                    MAX-ACCESS read-write
                    STATUS current
                    DESCRIPTION "Select unit type"
                    ::= { integerObjects 31 }

        -- 1.3.6.1.4.1.9839.2.1.3.32
        ph-circ-type OBJECT-TYPE
                    SYNTAX Integer32 (-32767..32767)
                    UNITS "N/A"
                    MAX-ACCESS read-only
                    STATUS current
                    DESCRIPTION "Type of circuit (physical)"
                    ::= { integerObjects 32 }

        -- 1.3.6.1.4.1.9839.2.1.3.33
        n-comps OBJECT-TYPE
                    SYNTAX Integer32 (1..8)
                    UNITS "N/A"
                    MAX-ACCESS read-write
                    STATUS current
                    DESCRIPTION "Total number of compressors on the machine"
                    DEFVAL { 1 }
                    ::= { integerObjects 33 }

        -- 1.3.6.1.4.1.9839.2.1.3.34
        comps-x-unit OBJECT-TYPE
                    SYNTAX Integer32 (1..4)
                    UNITS "N/A"
                    MAX-ACCESS read-write
                    STATUS current
                    DESCRIPTION "Number of compressors per unit (same for all units)"
                    DEFVAL { 1 }
                    ::= { integerObjects 34 }

        -- 1.3.6.1.4.1.9839.2.1.3.35
        n-unloaders OBJECT-TYPE
                    SYNTAX Integer32 (1..3)
                    UNITS "N/A"
                    MAX-ACCESS read-write
                    STATUS current
                    DESCRIPTION "Number of capacity stages per compressor (same for all units)"
                    DEFVAL { 3 }
                    ::= { integerObjects 35 }

        -- 1.3.6.1.4.1.9839.2.1.3.36
        cond-fans OBJECT-TYPE
                    SYNTAX Integer32 (-32767..32767)
                    UNITS "N/A"
                    MAX-ACCESS read-write
                    STATUS current
                    DESCRIPTION "Number of condenser fans"
                    DEFVAL { 1 }
                    ::= { integerObjects 36 }

        -- 1.3.6.1.4.1.9839.2.1.3.37
        fan1-speed-reg OBJECT-TYPE
                    SYNTAX Integer32 (-32767..32767)
                    UNITS "N/A"
                    MAX-ACCESS read-only
                    STATUS current
                    DESCRIPTION "Inverter speed circuit 1"
                    ::= { integerObjects 37 }

        -- 1.3.6.1.4.1.9839.2.1.3.38
        fan2-speed-reg OBJECT-TYPE
                    SYNTAX Integer32 (-32767..32767)
                    UNITS "N/A"
                    MAX-ACCESS read-only
                    STATUS current
                    DESCRIPTION "Inverter speed circuit 2"
                    ::= { integerObjects 38 }

        -- 1.3.6.1.4.1.9839.2.1.3.39
        freecool-valve OBJECT-TYPE
                    SYNTAX Integer32 (-32767..32767)
                    UNITS "N/A"
                    MAX-ACCESS read-only
                    STATUS current
                    DESCRIPTION "Freecooling valve opening"
                    ::= { integerObjects 39 }


	
	END

--
-- CAREL-mod-ch.MIB
--
