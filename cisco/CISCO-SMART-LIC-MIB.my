-- *****************************************************************
-- CISCO-SMART-LIC-MIB.my
--   
-- MIB for Cisco Software Smart Licensing
--   
-- Jul 2014, Sreejith Sreekumaran
-- Jan 2016, Kishan Panchangam
--   
-- Copyright (c) 2014-2017, 2020 by Cisco Systems Inc.
-- All rights reserved.
--   
-- The Structure looks like this
-- Smart License mib Objects
-- ---- Smart License Entitlements
-- ---- Smart License Entitlements Table
-- ---- Smart License Registration
-- ---- Initial Registration Times
-- ---- Renew Registration Times
-- ---- Authorization Info
-- ---- Authorization Info Eval Period
-- ---- Authorization Renewal Time
-- ---- Notification Objects
-- ---- Smart License MIB Notify
-- ---- Smart License MIB Conformance Objects
-- ---- Conformanc Compliance Objects
-- ---- Conformance Groups
--   
-- *****************************************************************

CISCO-SMART-LIC-MIB DEFINITIONS ::= BEGIN

IMPORTS
    MODULE-IDENTITY,
    OBJECT-TYPE,
    NOTIFICATION-TYPE,
    Unsigned32,
    Integer32
        FROM SNMPv2-SMI
    MODULE-COMPLIANCE,
    NOTIFICATION-GROUP,
    OBJECT-GROUP
        FROM SNMPv2-CONF
    SnmpAdminString
        FROM SNMP-FRAMEWORK-MIB
    TruthValue
        FROM SNMPv2-TC
    ciscoMgmt
        FROM CISCO-SMI;


ciscoSmartLicMIB MODULE-IDENTITY
    LAST-UPDATED    "202006210000Z"
    ORGANIZATION    "Cisco Systems, Inc."
    CONTACT-INFO
            "Cisco Systems
            Customer Service


            Postal: 170 W Tasman Drive

            San Jose, CA  95134

            USA


            Tel: +1 800 553-NETS


            E-mail: ask-smartlicensing@cisco.com"
    DESCRIPTION
        "The MIB module for managing licenses on the system.
        The licensing mechanism provides flexibility to
        enforce licensing for various features in the system.

        The following description introduces different concepts and
        terminologies necessary to understand the MIB
        definition and to perform license management.

        Product Instance: An instance of a Cisco software image that
        runs on a hardware platform and requires some licensing
        capability.

        Software ID tag: A string generated by the Cisco
        Connected Software IT team to uniquely identify a Cisco 
        software product.

        Smart Account: A Smart Licensing account that is created
        for Cisco customers or partners to manage their Smart
        Licensing product instances and licenses.  The account is
        created on the Cisco Smart Software Manager portal.  An
        enterprise account can have several virtual accounts (a.k.a.
        pools) of licenses.  

        Cisco Smart Software Manager (CSSM): The Smart Licensing
        back-end  system, hosted on Cisco IT infrastructure, is
        responsible for managing all Smart Licensing services and
        transactions.  It  provides a set of  APIs that the Smart Agent
        can communicate with and an external-facing 
        UI for Cisco customers and partners to log into and
        manage their  Smart Licensing account.

        Registration Token: A token that is generated from the
        Cisco Smart Software Manager.  The token is used to register a
        product instance with the Cisco Smart Software Manager.

        Smart Agent: A Smart Licensing software client that runs
        on a product instance and communicates with the Cisco Smart
        Software Manager.

        Entitlement Tag: A unique string that identifies a
        feature that can be enabled on a product instance.  The tags are
        used by both the  Smart Agent and the Cisco Smart Software
        Manager to track entitlement requests.  

        Transport Mode: The Smart Agent uses the Smart Call Home
        (SCH) service as a transport medium to communicate with the
        Smart Licensing back-end. 

        Crypto (LCS) Service: In addition to HTTPS exchanged
        messages are further signed and verified on both sides to ensure
        the authenticity of all communication.   The Smart Software
        Licensing system uses a crypto service and underlying crypto
        library (either CiscoSSL or PKI). The Smart Software Licensing
        back-end leverages the Licensing Crypto Service (LCS) service.

        UDI: Unique Device Identifier that uniquely identifies a
        device. Primarily it consists of a product ID, version ID and
        serial number of the Customers device.

        Grace Period: A product enters into a grace period when
        the authorization period expires. This is the result of
        multiple authorization attempt failures which occurring 90 days
        after the last successful authorization.  The grace period
        continues until the grace period expires - 90 days after the
        grace period starts.

        Counted License: Limits the number of similar entities that can
        consume a license. For example, a counted    license when used
        by a feature can limit the number of
        IP phones that can connect or the number of tunnels that can be
        created.

        Evaluation License: An Evaluation License grants the
        right to a customer to enable functionality of a product
        instance before registering it and without an explicit portal
        based license for a limited amount of time.  This amount of time
        ranges on average between 60 to 90 days.  Evaluation licenses
        are available for most functionality, but may be limited  for a
        variety of 
        reasons such as legal, royalty, regulatory, or other
        causes.

        This MIB module also defines various notifications that
        will be triggered to asynchronously notify the management
        application of any critical events."
    REVISION        "202006210000Z"
    DESCRIPTION
        "Documentaiton change."
    REVISION        "202005040000Z"
    DESCRIPTION
        "Documentaiton change."
    REVISION        "202001070000Z"
    DESCRIPTION
        "Added new notifications."
    REVISION        "201911270000Z"
    DESCRIPTION
        "Added new notifications."
    REVISION        "201708140000Z"
    DESCRIPTION
        "Added new notifications."
    REVISION        "201703300000Z"
    DESCRIPTION
        "Refactored the EntitlementInfo object and removed the HA info
        related notification objects"
    REVISION        "201703290000Z"
    DESCRIPTION
        "Removed Scheduler, HA and Certificate Info and also changes the
        data type for time related fields to Unsigned32.

        Also changed the data type to TruthValue for fields having
        boolean state"
    REVISION        "201411100000Z"
    DESCRIPTION
        "Modified based on review comments"
    REVISION        "201411090000Z"
    DESCRIPTION
        "Initial Version of Cisco Smart Licensing MIB"
    ::= { ciscoMgmt 831 }


-- Textual Conventions definition will be defined before this line
--   
-- Smart License MIB Objects

ciscoSlaMIBObjects  OBJECT IDENTIFIER
    ::= { ciscoSmartLicMIB 0 }


-- Smart License General Information

ciscoSlaInstanceId OBJECT-TYPE
    SYNTAX          Unsigned32
    MAX-ACCESS      read-only
    STATUS          current
    DESCRIPTION
        "This field contains the smart licence agent's instance number"
    ::= { ciscoSlaMIBObjects 1 }

ciscoSlaSUDIInfo OBJECT-TYPE
    SYNTAX          SnmpAdminString
    MAX-ACCESS      read-only
    STATUS          current
    DESCRIPTION
        "This field contains the device identifier information" 
    ::= { ciscoSlaMIBObjects 2 }

ciscoSlaVersion OBJECT-TYPE
    SYNTAX          SnmpAdminString
    MAX-ACCESS      read-only
    STATUS          current
    DESCRIPTION
        "Smart Licensing Version information in format
        e.g Cisco Smart Licensing Agent, Version 1.1.0_290" 
    ::= { ciscoSlaMIBObjects 3 }

ciscoSlaEnabled OBJECT-TYPE
    SYNTAX          TruthValue
    MAX-ACCESS      read-only
    STATUS          current
    DESCRIPTION
        "Tells whether the Smart Licensing mode is enabled or not."
    ::= { ciscoSlaMIBObjects 4 }
-- - Smart License Entitlements

ciscoSlaEntitlementInfo  OBJECT IDENTIFIER
    ::= { ciscoSlaMIBObjects 5 }

-- Smart License Entitlements Table

ciscoSlaEntitlementInfoTable OBJECT-TYPE
    SYNTAX          SEQUENCE OF CiscoSlaEntitlementInfoEntry 
    MAX-ACCESS      not-accessible
    STATUS          current
    DESCRIPTION
        "This table contains information about all entitlements being
        requested from this device"
    ::= { ciscoSlaEntitlementInfo 1 }

ciscoSlaEntitlementInfoEntry OBJECT-TYPE
    SYNTAX          CiscoSlaEntitlementInfoEntry
    MAX-ACCESS      not-accessible
    STATUS          current
    DESCRIPTION
        "An entry in ciscoSlaEntitlementInfoEntry. Each entry contains
        information about a entitlement requested on the device. This
        entry gets created when a license is requested successfully.
        Management application can not create these entries directly"
    INDEX           { ciscoSlaEntitlementInfoIndex } 
    ::= { ciscoSlaEntitlementInfoTable 1 }

CiscoSlaEntitlementInfoEntry ::= SEQUENCE {
        ciscoSlaEntitlementInfoIndex    Unsigned32,
        ciscoSlaEntitlementRequestCount Unsigned32,
        ciscoSlaEntitlementTag          SnmpAdminString,
        ciscoSlaEntitlementVersion      SnmpAdminString,
        ciscoSlaEntitlementEnforceMode  INTEGER,
        ciscoSlaEntitlementDescription  SnmpAdminString,
        ciscoSlaEntitlementFeatureName  SnmpAdminString,
        ciscoSlaEntitlementExportAllowed INTEGER
}

ciscoSlaEntitlementInfoIndex OBJECT-TYPE
    SYNTAX          Unsigned32
    MAX-ACCESS      not-accessible
    STATUS          current
    DESCRIPTION
        "This object uniquely identifies an entitlement record" 
    ::= { ciscoSlaEntitlementInfoEntry 1 }

ciscoSlaEntitlementRequestCount OBJECT-TYPE
    SYNTAX          Unsigned32
    MAX-ACCESS      read-only
    STATUS          current
    DESCRIPTION
        "Number of count that was requested for this entitlement tag. If
        the value is less than zero it means that this entitlement is
        not in use." 
    ::= { ciscoSlaEntitlementInfoEntry 2 }

ciscoSlaEntitlementTag OBJECT-TYPE
    SYNTAX          SnmpAdminString
    MAX-ACCESS      read-only
    STATUS          current
    DESCRIPTION
        "The tag name for the entitlement in use.
        This is abbreviated form of the entitlement tag." 
    ::= { ciscoSlaEntitlementInfoEntry 3 }

ciscoSlaEntitlementVersion OBJECT-TYPE
    SYNTAX          SnmpAdminString
    MAX-ACCESS      read-only
    STATUS          current
    DESCRIPTION
        "Entitlement version." 
    ::= { ciscoSlaEntitlementInfoEntry 4 }

ciscoSlaEntitlementEnforceMode OBJECT-TYPE
    SYNTAX          INTEGER  {
                        initialized(1), -- Initialized
                        waiting(2), -- The initial state after an
                                    -- entitlement request while we are
                                    -- waiting for the  authorization
                                    -- request  response. In this mode
                                    -- the device will already have
                                    -- established communication  with
                                    -- Cisco And successfully registered
                                    -- with Cisco Licensing Cloud
                        authorized(3), -- The Cisco Licensing Authority
                                       -- has responded that the
                                       -- entitlement requested is in
                                       -- compliance
                        outOfCompliance(4), -- The agent has received an
                                            -- out of compliance status
                                            -- in  response to an
                                            -- entitlement authorization
                                            -- request to the Cisco
                                            -- licensing authority. The
                                            -- customer is out of
                                            -- compliance with  their
                                            -- contract. They have
                                            -- either used too many
                                            -- licenses/entitlements or
                                            -- they are not authorized
                                            -- to  use a particular
                                            -- entitlement tag.
                        overage(5), -- The entitlement is in overage.
                                    -- This is informational only. No
                                    -- enforcement action should be
                                    -- taken. The customer is still in
                                    -- compliance
                                    -- but within the allowed overage
                                    -- amount as specified in their
                                    -- contract.
                        evaluationPeriod(6), -- The agent is using the
                                             -- evaluation period for
                                             -- this entitlement.
                                             -- In this mode
                                             -- the device has not
                                             -- established
                                             -- communication
                                             -- with Cisco and had not
                                             -- registered.
                        evaluationExpired(7), -- Evaluation period has
                                              -- expired.
                        authorizationExpired(8), -- Authorization period has expired.
                                                 -- This will occur if the device has not
                                                 -- has not been able to
                                                 -- communicate with Cisco for an
                                                 -- extended period of time
                                                 -- usually 90 days.
                        gracePeriodExpired(9), -- The grace period has
                                               -- expired. This means
                                               -- the device has not
                                               -- contacted
                                               -- Cisco for about 180
                                               -- days.
                        disabled(10), -- Smart Licensing has been
                                      -- deactivated or disabled. The
                                      -- application should disable the
                                      -- feature using this entitlement.
                        reservedAuthorized(11), -- Authorized and reservation 
                                                -- authorization code is installed.
                        invalidTag(12), -- The entitlement tag is
                                       -- invalid. The Licensing
                                       -- backend at Cisco
                                       -- does not recognize the
                                       -- entitlement tag because it is
                                       -- not in the database. 
                        notAuthorized(13) -- SLR authorization code is
                                          -- installed and it does not 
                                          -- contain one or more already
                                          -- consumed license.
                                          -- Or it does not contain enough 
                                          -- count for one or more license
                                          -- already consumed.
                    }
    MAX-ACCESS      read-only
    STATUS          current
    DESCRIPTION
        "Enforce Mode. This denotes  the enforcement mode for 
        the entitlement tag.

        * In Entitlement notifications this will indicate the
        enforcement mode of an individual entitlement.
        
        * In global notifications this indicates the overall
        enforcement mode in the agent." 
    ::= { ciscoSlaEntitlementInfoEntry 5 }

ciscoSlaEntitlementDescription OBJECT-TYPE
    SYNTAX          SnmpAdminString
    MAX-ACCESS      read-only
    STATUS          current
    DESCRIPTION
        "Description of this feature. May be NULL.
        This value is only available after the agent receives a
        response from CSSM to an Authorization request." 
    ::= { ciscoSlaEntitlementInfoEntry 6 }

ciscoSlaEntitlementFeatureName OBJECT-TYPE
    SYNTAX          SnmpAdminString
    MAX-ACCESS      read-only
    STATUS          current
    DESCRIPTION
        "The short feature name used by CSSM. May be NULL.
        The feature name is only available after the agent receives a
        response, from Cisco, to an Authorization request." 
    ::= { ciscoSlaEntitlementInfoEntry 7 }
    
ciscoSlaEntitlementExportAllowed OBJECT-TYPE
    SYNTAX          INTEGER  {
                        false(0), -- The entitlement is export restricted
                                  -- and this device is not allowed to use
                                  -- it.
                        true(1) -- Either the entitlement is not export
                                -- restricted so device is allowed to use
                                -- it. Or it's export restricted but
                                -- still device is is allowed to use it.
                    }
    MAX-ACCESS      read-only
    STATUS          current
    DESCRIPTION
        "Export allowed flag value for this entitlement" 
    ::= { ciscoSlaEntitlementInfoEntry 8 }
 

-- - Smart License Registration

ciscoSlaRegistrationStatusInfo  OBJECT IDENTIFIER
    ::= { ciscoSlaMIBObjects 6 }


ciscoSlaRegistrationStatus OBJECT-TYPE
    SYNTAX          INTEGER  {
                        notRegistered(1), -- Smart Agent not registered
                        registrationInProgress(2), -- Smart Agent
                                                   -- Registration is in
                                                   -- Progress
                        registrationFailed(3), -- Smart Agent
                                               -- Registration Failed
                        registrationRetryinProgress(4), -- Smart Agent
                                                        -- registration
                                                        -- retry in
                                                        -- Progress
                        registrationCompleted(5) -- Smart Agent
                                                 -- registration
                                                 -- completed.
                    }
    MAX-ACCESS      read-only
    STATUS          current
    DESCRIPTION
        "Smart Agent Registration Status. This is the status of the
        registration  initiated using the token generated from the
        Cisco
        Licensing portal." 
    ::= { ciscoSlaRegistrationStatusInfo 1 }

ciscoSlaVirtualAccount OBJECT-TYPE
    SYNTAX          SnmpAdminString
    MAX-ACCESS      read-only
    STATUS          current
    DESCRIPTION
        "The virtual account name created in the Licensing Portal to
        which this device will be registered." 
    ::= { ciscoSlaRegistrationStatusInfo 2 }

ciscoSlaNextCertificateExpireTime OBJECT-TYPE
    SYNTAX          Unsigned32
    MAX-ACCESS      read-only
    STATUS          current
    DESCRIPTION
        "The next expiration date/time of ID Certificate in UTC epoch
        seconds." 
    ::= { ciscoSlaRegistrationStatusInfo 3 }

ciscoSlaEnterpriseAccountName OBJECT-TYPE
    SYNTAX          SnmpAdminString
    MAX-ACCESS      read-only
    STATUS          current
    DESCRIPTION
        "The enterprise account name as configured in the Cisco
        Licensing Portal." 
    ::= { ciscoSlaRegistrationStatusInfo 4 }
-- Initial Registration Times

ciscoSlaRegisterTime  OBJECT IDENTIFIER
    ::= { ciscoSlaRegistrationStatusInfo 5 }


ciscoSlaRegisterInitTime OBJECT-TYPE
    SYNTAX          Unsigned32
    MAX-ACCESS      read-only
    STATUS          current
    DESCRIPTION
        "Time in UTC epoch seconds when the Registration of the Smart
        Agent
        was initialized." 
    ::= { ciscoSlaRegisterTime 1 }

ciscoSlaRegisterSuccess OBJECT-TYPE
    SYNTAX          TruthValue
    MAX-ACCESS      read-only
    STATUS          current
    DESCRIPTION
        "Status of the last attempted Registration of Smart Agent" 
    ::= { ciscoSlaRegisterTime 2 }

ciscoSlaRegisterFailureReason OBJECT-TYPE
    SYNTAX          SnmpAdminString
    MAX-ACCESS      read-only
    STATUS          current
    DESCRIPTION
        "Reason for the failure of the last Registration Attempt" 
    ::= { ciscoSlaRegisterTime 3 }

ciscoSlaRegisterNextRetryTime OBJECT-TYPE
    SYNTAX          Unsigned32
    MAX-ACCESS      read-only
    STATUS          current
    DESCRIPTION
        "Time in UTC epoch seconds when the next registration attempt
        will be made." 
    ::= { ciscoSlaRegisterTime 4 }
-- Renew Registration Times

ciscoSlaRenewTime  OBJECT IDENTIFIER
    ::= { ciscoSlaRegistrationStatusInfo 6 }


ciscoSlaRenewInitTime OBJECT-TYPE
    SYNTAX          Unsigned32
    MAX-ACCESS      read-only
    STATUS          current
    DESCRIPTION
        "Time in UTC epoch seconds when the ID Cert renewal was
        initialized" 
    ::= { ciscoSlaRenewTime 1 }

ciscoSlaRenewSuccess OBJECT-TYPE
    SYNTAX          TruthValue
    MAX-ACCESS      read-only
    STATUS          current
    DESCRIPTION
        "Status of Renewal of ID Certificate" 
    ::= { ciscoSlaRenewTime 2 }

ciscoSlaRenewFailureReason OBJECT-TYPE
    SYNTAX          SnmpAdminString
    MAX-ACCESS      read-only
    STATUS          current
    DESCRIPTION
        "Reason for the failure of the last attempted ID Cert Renewal" 
    ::= { ciscoSlaRenewTime 3 }

ciscoSlaRenewNextRetryTime OBJECT-TYPE
    SYNTAX          Unsigned32
    MAX-ACCESS      read-only
    STATUS          current
    DESCRIPTION
        "Time in UTC epoch seconds when the next ID Cert  renewal will
        be tried." 
    ::= { ciscoSlaRenewTime 4 }
-- - Authorization Info

ciscoSlaAuthorizationInfo  OBJECT IDENTIFIER
    ::= { ciscoSlaMIBObjects 7 }


ciscoSlaAuthExpireTime OBJECT-TYPE
    SYNTAX          Unsigned32
    MAX-ACCESS      read-only
    STATUS          current
    DESCRIPTION
        "The time in UTC epoch seconds  when the authorization will
        expire if
        not renewed" 
    ::= { ciscoSlaAuthorizationInfo 1 }

ciscoSlaAuthComplianceStatus OBJECT-TYPE
    SYNTAX          SnmpAdminString
    MAX-ACCESS      read-only
    STATUS          current
    DESCRIPTION
        "Overall enforcement status of Smart Licensing in the device." 
    ::= { ciscoSlaAuthorizationInfo 2 }

ciscoSlaAuthOOCStartTime OBJECT-TYPE
    SYNTAX          Unsigned32
    MAX-ACCESS      read-only
    STATUS          current
    DESCRIPTION
        "The  time in UTC epoch seconds Smart Agent entered Out of
        Compliance state for this
        device." 
    ::= { ciscoSlaAuthorizationInfo 3 }
-- Authorization Info Eval Period

ciscoSlaAuthEvalPeriod  OBJECT IDENTIFIER
    ::= { ciscoSlaAuthorizationInfo 4 }


ciscoSlaAuthEvalPeriodInUse OBJECT-TYPE
    SYNTAX          TruthValue
    MAX-ACCESS      read-only
    STATUS          current
    DESCRIPTION
        "Indicates if the Evaluation Period is in Use or not" 
    ::= { ciscoSlaAuthEvalPeriod 1 }

ciscoSlaAuthEvalExpiredTime OBJECT-TYPE
    SYNTAX          Unsigned32
    MAX-ACCESS      read-only
    STATUS          current
    DESCRIPTION
        "Time in UTC epoch seconds  when the Evaluation Period had
        expired." 
    ::= { ciscoSlaAuthEvalPeriod 2 }

ciscoSlaAuthEvalPeriodLeft OBJECT-TYPE
    SYNTAX          Unsigned32
    MAX-ACCESS      read-only
    STATUS          current
    DESCRIPTION
        "Amount of Time left in the Evaluation Period" 
    ::= { ciscoSlaAuthEvalPeriod 3 }
-- Authorization Renewal

ciscoSlaAuthRenewTime  OBJECT IDENTIFIER
    ::= { ciscoSlaAuthorizationInfo 5 }


ciscoSlaAuthRenewInitTime OBJECT-TYPE
    SYNTAX          Unsigned32
    MAX-ACCESS      read-only
    STATUS          current
    DESCRIPTION
        "Smart Agent Authorization Renewal Initialization Time in UTC
        epoch seconds" 
    ::= { ciscoSlaAuthRenewTime 1 }

ciscoSlaAuthRenewSuccess OBJECT-TYPE
    SYNTAX          TruthValue
    MAX-ACCESS      read-only
    STATUS          current
    DESCRIPTION
        "Indicates if the Authorization Renewal was successful
        or not" 
    ::= { ciscoSlaAuthRenewTime 2 }

ciscoSlaAuthRenewFailureReason OBJECT-TYPE
    SYNTAX          SnmpAdminString
    MAX-ACCESS      read-only
    STATUS          current
    DESCRIPTION
        "The reason for the failure of the last renewal request." 
    ::= { ciscoSlaAuthRenewTime 3 }

ciscoSlaAuthRenewNextRetryTime OBJECT-TYPE
    SYNTAX          Unsigned32
    MAX-ACCESS      read-only
    STATUS          current
    DESCRIPTION
        "Time in UTC epoch seconds when the next renewal will be
        retried." 
    ::= { ciscoSlaAuthRenewTime 4 }
-- - Notification Objects

ciscoSlaNotifObjects  OBJECT IDENTIFIER
    ::= { ciscoSlaMIBObjects 8 }


ciscoSlaGlobalNotifEnable OBJECT-TYPE
    SYNTAX          TruthValue
    MAX-ACCESS      read-write
    STATUS          current
    DESCRIPTION
        "This object indicates whether the device should generate
        the global notifications related to Smart Agent. This object
        enables/disables sending following notifications:
         ciscoSlaSmartAgentNotifyEnforcementMode,
         ciscoSlaSmartAgentNotifyReady,
         ciscoSlaSmartAgentNotifyEnabled,
         ciscoSlaSmartAgentNotifyDisabled,                            
         ciscoSlaSmartAgentNotifyRegisterFailed,                       
         ciscoSlaSmartAgentNotifyRegisterSuccess,                       
         ciscoSlaSmartAgentNotifyIdCertExpired,                       
         ciscoSlaSmartAgentNotifyIdCertRenewSuccess,
         ciscoSlaSmartAgentNotifyIdCertRenewFail,                      
         ciscoSlaSmartAgentNotifyAuthRenewSuccess,                      
         ciscoSlaSmartAgentNotifyAuthRenewFail,                       
         ciscoSlaSmartAgentNotifyCommunicationFailure,
         ciscoSlaSmartAgentNotifyCommunicationRestored,              
         ciscoSlaSmartAgentNotifyIdCertRenewNotStarted,         
         ciscoSlaSmartAgentNotifyIdCertOutOfRange,         
         ciscoSlaSmartAgentNotifySystemClockChanged,       
         ciscoSlaSmartAgentNotifyEvalExpiryWarning,      
         ciscoSlaSmartAgentNotifyEvalExpired,           
         ciscoSlaSmartAgentNotifyIdCertExpiryWarning,
         ciscoSlaSmartAgentNotifyDeRegisterSuccess,
         ciscoSlaSmartAgentNotifyDeRegisterFailed,
         ciscoSlaSmartAgentNotifyConversionStarted,
         ciscoSlaSmartAgentNotifyConversionStatus,
         ciscoSlaSmartAgentNotifyConversionComplete,
         ciscoSlaSmartAgentNotifyThirdpartyModeEnabled,
         ciscoSlaSmartAgentNotifyThirdpartyModeDisabled,
         ciscoSlaSmartAgentNotifyUtilityCertExpired,
         ciscoSlaSmartAgentNotifyUtilityCertRenewFailed,
         ciscoSlaSmartAgentNotifyUtilityCertRenewSuccess,
         ciscoSlaSmartAgentNotifyUtilityDataReportingStarted,
         ciscoSlaSmartAgentNotifyUtilityDataReportingStopped,
         ciscoSlaSmartAgentNotifyUtilitySendRUMFailed,
         ciscoSlaSmartAgentNotifyUtilityCertFQDNMismatch,
         ciscoSlaSmartAgentNotifySmartTransportNotConfigured,
         ciscoSlaSmartAgentNotifyHostnameMatchedWithUDI,
         ciscoSlaSmartAgentNotifyExportRequestFailure,
         ciscoSlaSmartAgentNotifyExportHAMismatch,
         ciscoSlaSmartAgentNotifyExportAuthKeyNotSupported,
         ciscoSlaSmartAgentNotifyExportControlledTag,
         ciscoSlaSmartAgentNotifyEndPointReset,
         ciscoSlaSmartAgentNotifyExportRequestSuccess,
         ciscoSlaSmartAgentNotifyAuthorizationInstall,
         ciscoSlaSmartAgentNotifyAuthorizationRemove,
         ciscoSlaSmartAgentNotifyPolicyInstalled,
         ciscoSlaSmartAgentNotifyPolicyRemoved,
         ciscoSlaSmartAgentNotifyRUMACKNotReceived,
         ciscoSlaSmartAgentNotifyRUMACKReceived,
         ciscoSlaSmartAgentNotifyAuthorizationInstallFailed,
         ciscoSlaSmartAgentNotifyReportingRequired"
    DEFVAL          { true } 
    ::= { ciscoSlaNotifObjects 1 }

ciscoSlaEntitlementNotifEnable OBJECT-TYPE
    SYNTAX          TruthValue
    MAX-ACCESS      read-write
    STATUS          current
    DESCRIPTION
        "This object indicates whether the device should generate
        the  notifications related to entitlement enforce mode in Smart
        Agent. This object
        enables/disables sending following notifications:
        ciscoSlaSmartAgentNotifyEntitlementEnforceMode"
    ::= { ciscoSlaNotifObjects 2 }
-- De Registration Info objects

ciscoSlaDeRegistrationInfo  OBJECT IDENTIFIER
    ::= { ciscoSlaMIBObjects 9 }


ciscoSlaFailureReason OBJECT-TYPE
    SYNTAX          INTEGER  {
                        invalid(0), -- Invalid failure reason
                        alreadyRegistered(1), -- Smart Agent already
                                              -- registered
                        dailyJobTimerReset(2), -- Smart Agent
                                               -- Daily Job timer reset
                        deRegisterFailure(3) -- Generic failure reason
                                              -- for de-register
                                              -- Specific reason is in ciscoSlaDeRegisterFailureMsg
                    }
    MAX-ACCESS      read-only
    STATUS          current
    DESCRIPTION
        "Smart Agent Registration/de-registration failure reasons. This
        should be received in response message from Cisco Smart Software
        Manager." 
    ::= { ciscoSlaDeRegistrationInfo 1 }

ciscoSlaDeRegisterFailureMsg OBJECT-TYPE
    SYNTAX          SnmpAdminString
    MAX-ACCESS      read-only
    STATUS          current
    DESCRIPTION
        "The failure message of the last deregistration request." 
    ::= { ciscoSlaDeRegistrationInfo 2 }
-- Third party and Utility Info objects

ciscoSlaThirdPartyAndUtilityInfo  OBJECT IDENTIFIER
    ::= { ciscoSlaMIBObjects 10 }


ciscoSlaThirdPartyAndUtilityFailureMsg OBJECT-TYPE
    SYNTAX          SnmpAdminString
    MAX-ACCESS      read-only
    STATUS          current
    DESCRIPTION
        "Failure reason string." 
    ::= { ciscoSlaThirdPartyAndUtilityInfo 1 }
ciscoSlaExportInfo  OBJECT IDENTIFIER
    ::= { ciscoSlaMIBObjects 11 }


ciscoSlaExportFailureReason OBJECT-TYPE
    SYNTAX          Integer32
    MAX-ACCESS      read-only
    STATUS          current
    DESCRIPTION
        "Failure reason enum. Enum includes:
        Invalid = 0
        AlreadyRegistered = 1
        DailyJobTimerReset = 2
        Deregister = 3" 
    ::= { ciscoSlaExportInfo 1 }

ciscoSlaExportFailureMessage OBJECT-TYPE
    SYNTAX          SnmpAdminString
    MAX-ACCESS      read-only
    STATUS          current
    DESCRIPTION
        "Failure message in string format." 
    ::= { ciscoSlaExportInfo 2 }
ciscoSlaReportingInfo  OBJECT IDENTIFIER
    ::= { ciscoSlaMIBObjects 12 }


ciscoSlaDaysRUMAckNotReceived OBJECT-TYPE
    SYNTAX          Unsigned32
    MAX-ACCESS      read-only
    STATUS          current
    DESCRIPTION
        "Number of days RUM ack has not been received." 
    ::= { ciscoSlaReportingInfo 1 }

ciscoSlaDaysReportingRequired OBJECT-TYPE
    SYNTAX          Unsigned32
    MAX-ACCESS      read-only
    STATUS          current
    DESCRIPTION
        "Number of days within which reporting has to be done." 
    ::= { ciscoSlaReportingInfo 2 }
-- Smart License MIB Notify

ciscoSlaMIBNotifs  OBJECT IDENTIFIER
    ::= { ciscoSmartLicMIB 1 }


ciscoSlaSmartAgentNotifyEnforcementMode NOTIFICATION-TYPE
    OBJECTS         {
                        ciscoSlaSUDIInfo,
                        ciscoSlaEntitlementEnforceMode
                    }
    STATUS          current
    DESCRIPTION
        "This notification is sent when the overall enforcement mode in
        the agent changes."
   ::= { ciscoSlaMIBNotifs 1 }

ciscoSlaSmartAgentNotifyReady NOTIFICATION-TYPE
    OBJECTS         { ciscoSlaSUDIInfo }
    STATUS          current
    DESCRIPTION
        "This notification is sent when the Smart agent is initialized
        and ready."
   ::= { ciscoSlaMIBNotifs 2 }

ciscoSlaSmartAgentNotifyEnabled NOTIFICATION-TYPE
    OBJECTS         { ciscoSlaSUDIInfo }
    STATUS          current
    DESCRIPTION
        "This notification is sent when Smart licensing has been
        enabled."
   ::= { ciscoSlaMIBNotifs 3 }

ciscoSlaSmartAgentNotifyDisabled NOTIFICATION-TYPE
    OBJECTS         { ciscoSlaSUDIInfo }
    STATUS          current
    DESCRIPTION
        "This notification is sent when Smart licensing has been
        disabled"
   ::= { ciscoSlaMIBNotifs 4 }

ciscoSlaSmartAgentNotifyRegisterFailed NOTIFICATION-TYPE
    OBJECTS         { ciscoSlaSUDIInfo }
    STATUS          current
    DESCRIPTION
        "This notification is sent when Smart licensing registration
        with Cisco Software Manager has failed"
   ::= { ciscoSlaMIBNotifs 5 }

ciscoSlaSmartAgentNotifyRegisterSuccess NOTIFICATION-TYPE
    OBJECTS         { ciscoSlaSUDIInfo }
    STATUS          current
    DESCRIPTION
        "This notification is sent when Smart licensing registration
        with Cisco Software Manager has succeeded."
   ::= { ciscoSlaMIBNotifs 6 }

ciscoSlaSmartAgentNotifyIdCertExpired NOTIFICATION-TYPE
    OBJECTS         { ciscoSlaSUDIInfo }
    STATUS          current
    DESCRIPTION
        "This notification is sent when Smart licensing ID (node)
        certificate has expired"
   ::= { ciscoSlaMIBNotifs 7 }

ciscoSlaSmartAgentNotifyIdCertRenewSuccess NOTIFICATION-TYPE
    OBJECTS         { ciscoSlaSUDIInfo }
    STATUS          current
    DESCRIPTION
        "This notification is sent when Smart licensing ID (node)
        certificate renewal has succeded."
   ::= { ciscoSlaMIBNotifs 8 }

ciscoSlaSmartAgentNotifyIdCertRenewFail NOTIFICATION-TYPE
    OBJECTS         { ciscoSlaSUDIInfo }
    STATUS          current
    DESCRIPTION
        "This notification is sent when Smart licensing ID (node)
        certificate renewal has failed."
   ::= { ciscoSlaMIBNotifs 9 }

ciscoSlaSmartAgentNotifyAuthRenewSuccess NOTIFICATION-TYPE
    OBJECTS         { ciscoSlaSUDIInfo }
    STATUS          current
    DESCRIPTION
        "This notification is sent when Smart licensing entitlement
        (AUTH) renew was successful."
   ::= { ciscoSlaMIBNotifs 10 }

ciscoSlaSmartAgentNotifyAuthRenewFail NOTIFICATION-TYPE
    OBJECTS         { ciscoSlaSUDIInfo }
    STATUS          current
    DESCRIPTION
        "This notification is sent when Smart licensing entitlement
        (AUTH) renew has failed"
   ::= { ciscoSlaMIBNotifs 11 }

ciscoSlaSmartAgentNotifyCommunicationFailure NOTIFICATION-TYPE
    OBJECTS         { ciscoSlaSUDIInfo }
    STATUS          current
    DESCRIPTION
        "This notification is sent when Smart Agent
        failed to communicate with CSSM."
   ::= { ciscoSlaMIBNotifs 12 }

ciscoSlaSmartAgentNotifyCommunicationRestored NOTIFICATION-TYPE
    OBJECTS         { ciscoSlaSUDIInfo }
    STATUS          current
    DESCRIPTION
        "This notification is sent when Smart Agent
        communication with CSSM has been restored"
   ::= { ciscoSlaMIBNotifs 13 }

ciscoSlaSmartAgentNotifyIdCertRenewNotStarted NOTIFICATION-TYPE
    OBJECTS         { ciscoSlaSUDIInfo }
    STATUS          current
    DESCRIPTION
        "This notification is sent when Smart Agent
        Id (Node) certificate renewal is not started"
   ::= { ciscoSlaMIBNotifs 14 }

ciscoSlaSmartAgentNotifyEntitlementEnforceMode NOTIFICATION-TYPE
    OBJECTS         {
                        ciscoSlaEntitlementRequestCount,
                        ciscoSlaEntitlementTag,
                        ciscoSlaEntitlementVersion,
                        ciscoSlaEntitlementEnforceMode,
                        ciscoSlaSUDIInfo
                    }
    STATUS          current
    DESCRIPTION
        "This notification is sent when the enforcement mode of an
        entitlement has changed."
   ::= { ciscoSlaMIBNotifs 15 }

ciscoSlaSmartAgentNotifyIdCertOutOfRange NOTIFICATION-TYPE
    OBJECTS         { ciscoSlaSUDIInfo }
    STATUS          current
    DESCRIPTION
        "This notification is sent when the ID certificate is
        out of the valid range after the system clock changed.
        It means the current time is either before the start time or
        after the end time of the certificate."
   ::= { ciscoSlaMIBNotifs 16 }

ciscoSlaSmartAgentNotifySystemClockChanged NOTIFICATION-TYPE
    OBJECTS         { ciscoSlaSUDIInfo }
    STATUS          current
    DESCRIPTION
        "This notification is sent when the system clock has changed."
   ::= { ciscoSlaMIBNotifs 17 }

ciscoSlaSmartAgentNotifyEvalExpiryWarning NOTIFICATION-TYPE
    OBJECTS         { ciscoSlaSUDIInfo }
    STATUS          current
    DESCRIPTION
        "This notification is sent to warn regarding the impending
        evaluation  time expiry."
   ::= { ciscoSlaMIBNotifs 18 }

ciscoSlaSmartAgentNotifyEvalExpired NOTIFICATION-TYPE
    OBJECTS         { ciscoSlaSUDIInfo }
    STATUS          current
    DESCRIPTION
        "This notification is sent to notify the expiration of the
        evaluation period."
   ::= { ciscoSlaMIBNotifs 19 }

ciscoSlaSmartAgentNotifyIdCertExpiryWarning NOTIFICATION-TYPE
    OBJECTS         { ciscoSlaSUDIInfo }
    STATUS          current
    DESCRIPTION
        "This notification is sent to warn regarding the impending
        expiry of the id (node) certificate."
   ::= { ciscoSlaMIBNotifs 20 }
   
ciscoSlaSmartAgentNotifyDeRegisterSuccess NOTIFICATION-TYPE
    OBJECTS         { ciscoSlaSUDIInfo }
    STATUS          current
    DESCRIPTION
        "This notification is sent to inform that the product has
        successfully un-registered with the Cisco Smart Software 
        Manager."
   ::= { ciscoSlaMIBNotifs 21 }

ciscoSlaSmartAgentNotifyDeRegisterFailed NOTIFICATION-TYPE
    OBJECTS         {
                        ciscoSlaSUDIInfo,
                        ciscoSlaFailureReason,
                        ciscoSlaDeRegisterFailureMsg
                    }
    STATUS          current
    DESCRIPTION
        "This notification is sent to inform that Cisco Smart Software
        Manager has send error in de-registration response.
        The agent will locally remove all registration information and 
        transition back to the unidentified (not-registered) state.
        CSSM would not know the agent is un-registered."
   ::= { ciscoSlaMIBNotifs 22 }

ciscoSlaSmartAgentNotifyThirdpartyModeEnabled NOTIFICATION-TYPE
    OBJECTS         { ciscoSlaSUDIInfo }
    STATUS          current
    DESCRIPTION
        "This notification is sent to inform the Agent is now in
        thirdparty mode."
   ::= { ciscoSlaMIBNotifs 23 }

ciscoSlaSmartAgentNotifyThirdpartyModeDisabled NOTIFICATION-TYPE
    OBJECTS         { ciscoSlaSUDIInfo }
    STATUS          current
    DESCRIPTION
        "This notification is sent to inform the Agent is now out of
        thirdparty mode."
   ::= { ciscoSlaMIBNotifs 24 }

ciscoSlaSmartAgentNotifyUtilityCertExpired NOTIFICATION-TYPE
    OBJECTS         { ciscoSlaSUDIInfo }
    STATUS          current
    DESCRIPTION
        "This notification is sent to inform that Utility certificate
        has expired."
   ::= { ciscoSlaMIBNotifs 25 }

ciscoSlaSmartAgentNotifyUtilityCertRenewFailed NOTIFICATION-TYPE
    OBJECTS         {
                        ciscoSlaSUDIInfo,
                        ciscoSlaThirdPartyAndUtilityFailureMsg
                    }
    STATUS          current
    DESCRIPTION
        "This notification is sent to inform that Utility certificate
        renewal has failed."
   ::= { ciscoSlaMIBNotifs 26 }

ciscoSlaSmartAgentNotifyUtilityCertRenewSuccess NOTIFICATION-TYPE
    OBJECTS         { ciscoSlaSUDIInfo }
    STATUS          current
    DESCRIPTION
        "This notification is sent to inform that Utility certificate
        renewal successful."
   ::= { ciscoSlaMIBNotifs 27 }

ciscoSlaSmartAgentNotifyUtilityDataReportingStarted NOTIFICATION-TYPE
    OBJECTS         { ciscoSlaSUDIInfo }
    STATUS          current
    DESCRIPTION
        "This notification is sent to inform that Utility data reporting
        has started.
        In TPBP this will occur when the product instance receives a 
        utility certificate during registration.
        In SPLA utility it occurs when utility is enabled, the URL is
        set in the CLI and the agent has received subscription 
        information."
   ::= { ciscoSlaMIBNotifs 28 }

ciscoSlaSmartAgentNotifyUtilityDataReportingStopped NOTIFICATION-TYPE
    OBJECTS         { ciscoSlaSUDIInfo }
    STATUS          current
    DESCRIPTION
        "This notification is sent to inform that Utility data reporting
        has stopped.
        In TPBP this will occur on a de-registration or when the utility
        certificate expires.
        In SPLA it occurs when utility is utility is disabled, a 
        de-registration occurs or the ID certificate expires."
   ::= { ciscoSlaMIBNotifs 29 }

ciscoSlaSmartAgentNotifyUtilitySendRUMFailed NOTIFICATION-TYPE
    OBJECTS         {
                        ciscoSlaSUDIInfo,
                        ciscoSlaThirdPartyAndUtilityFailureMsg
                    }
    STATUS          current
    DESCRIPTION
        "This notification is sent to inform that rum report send
        failed."
   ::= { ciscoSlaMIBNotifs 30 }

ciscoSlaSmartAgentNotifyUtilityCertFQDNMismatch NOTIFICATION-TYPE
    OBJECTS         { ciscoSlaSUDIInfo }
    STATUS          current
    DESCRIPTION
        "This notification is sent to inform Utility cert config
        mismatch. The Smart licensing url setting does not match the 
        FQDN embedded in the utility certificate."
   ::= { ciscoSlaMIBNotifs 31 }

ciscoSlaSmartAgentNotifySmartTransportNotConfigured NOTIFICATION-TYPE
    OBJECTS         { ciscoSlaSUDIInfo }
    STATUS          current
    DESCRIPTION
        "This notification is sent when Utility is enabled and we have
        subscription but smart transport is not configured"
   ::= { ciscoSlaMIBNotifs 32 }

ciscoSlaSmartAgentNotifyHostnameMatchedWithUDI NOTIFICATION-TYPE
    OBJECTS         { ciscoSlaSUDIInfo }
    STATUS          current
    DESCRIPTION
        "This notification is sent when Smart Agent receives a
        HostnameChange event and new hostname is matched with one or
        more fields in current UDI."
   ::= { ciscoSlaMIBNotifs 33 }

ciscoSlaSmartAgentNotifyExportRequestFailure NOTIFICATION-TYPE
    OBJECTS         {
                        ciscoSlaSUDIInfo,
                        ciscoSlaEntitlementFeatureName,
                        ciscoSlaEntitlementTag,
                        ciscoSlaExportFailureMessage
                    }
    STATUS          current
    DESCRIPTION
        "This notification is sent when request for the export
        authorization key has failed."
   ::= { ciscoSlaMIBNotifs 34 }

ciscoSlaSmartAgentNotifyExportHAMismatch NOTIFICATION-TYPE
    OBJECTS         {
                        ciscoSlaSUDIInfo,
                        ciscoSlaExportFailureReason,
                        ciscoSlaExportFailureMessage
                    }
    STATUS          current
    DESCRIPTION
        "This notification is sent when standby or members do not have
        the export authorization keys for all the same features as the
        active has."
   ::= { ciscoSlaMIBNotifs 35 }

ciscoSlaSmartAgentNotifyExportAuthKeyNotSupported NOTIFICATION-TYPE
    OBJECTS         { ciscoSlaSUDIInfo }
    STATUS          current
    DESCRIPTION
        "This notification is sent when the request for export
        authorization (or return) key is currently not supported by the
        satellite."
   ::= { ciscoSlaMIBNotifs 36 }

ciscoSlaSmartAgentNotifyExportControlledTag NOTIFICATION-TYPE
    OBJECTS         {
                        ciscoSlaSUDIInfo,
                        ciscoSlaEntitlementTag,
                        ciscoSlaEntitlementExportAllowed
                    }
    STATUS          current
    DESCRIPTION
        "This notification is sent to specify whether the Customer is
        allowed or not allowed to use an export controlled entitlement."
   ::= { ciscoSlaMIBNotifs 37 }

ciscoSlaSmartAgentNotifyEndPointReset NOTIFICATION-TYPE
    OBJECTS         { ciscoSlaSUDIInfo }
    STATUS          current
    DESCRIPTION
        "This notification is sent to platform so that it reports the
        entire list of End Points to Smart Agent instead of delta."
   ::= { ciscoSlaMIBNotifs 38 }

ciscoSlaSmartAgentNotifyExportRequestSuccess NOTIFICATION-TYPE
    OBJECTS         {
                        ciscoSlaSUDIInfo,
                        ciscoSlaEntitlementFeatureName,
                        ciscoSlaEntitlementTag
                    }
    STATUS          current
    DESCRIPTION
        "This notification is sent when the request for the export
        authorization key is successful."
   ::= { ciscoSlaMIBNotifs 39 }

ciscoSlaSmartAgentNotifyAuthorizationInstall NOTIFICATION-TYPE
    OBJECTS         { ciscoSlaSUDIInfo }
    STATUS          current
    DESCRIPTION
        "This notification is sent in all the below scenarios:
        - A new Smart Licensing authorization code has been
        installed.
        - A new authorization code has been installed and has
        overwritten a previous code.
        - The platform has delivered a list of entitlements to the
        agent that may be authorized."
   ::= { ciscoSlaMIBNotifs 40 }

ciscoSlaSmartAgentNotifyAuthorizationRemove NOTIFICATION-TYPE
    OBJECTS         { ciscoSlaSUDIInfo }
    STATUS          current
    DESCRIPTION
        "This notification is sent when an authorization code has
        been removed."
   ::= { ciscoSlaMIBNotifs 41 }

ciscoSlaSmartAgentNotifyPolicyInstalled NOTIFICATION-TYPE
    OBJECTS         { ciscoSlaSUDIInfo }
    STATUS          current
    DESCRIPTION
        "This notification is sent when policy file is installed in
        device."
   ::= { ciscoSlaMIBNotifs 42 }

ciscoSlaSmartAgentNotifyPolicyRemoved NOTIFICATION-TYPE
    OBJECTS         { ciscoSlaSUDIInfo }
    STATUS          current
    DESCRIPTION
        "This notification is sent when policy file is removed from
        device."
   ::= { ciscoSlaMIBNotifs 43 }

ciscoSlaSmartAgentNotifyRUMACKNotReceived NOTIFICATION-TYPE
    OBJECTS         {
                        ciscoSlaSUDIInfo,
                        ciscoSlaDaysRUMAckNotReceived
                    }
    STATUS          current
    DESCRIPTION
        "This notification would be sent when RUM report ack has not
        been received in the time (in days) specified by the installed
        policy."
   ::= { ciscoSlaMIBNotifs 44 }

ciscoSlaSmartAgentNotifyRUMACKReceived NOTIFICATION-TYPE
    OBJECTS         { ciscoSlaSUDIInfo }
    STATUS          current
    DESCRIPTION
        "This notification is sent when a RUM report ACK is received."
   ::= { ciscoSlaMIBNotifs 45 }

ciscoSlaSmartAgentNotifyAuthorizationInstallFailed NOTIFICATION-TYPE
    OBJECTS         { ciscoSlaSUDIInfo }
    STATUS          current
    DESCRIPTION
        "This notification is sent when an attempt to install licensing
        authorization code is failed."
   ::= { ciscoSlaMIBNotifs 46 }

ciscoSlaSmartAgentNotifyReportingRequired NOTIFICATION-TYPE
    OBJECTS         {
                        ciscoSlaSUDIInfo,
                        ciscoSlaDaysReportingRequired
                    }
    STATUS          current
    DESCRIPTION
        "This notification is sent when a license is in use that was not
        purchased so reporting will be required at the time specified."
   ::= { ciscoSlaMIBNotifs 47 }
-- Smart License MIB Conformance Objects

ciscoSlaMIBConform  OBJECT IDENTIFIER
    ::= { ciscoSmartLicMIB 2 }

-- - Conformanc Compliance Objects

ciscoSlaMIBCompliances  OBJECT IDENTIFIER
    ::= { ciscoSlaMIBConform 1 }


ciscoSlaMIBCompliance MODULE-COMPLIANCE
    STATUS          current
    DESCRIPTION
        "Compliance statement for Cisco Smart license MIB."
    MODULE          -- this module
    MANDATORY-GROUPS {
                        ciscoSlaMIBEntitlementInfoGroup,
                        ciscoSlaMIBRegistrationStatusInfoGroup,
                        ciscoSlaMIBGlobalNotificationGroup,
                        ciscoSlaMIBAgentInfoGroup,
                        ciscoSlaMIBEntitlementNotifGroup,
                        ciscoSlaMIBNotificationEnableGroup,
                        ciscoSlaMIBAuthorizationInfoGroup,
                        ciscoSlaMIBDeRegistrationInfoGroup,
                        ciscoSlaMIBThirdPartyAndUtilityInfoGroup,
                        ciscoSlaMIBExportInfoGroup,
                        ciscoSlaMIBReportingInfoGroup
                    }
    ::= { ciscoSlaMIBCompliances 1 }
-- - Conformance Groups

ciscoSlaMIBGroups  OBJECT IDENTIFIER
    ::= { ciscoSlaMIBConform 2 }


ciscoSlaMIBEntitlementInfoGroup OBJECT-GROUP
    OBJECTS         {
                        ciscoSlaEntitlementRequestCount,
                        ciscoSlaEntitlementTag,
                        ciscoSlaEntitlementVersion,
                        ciscoSlaEntitlementEnforceMode,
                        ciscoSlaEntitlementFeatureName,
                        ciscoSlaEntitlementDescription,
                        ciscoSlaEntitlementExportAllowed
                    }
    STATUS          current
    DESCRIPTION
        "Collection of objects for Entitlements requested and their
        related information."
    ::= { ciscoSlaMIBGroups 1 }

ciscoSlaMIBRegistrationStatusInfoGroup OBJECT-GROUP
    OBJECTS         {
                        ciscoSlaRegistrationStatus,
                        ciscoSlaVirtualAccount,
                        ciscoSlaNextCertificateExpireTime,
                        ciscoSlaEnterpriseAccountName,
                        ciscoSlaRegisterInitTime,
                        ciscoSlaRegisterSuccess,
                        ciscoSlaRenewInitTime,
                        ciscoSlaRenewSuccess,
                        ciscoSlaRenewFailureReason,
                        ciscoSlaRenewNextRetryTime,
                        ciscoSlaRegisterFailureReason,
                        ciscoSlaRegisterNextRetryTime
                    }
    STATUS          current
    DESCRIPTION
        "Collection of objects representing the information regarding
        the registration status of the device."
    ::= { ciscoSlaMIBGroups 2 }

ciscoSlaMIBGlobalNotificationGroup NOTIFICATION-GROUP
   NOTIFICATIONS    {
                        ciscoSlaSmartAgentNotifyEnforcementMode,
                        ciscoSlaSmartAgentNotifyReady,
                        ciscoSlaSmartAgentNotifyEnabled,
                        ciscoSlaSmartAgentNotifyDisabled,
                        ciscoSlaSmartAgentNotifyRegisterFailed,
                        ciscoSlaSmartAgentNotifyRegisterSuccess,
                        ciscoSlaSmartAgentNotifyIdCertExpired,
                        ciscoSlaSmartAgentNotifyIdCertRenewSuccess,
                        ciscoSlaSmartAgentNotifyIdCertRenewFail,
                        ciscoSlaSmartAgentNotifyAuthRenewSuccess,
                        ciscoSlaSmartAgentNotifyAuthRenewFail,
                        ciscoSlaSmartAgentNotifyCommunicationFailure,
                        ciscoSlaSmartAgentNotifyCommunicationRestored,
                        ciscoSlaSmartAgentNotifyIdCertRenewNotStarted,
                        ciscoSlaSmartAgentNotifyIdCertOutOfRange,
                        ciscoSlaSmartAgentNotifySystemClockChanged,
                        ciscoSlaSmartAgentNotifyEvalExpiryWarning,
                        ciscoSlaSmartAgentNotifyEvalExpired,
                        ciscoSlaSmartAgentNotifyIdCertExpiryWarning,
                        ciscoSlaSmartAgentNotifyDeRegisterSuccess,
                        ciscoSlaSmartAgentNotifyDeRegisterFailed,
                        ciscoSlaSmartAgentNotifyThirdpartyModeEnabled,
                        ciscoSlaSmartAgentNotifyThirdpartyModeDisabled,
                        ciscoSlaSmartAgentNotifyUtilityCertExpired,
                        ciscoSlaSmartAgentNotifyUtilityCertRenewFailed,
                        ciscoSlaSmartAgentNotifyUtilityCertRenewSuccess,
                        ciscoSlaSmartAgentNotifyUtilityDataReportingStarted,
                        ciscoSlaSmartAgentNotifyUtilityDataReportingStopped,
                        ciscoSlaSmartAgentNotifyUtilitySendRUMFailed,
                        ciscoSlaSmartAgentNotifyUtilityCertFQDNMismatch,
                        ciscoSlaSmartAgentNotifySmartTransportNotConfigured,
                        ciscoSlaSmartAgentNotifyHostnameMatchedWithUDI,
                        ciscoSlaSmartAgentNotifyExportRequestFailure,
                        ciscoSlaSmartAgentNotifyExportHAMismatch,
                        ciscoSlaSmartAgentNotifyExportAuthKeyNotSupported,
                        ciscoSlaSmartAgentNotifyExportControlledTag,
                        ciscoSlaSmartAgentNotifyEndPointReset,
                        ciscoSlaSmartAgentNotifyExportRequestSuccess,
                        ciscoSlaSmartAgentNotifyAuthorizationInstall,
                        ciscoSlaSmartAgentNotifyAuthorizationRemove,
                        ciscoSlaSmartAgentNotifyPolicyInstalled,
                        ciscoSlaSmartAgentNotifyPolicyRemoved,
                        ciscoSlaSmartAgentNotifyRUMACKNotReceived,
                        ciscoSlaSmartAgentNotifyRUMACKReceived,
                        ciscoSlaSmartAgentNotifyAuthorizationInstallFailed,
                        ciscoSlaSmartAgentNotifyReportingRequired
                    }
    STATUS          current
    DESCRIPTION
        "A collection of global notifications related to Smart   Agent"
    ::= { ciscoSlaMIBGroups 3 }

ciscoSlaMIBAgentInfoGroup OBJECT-GROUP
    OBJECTS         {
                        ciscoSlaVersion,
                        ciscoSlaEnabled,
                        ciscoSlaSUDIInfo,
                        ciscoSlaInstanceId
                    }
    STATUS          current
    DESCRIPTION
        "Collection of objects representing meta data related to Smart
        Agent state"
    ::= { ciscoSlaMIBGroups 4 }

ciscoSlaMIBEntitlementNotifGroup NOTIFICATION-GROUP
   NOTIFICATIONS    { ciscoSlaSmartAgentNotifyEntitlementEnforceMode }
    STATUS          current
    DESCRIPTION
        "A collection of  notifications related to entitlement enforce
        mode in SmartAgent"
    ::= { ciscoSlaMIBGroups 5 }

ciscoSlaMIBNotificationEnableGroup OBJECT-GROUP
    OBJECTS         {
                        ciscoSlaGlobalNotifEnable,
                        ciscoSlaEntitlementNotifEnable
                    }
    STATUS          current
    DESCRIPTION
        "A collection of objects for controlling
        (enabling/disabling) license notifications to a management
        application."
    ::= { ciscoSlaMIBGroups 6 }

ciscoSlaMIBAuthorizationInfoGroup OBJECT-GROUP
    OBJECTS         {
                        ciscoSlaAuthExpireTime,
                        ciscoSlaAuthComplianceStatus,
                        ciscoSlaAuthOOCStartTime,
                        ciscoSlaAuthRenewInitTime,
                        ciscoSlaAuthRenewSuccess,
                        ciscoSlaAuthRenewFailureReason,
                        ciscoSlaAuthRenewNextRetryTime,
                        ciscoSlaAuthEvalPeriodInUse,
                        ciscoSlaAuthEvalExpiredTime,
                        ciscoSlaAuthEvalPeriodLeft
                    }
    STATUS          current
    DESCRIPTION
        "Collection of MIB objects representing the Authorization State
        of the Smart Agent."
    ::= { ciscoSlaMIBGroups 7 }

ciscoSlaMIBDeRegistrationInfoGroup OBJECT-GROUP
    OBJECTS         {
                        ciscoSlaFailureReason,
                        ciscoSlaDeRegisterFailureMsg
                    }
    STATUS          current
    DESCRIPTION
        "Collection of MIB objects representing de-registration
        related information of the Smart Agent."
    ::= { ciscoSlaMIBGroups 8 }

ciscoSlaMIBThirdPartyAndUtilityInfoGroup OBJECT-GROUP
    OBJECTS         { ciscoSlaThirdPartyAndUtilityFailureMsg }
    STATUS          current
    DESCRIPTION
        "Collection of MIB objects representing third party
        and utility related information of the Smart Agent."
    ::= { ciscoSlaMIBGroups 9 }

ciscoSlaMIBExportInfoGroup OBJECT-GROUP
    OBJECTS         {
                        ciscoSlaExportFailureReason,
                        ciscoSlaExportFailureMessage
                    }
    STATUS          current
    DESCRIPTION
        "Collection of MIB object representing Export related
        information for Smart Agent."
    ::= { ciscoSlaMIBGroups 10 }

ciscoSlaMIBReportingInfoGroup OBJECT-GROUP
    OBJECTS         {
                        ciscoSlaDaysRUMAckNotReceived,
                        ciscoSlaDaysReportingRequired
                    }
    STATUS          current
    DESCRIPTION
        "Please enter the description here"
    ::= { ciscoSlaMIBGroups 11 }

END
