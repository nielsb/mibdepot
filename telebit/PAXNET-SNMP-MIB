PAXNET-SNMP-MIB DEFINITIONS ::= BEGIN

    IMPORTS
	MODULE-IDENTITY
	    FROM SNMPv2-SMI
	RowStatus, StorageType, AutonomousType
	    FROM SNMPv2-TC
	SnmpAdminString, SnmpEngineID, snmpAuthProtocols, snmpPrivProtocols
	    FROM SNMP-FRAMEWORK-MIB
	usmUserEngineID, usmUserName, usmNoPrivProtocol, usmHMACMD5AuthProtocol
	    FROM SNMP-USER-BASED-SM-MIB
	paxnet,	paxManagement
	    FROM PAXNET-MIB;

    paxnetSNMPMIB MODULE-IDENTITY
		LAST-UPDATED "9903230000Z"

		ORGANIZATION "Telebit Communications A/S, Denmark"
		CONTACT-INFO
			"      "
		DESCRIPTION
			"MIB for management of SNMP for PAXNET routers"
		::= { paxManagement 5 }


    paxnetSNMP OBJECT IDENTIFIER ::= { paxnetSNMPMIB 1 }
    paxnetSNMPMIBConformance OBJECT IDENTIFIER ::= { paxnetSNMPMIB 2 }

    -- make space for several statistics

pusmUserTable     OBJECT-TYPE
    SYNTAX       SEQUENCE OF PUsmUserEntry
    MAX-ACCESS   not-accessible
    STATUS       current
    DESCRIPTION "The table of users configured in the SNMP engine's
                 Local Configuration Datastore (LCD)."
    ::= { paxnetSNMP 10 }

pusmUserEntry     OBJECT-TYPE
    SYNTAX       PUsmUserEntry
    MAX-ACCESS   not-accessible
    STATUS       current
    DESCRIPTION "A user configured in the SNMP engine's Local
                 Configuration Datastore (LCD) for the User-based
                 Security Model.
                "
    INDEX       { usmUserEngineID,
                  usmUserName
                }
    ::= { pusmUserTable 1 }

PUsmUserEntry ::= SEQUENCE
    {
        usmUserEngineID         SnmpEngineID,
        usmUserName             SnmpAdminString,
        pusmUserAuthProtocol    AutonomousType,
        pusmUserAuthKey         OCTET STRING,
        pusmUserAuthPassw       OCTET STRING,
        pusmUserPrivProtocol    AutonomousType,
        pusmUserPrivKey		OCTET STRING,
        pusmUserPrivPassw	OCTET STRING,
        pusmUserPublic          OCTET STRING,
        pusmUserStorageType     StorageType,
        pusmUserStatus          RowStatus
    }

pusmUserAuthProtocol OBJECT-TYPE
    SYNTAX       AutonomousType
    MAX-ACCESS   read-create
    STATUS       current
    DESCRIPTION "realizing usmUserAuthProtocol from the std MIB"
    DEFVAL      { usmHMACMD5AuthProtocol }
    ::= { pusmUserEntry 5 }

pusmUserAuthKey OBJECT-TYPE
    SYNTAX       OCTET STRING
    MAX-ACCESS   read-create
    STATUS       current
    DESCRIPTION "This is the real, unhidden, unencrypted value of the
		Authentication Key for this user"
    DEFVAL      { ''H }    -- the empty string
    ::= { pusmUserEntry 6 }

pusmUserAuthPassw OBJECT-TYPE
    SYNTAX       OCTET STRING
    MAX-ACCESS   read-create
    STATUS       current
    DESCRIPTION "This object can be written to update the AuthKey via the
		usual password-to-key algorithm.  Reading the object always
		returns the empty string"
    DEFVAL      { ''H }    -- the empty string
    ::= { pusmUserEntry 3 }

pusmUserPrivProtocol OBJECT-TYPE
    SYNTAX       AutonomousType
    MAX-ACCESS   read-create
    STATUS       current
    DESCRIPTION ""
    DEFVAL      { usmNoPrivProtocol }
    ::= { pusmUserEntry 8 }

pusmUserPrivKey OBJECT-TYPE
    SYNTAX       OCTET STRING (SIZE(0..32))
    MAX-ACCESS   read-create
    STATUS       current
    DESCRIPTION "The is the real, unencrypted key for the Privacy protocol"
    ::= { pusmUserEntry 9 }


pusmUserPrivPassw OBJECT-TYPE
    SYNTAX       OCTET STRING (SIZE(0..32))
    MAX-ACCESS   read-create
    STATUS       current
    DESCRIPTION "This object can be written to update the PrivKey via
		the usual password-to-key algorithm.  Reading the object
		always returns the empty string"
    ::= { pusmUserEntry 4 }


pusmUserPublic    OBJECT-TYPE
    SYNTAX       OCTET STRING (SIZE(0..32))
    MAX-ACCESS   read-create
    STATUS       current
    DESCRIPTION "A publicly-readable value which is written as part
                 of the procedure for changing a user's secret
                 authentication and/or privacy key, and later read to
                 determine whether the change of the secret was
                 effected.
                "
    DEFVAL      { ''H }  -- the empty string
    ::= { pusmUserEntry 11 }

pusmUserStorageType OBJECT-TYPE
    SYNTAX       StorageType
    MAX-ACCESS   read-create
    STATUS       current
    DESCRIPTION "The storage type for this conceptual row.

                 Conceptual rows having the value 'permanent'
                 must allow write-access at a minimum to:

                 - usmUserAuthKeyChange, usmUserOwnAuthKeyChange
                   and usmUserPublic for a user who employs
                   authentication, and
                 - usmUserPrivKeyChange, usmUserOwnPrivKeyChange
                   and usmUserPublic for a user who employs
                   privacy.

                 Note that any user who employs authentication or
                 privacy must allow its secret(s) to be updated and
                 thus cannot be 'readOnly'.
                "
    DEFVAL      { nonVolatile }
    ::= { pusmUserEntry 12 }

pusmUserStatus   OBJECT-TYPE
    SYNTAX       RowStatus
    MAX-ACCESS   read-create
    STATUS       current
    DESCRIPTION "The status of this conceptual row.

                 Until instances of all corresponding columns are
                 appropriately configured, the value of the
                 corresponding instance of the usmUserStatus column
                 is 'notReady'.

                 In particular, a newly created row cannot be made
                 active until the corresponding usmUserCloneFrom,
                 usmUserAuthKeyChange, usmUserOwnAuthKeyChange,
                 usmUserPrivKeyChange and usmUserOwnPrivKeyChange
                 have all been set.

                 The  RowStatus TC [RFC1903] requires that this
                 DESCRIPTION clause states under which circumstances
                 other objects in this row can be modified:

                 The value of this object has no effect on whether
                 other objects in this conceptual row can be modified.
                "
    ::= { pusmUserEntry 13 }


-- various constants

paxConstants OBJECT IDENTIFIER ::= { paxnet 4 }

paxSysObjects OBJECT IDENTIFIER ::= { paxConstants 1 }

paxSysObjectRel1v0 OBJECT-IDENTITY
    STATUS     current
    DESCRIPTION
	"Identifies the release 1.0 of the paxnet SNMP agent"
    ::= { paxSysObjects 1 }


paxDomains OBJECT IDENTIFIER ::= { paxConstants 3 }

paxTCPDomain OBJECT-IDENTITY
    STATUS current
    DESCRIPTION
        "The TCP/IPv4 domain; the transport address is encoded just like
	 for the SNMPUDPDomain"
    ::= { paxDomains 1 }

paxUDPv6Domain OBJECT-IDENTITY
    STATUS current
    DESCRIPTION
	"The UDP/IPv6 domain; the transport address encoded is an OCTET STRING
	 of SIZE 18, 16 bytes of IPv6 address and two bytes of port number"
    ::= { paxDomains 2 }

paxTCPv6Domain OBJECT-IDENTITY
    STATUS current
    DESCRIPTION
	"The TCP/IPv6 domain"
    ::= { paxDomains 3 }

paxnetSNMPMIBCompliances OBJECT IDENTIFIER ::= { paxnetSNMPMIBConformance 1 }
paxnetSNMPMIBGroups      OBJECT IDENTIFIER ::= { paxnetSNMPMIBConformance 2 }


-- compliance statements

paxnetSNMPMIBCompliance MODULE-COMPLIANCE
    STATUS  current
    DESCRIPTION
            "The compliance statement for a paxnet router."
    MODULE  -- this module
        MANDATORY-GROUPS { paxnetSNMPMIBGroup }

    ::= { paxnetSNMPMIBCompliances 1 }


-- units of conformance

paxnetSNMPMIBGroup OBJECT-GROUP
    OBJECTS { pusmUserAuthProtocol, pusmUserAuthKey, pusmUserPrivProtocol,
	pusmUserPrivKey, pusmUserPublic, pusmUserStorageType, pusmUserStatus }
    STATUS  current
    DESCRIPTION
            "A collection of objects to support management of the
	     snmp service of a Paxnet router."
    ::= { paxnetSNMPMIBGroups 2 }


END
