-- Module Name: HMS116R7.MIB (SCTE 84-2)

SCTE-HMS-HE-POWER-SUPPLY-MIB DEFINITIONS ::= BEGIN

IMPORTS
	OBJECT-TYPE, MODULE-IDENTITY, Unsigned32
		FROM SNMPv2-SMI
	OBJECT-GROUP, MODULE-COMPLIANCE
		FROM SNMPv2-CONF
	DisplayString
		FROM SNMPv2-TC
	hePowerSupply, HeTenthVolt, HeHundredthWatts, 
	HeMilliAmp
		FROM SCTE-HMS-HEADENDIDENT-MIB
	entPhysicalIndex
		FROM ENTITY-MIB;

hePowerSupplyMIB MODULE-IDENTITY
	LAST-UPDATED "200403250410Z"
	ORGANIZATION 
		"SCTE HMS Working Group"
	CONTACT-INFO 
		"SCTE HMS Subcommittee, Chairman
		             mail to: standards@scte.org"
	DESCRIPTION 
		"The MIB module is for representing a power supply present in the 
		            headend (or indoor) and supported by a SNMP agent."
::= { hePowerSupply 1 }

hePsMIBObjects       OBJECT IDENTIFIER ::= { hePowerSupplyMIB 1 }

-- Conformance Information

hePsMIBConformance   OBJECT IDENTIFIER ::= { hePowerSupplyMIB 2 }
hePsMIBCompliances   OBJECT IDENTIFIER ::= { hePsMIBConformance 1 }
hePsMIBGroups        OBJECT IDENTIFIER ::= { hePsMIBConformance 2 }

--          The Power Supply Unit Table

hePsUnitTable  OBJECT-TYPE
	SYNTAX SEQUENCE OF HePsUnitEntry
	MAX-ACCESS not-accessible
	STATUS     current
	DESCRIPTION 
		"A table containing information about headend (or indoor plant) 
		        power supplies. These power supplies could be, for example, 
		        plug-in modules for a chassis."
	::= { hePsMIBObjects 1 }

hePsUnitEntry  OBJECT-TYPE
	SYNTAX 	HePsUnitEntry
	MAX-ACCESS not-accessible
	STATUS     current
	DESCRIPTION 
		"Information about each Power Supply in the subsystem. Each Power Supply 
		         unit will have an entry in the Entity MIB supported for this agent."
	INDEX { entPhysicalIndex }
	::= { hePsUnitTable 1 }

HePsUnitEntry ::= SEQUENCE {
	hePsUnitCurrentIN
		HeMilliAmp,
	hePsUnitPowerIN
		HeHundredthWatts,
	hePsUnitDescription
		DisplayString,
	hePsUnitVoltageIN
		HeTenthVolt
}

hePsUnitCurrentIN  OBJECT-TYPE
	SYNTAX     HeMilliAmp
	UNITS 	"milliamperes"
	MAX-ACCESS read-only
	STATUS     current
	DESCRIPTION 
		"Scaled representation of the input current (AC or DC) for
		        this power supply.  This is an RMS value for AC currents.
		
		        This object must provide for the alarm management capabilities 
		        with a corresponding entry in the propertyTable of 
		        SCTE-HMS-PROPERTY-MIB (ANSI/SCTE 38-1).
		
		        An alarm shall be recorded as an entry in the currentAlarmTable
		        of SCTE-HMS-PROPERTY-MIB (ANSI/SCTE 38-1).
		
		        A log record shall be added as an entry in the heCommonLogTable.
		
		        An heCommonAlarmEvent notification shall be sent."
	::= { hePsUnitEntry 1 }

hePsUnitPowerIN  OBJECT-TYPE
	SYNTAX     HeHundredthWatts
	UNITS 	"hundredths of a watt"
	MAX-ACCESS read-only
	STATUS     current
	DESCRIPTION 
		"Scaled representation of the input power (AC or DC) for
		        this power supply.  This is an RMS value for AC powers.
		
		        This object must provide for the alarm management capabilities 
		        with a corresponding entry in the propertyTable of 
		        SCTE-HMS-PROPERTY-MIB (ANSI/SCTE 38-1).
		
		        An alarm shall be recorded as an entry in the currentAlarmTable
		        of SCTE-HMS-PROPERTY-MIB (ANSI/SCTE 38-1).
		
		        A log record shall be added as an entry in the heCommonLogTable.
		
		        An heCommonAlarmEvent notification shall be sent."
	::= { hePsUnitEntry 2 }

hePsUnitDescription  OBJECT-TYPE
	SYNTAX     DisplayString
	MAX-ACCESS read-only
	STATUS     current
	DESCRIPTION 
		"This string will describe the model type of the Power Supply.
		        Examples are AC+110, AC+220, DC-48, DC+48. This model type should
		        match the entry in the Entity mib for this object."
	::= { hePsUnitEntry 3 }

hePsUnitVoltageIN  OBJECT-TYPE
	SYNTAX     HeTenthVolt
	UNITS 	"tenths of a volt"
	MAX-ACCESS read-only
	STATUS     current
	DESCRIPTION 
		"Scaled representation of the input voltage (AC or DC) for
		        this power supply.  This is an RMS value for AC voltages.
		
		        This object must provide for the alarm management capabilities 
		        with a corresponding entry in the propertyTable of 
		        SCTE-HMS-PROPERTY-MIB (ANSI/SCTE 38-1).
		
		        An alarm shall be recorded as an entry in the currentAlarmTable
		        of SCTE-HMS-PROPERTY-MIB (ANSI/SCTE 38-1).
		
		        A log record shall be added as an entry in the heCommonLogTable.
		
		        An heCommonAlarmEvent notification shall be sent."
	::= { hePsUnitEntry 4 }

--          The Power Supply Output Table

hePsOutputTable  OBJECT-TYPE
	SYNTAX SEQUENCE OF HePsOutputEntry
	MAX-ACCESS not-accessible
	STATUS     current
	DESCRIPTION 
		"A list of monitorable parameter entries for power supply 
		         outputs."
	::= { hePsMIBObjects 2 }

hePsOutputEntry  OBJECT-TYPE
	SYNTAX 	HePsOutputEntry
	MAX-ACCESS not-accessible
	STATUS     current
	DESCRIPTION 
		"An entry containing management information applicable to
		         a particular power supplies outputs."
	INDEX { entPhysicalIndex, 
		hePsOutputIndex }
	::= { hePsOutputTable 1 }

HePsOutputEntry ::= SEQUENCE {
	hePsOutputIndex
		Unsigned32,
	hePsOutputVoltage
		HeTenthVolt,
	hePsOutputCurrent
		HeMilliAmp,
	hePsOutputPower
		HeHundredthWatts
}

hePsOutputIndex  OBJECT-TYPE
	SYNTAX     Unsigned32
	MAX-ACCESS not-accessible
	STATUS     current
	DESCRIPTION 
		"An arbitrary value which uniquely identifies each entry."
	::= { hePsOutputEntry 1 }

hePsOutputVoltage  OBJECT-TYPE
	SYNTAX     HeTenthVolt
	UNITS 	"tenths of a volt"
	MAX-ACCESS read-only
	STATUS     current
	DESCRIPTION 
		"Scaled representation of the output voltage for this power supply output.
		
		        If a single PHYSICAL power supply provides multiple voltages, each voltage 
		        shall have its own entry in this table.
		
		        This object must provide for the alarm management capabilities
		        with a corresponding entry in the propertyTable of
		        SCTE-HMS-PROPERTY-MIB (ANSI/SCTE 38-1).
		
		        An alarm shall be recorded as an entry in the currentAlarmTable
		        of SCTE-HMS-PROPERTY-MIB (ANSI/SCTE 38-1).  
		
		        A log record shall be added as an entry in the heCommonLogTable.
		
		        An heCommonAlarmEvent notification shall be sent."
	::= { hePsOutputEntry 2 }

hePsOutputCurrent  OBJECT-TYPE
	SYNTAX     HeMilliAmp
	UNITS 	"milliamperes"
	MAX-ACCESS read-only
	STATUS     current
	DESCRIPTION 
		"Scaled representation of the output current for this power supply output.
		
		        This object must provide for the alarm management capabilities 
		        with a corresponding entry in the propertyTable of 
		        SCTE-HMS-PROPERTY-MIB (ANSI/SCTE 38-1).
		
		        An alarm shall be recorded as an entry in the currentAlarmTable
		        of SCTE-HMS-PROPERTY-MIB (ANSI/SCTE 38-1).  
		
		        A log record shall be added as an entry in the heCommonLogTable.
		
		        An heCommonAlarmEvent notification shall be sent."
	::= { hePsOutputEntry 3 }

hePsOutputPower  OBJECT-TYPE
	SYNTAX     HeHundredthWatts
	UNITS 	"hundredths of a watt"
	MAX-ACCESS read-only
	STATUS     current
	DESCRIPTION 
		"Scaled representation of the output power for this power supply output.
		
		        This object must provide for the alarm management capabilities 
		        with a corresponding entry in the propertyTable of 
		        SCTE-HMS-PROPERTY-MIB (ANSI/SCTE 38-1).
		
		        An alarm shall be recorded as an entry in the currentAlarmTable
		        of SCTE-HMS-PROPERTY-MIB (ANSI/SCTE 38-1).
		
		        A log record shall be added as an entry in the heCommonLogTable.
		
		        An heCommonAlarmEvent notification shall be sent."
	::= { hePsOutputEntry 4 }

-- Compliance statements

hePsCompliance  MODULE-COMPLIANCE
	STATUS     current
	DESCRIPTION 
		"The minimum compliance statement for indoor power supplies."
	MODULE
		MANDATORY-GROUPS { hePsOutputMandatoryGroup } 
		GROUP hePsUnitGroup
		DESCRIPTION 
		"The hePsUnitGroup is unconditionally optional."
		GROUP hePsOutputGroup
		DESCRIPTION 
		"The hePsOutputGroup is unconditionally optional."
	::= { hePsMIBCompliances 1 }

-- this module

hePsOutputMandatoryGroup  OBJECT-GROUP
	OBJECTS { hePsOutputVoltage }
	STATUS     current
	DESCRIPTION 
		"A mandatory collection of objects that provide information
		        applicable to a particular power supply's output
		        parameters."
	::= { hePsMIBGroups 1 }

hePsUnitGroup  OBJECT-GROUP
	OBJECTS { hePsUnitVoltageIN, 
		hePsUnitCurrentIN, 
		hePsUnitPowerIN, 
		hePsUnitDescription }
	STATUS     current
	DESCRIPTION 
		"A collection of objects that provide information applicable to a 
		        particular power supply's input parameters."
	::= { hePsMIBGroups 2 }

hePsOutputGroup  OBJECT-GROUP
	OBJECTS { hePsOutputCurrent, 
		hePsOutputPower }
	STATUS     current
	DESCRIPTION 
		"A collection of objects that provide information applicable to a 
		        particular power supply's output parameters."
	::= { hePsMIBGroups 3 }
END
