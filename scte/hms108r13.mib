-- Module Name: HMS108R13.MIB (SCTE 83-1)
-- SCTE Status: Adopted

SCTE-HMS-HE-OPTICS-MIB DEFINITIONS ::= BEGIN

IMPORTS
    OBJECT-IDENTITY, MODULE-IDENTITY
        FROM SNMPv2-SMI
    heOptics
        FROM SCTE-HMS-HEADENDIDENT-MIB;

heOpticsMib MODULE-IDENTITY
    LAST-UPDATED "200603030000Z" -- March 3, 2006
    ORGANIZATION "SCTE HMS Working Group"
    CONTACT-INFO
            " SCTE HMS Subcommittee, Chairman
              mailto:standards@scte.org
            "
    DESCRIPTION
            "The MIB module provides the branch object identifiers for the
            headend optics MIBs within the SCTE HMS Headend subtree."

    REVISION "200603030000Z" -- March 3, 2006
     DESCRIPTION
            "Corrected Last-Updated date, date format and and revision order"

    REVISION "200601100000Z" -- January  10, 2006
     DESCRIPTION
            "Corrected Revision in Header and typo that prevented the MIB from Compiling"

    REVISION "200511090000Z" -- November 09, 2005
     DESCRIPTION
            "Added heOpticalTransportGroup as a branch identifier."

    ::= { heOptics 0 }

-- Registration subtree for headend optical equipment

heOpticalTransmitterGroup OBJECT-IDENTITY
    STATUS current
    DESCRIPTION
            "Defines the base OID for the inside plant
            optical transmitters (see SCTE 85-1; formerly HMS112)."
    ::= { heOptics 1 }

heOpticalReceiverGroup OBJECT-IDENTITY
    STATUS current
    DESCRIPTION
            "Defines the base OID for the inside plant
            optical receivers (see SCTE 85-2; formerly HMS113)."
    ::= { heOptics 2 }

heOpticalAmplifierGroup OBJECT-IDENTITY
    STATUS current
    DESCRIPTION
            "Defines the base OID for the inside plant
            optical amplifiers (see SCTE 85-3; formerly HMS118)."
    ::= { heOptics 3 }

heOpticalSwitchGroup OBJECT-IDENTITY
    STATUS current
    DESCRIPTION
            "Defines the base OID for the inside plant
            optical switches (see SCTE 85-4; formerly HMS119)."
    ::= { heOptics 4 }

heOpticalTransportGroup OBJECT-IDENTITY
    STATUS current
    DESCRIPTION
            "Defines the base OID for the inside plant
            optical transport equipment such as a 10GbE Aggregator."
    ::= { heOptics 5 }

END
