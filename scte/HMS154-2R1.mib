SCTE-HMS-QAM-MIB DEFINITIONS ::= BEGIN

IMPORTS
	OBJECT-TYPE, OBJECT-IDENTITY, MODULE-IDENTITY, 
	enterprises, IpAddress, Integer32, Unsigned32
		FROM SNMPv2-SMI
	OBJECT-GROUP, MODULE-COMPLIANCE
		FROM SNMPv2-CONF
	entPhysicalIndex
		FROM ENTITY-MIB
	ifIndex
		FROM IF-MIB
	InetAddressType, InetAddress
		FROM INET-ADDRESS-MIB
	QAMChannelModulationFormat
	    FROM SCTE-HMS-HEADENDIDENT-TC-MIB;

heDigitalQamMIB MODULE-IDENTITY
	LAST-UPDATED "200710021200Z"
	ORGANIZATION 
		"SCTE HMS Working Group"
	CONTACT-INFO 
		"SCTE HMS Subcommittee, Chairman
		mailto:standards@scte.org "
	DESCRIPTION 
		"This MIB module is for representing Edge QAM equipment present 
                 in the headend (or indoor) and is supported by a SNMP agent.
                 It defines QAM channel related configuration MIB objects 
                 associated with both QAM channel's physical and logical characteristics.
                 
                 qamChannelTable is optional for devices that are supporting 
                 equivalent DOCSIS MIB objects.

                 qamConfigTable is optional and applies to devices wish to 
                 provide logical level configuration. "  

      REVISION "200710031700Z"
	DESCRIPTION 
		" Added SCTE-HMS-HEADENDIDENT-TC name to file. Added QAMModulationFormat
            textual convention"
            
      REVISION "200710021200Z"
	DESCRIPTION 
		" Prepare MIB for ballot"
      
::= { enterprises scteRoot(5591) scteHmsTree(1) insidePlantIdent(11) heDigital(5) heDigitalQamGroups(4) 1 }


-- 
-- Node definitions
-- 
qamMIBObjects  OBJECT-IDENTITY
	STATUS     current
	DESCRIPTION 
		"This branch specifies the QAM MIB objects."
	::= { heDigitalQamMIB 1 }

qamMIBConformance  OBJECT-IDENTITY
	STATUS     current
	DESCRIPTION 
		"This branch describes the different QAM MIB object groups and 
		the different level of compliance."
	::= { heDigitalQamMIB 2 }

qamMIBCompliances  OBJECT-IDENTITY
	STATUS     current
	DESCRIPTION 
		"The different levels of compliance to the QAM MIB."
	::= { qamMIBConformance 1 }

qamMIBGroups  OBJECT-IDENTITY
	STATUS     current
	DESCRIPTION 
		"The QAM MIB object groups."
	::= { qamMIBConformance 2 }

qamChannelTable  OBJECT-TYPE
	SYNTAX SEQUENCE OF QamChannelEntry
	MAX-ACCESS not-accessible
	STATUS     current
	DESCRIPTION 
		"This table describes the configuration and attributes of each
		QAM channel of the QAM designated by ifIndex."
	::= { qamMIBObjects 1 }

qamChannelEntry  OBJECT-TYPE
	SYNTAX 	QamChannelEntry
	MAX-ACCESS not-accessible
	STATUS     current
	DESCRIPTION 
		"There is an entry in the table for each QAM channel. The index 
		to this table is the ifIndex of each QAM channel."
	INDEX { ifIndex }
	::= { qamChannelTable 1 }

QamChannelEntry ::= SEQUENCE {
	qamChannelFrequency
		Unsigned32,
	qamChannelModulationFormat
		QAMChannelModulationFormat,
	qamChannelInterleaverLevel
		INTEGER,
	qamChannelInterleaverMode
		INTEGER,
	qamChannelPower
		Integer32,
	qamChannelSquelch
		INTEGER,
	qamChannelContWaveMode
		INTEGER,
	qamChannelAnnexMode
		INTEGER
}

qamChannelFrequency  OBJECT-TYPE
	SYNTAX     Unsigned32
	UNITS 	"100 Hertz"
	MAX-ACCESS read-only
	STATUS     current
	DESCRIPTION 
		"The center frequency of the QAM channel."
	::= { qamChannelEntry 1 }

qamChannelModulationFormat  OBJECT-TYPE
	SYNTAX     QAMChannelModulationFormat
	MAX-ACCESS read-only
	STATUS     current
	DESCRIPTION 
		"RF Modululation for this output QAM channel when 
		qamChannelContWaveMode is off."
	::= { qamChannelEntry 2 }

qamChannelInterleaverLevel  OBJECT-TYPE
	SYNTAX     INTEGER {
		level1 (1),
		level2 (2)
	}
	MAX-ACCESS read-only
	STATUS     current
	DESCRIPTION 
		"The interleaver level for FEC coding. 
		
		level1 - implies interleaver level 1
		level2 - implies interleaver level 2
		
		This object is only valid when AnnexMode has the value annexB."
	::= { qamChannelEntry 3 }

qamChannelInterleaverMode  OBJECT-TYPE
	SYNTAX     INTEGER {
		fecI128J1 (1),
		fecI128J2 (2),
		fecI64J2 (3),
		fecI128J3 (4),
		fecI32J4 (5),
		fecI128J4 (6),
		fecI16J8 (7),
		fecI128J5 (8),
		fecI8J16 (9),
		fecI128J6 (10),
		fecI128J7 (12),
		fecI128J8 (14)
	}
	MAX-ACCESS read-only
	STATUS     current
	DESCRIPTION 
		"The interleaving depth or operation mode of the interleaver.
		
		fecI128J1 - FEC_I_128_J_1,
		fecI128J2 - FEC_I_128_J_2,
		fecI64J2 - FEC_I_64_J_2,
		fecI128J3 - FEC_I_128_J_3,
		fecI32J4 - FEC_I_32_J_4,
		fecI128J4 - FEC_I_128_J_4,
		fecI16J8 - FEC_I_16_J_8,
		fecI128J5 - FEC_I_128_J_5,
		fecI8J16 - FEC_I_8_J_16,
		fecI128J6 - FEC_I_128_J_6,
		fecI128J7 - FEC_I_128_J_7,
		fecI128J8 - FEC_I_128_J_8
		
		When the qamChannelInterleaverLevel is set to 'level 1', a 
		single interleaving depth is supported, namely 'fecI128J1'.
		
		When the qamChannelInterleaverLevel is set to 'level2', all the 
		other interleaving depths are also supported.
		
		This object is only valid when AnnexMode has the value annexB."
	REFERENCE 
		"ITU-T J.83 Annex B."
	::= { qamChannelEntry 4 }

qamChannelPower  OBJECT-TYPE
	SYNTAX     Integer32
	UNITS 	"0.1 dBmV"
	MAX-ACCESS read-only
	STATUS     current
	DESCRIPTION 
		"The output power of the QAM channel. If the QAM is muted, this 
		object is set to 0."
	::= { qamChannelEntry 5 }

qamChannelSquelch  OBJECT-TYPE
	SYNTAX     INTEGER {
		unmuted (1),
		muted (2)
	}
	MAX-ACCESS read-only
	STATUS     current
	DESCRIPTION 
		"Indicates whether the QAM port is muted or not."
	::= { qamChannelEntry 6 }

qamChannelContWaveMode  OBJECT-TYPE
	SYNTAX     INTEGER {
		cwmOff (1),
		cwmOn (2)
	}
	MAX-ACCESS read-only
	STATUS     current
	DESCRIPTION 
		"Indicates whether Continuous Wave mode is enabled or not for
		output."
	::= { qamChannelEntry 7 }

qamChannelAnnexMode  OBJECT-TYPE
	SYNTAX     INTEGER {
		annexA (1),
		annexB (2),
		annexC (3),
		other (4)
	}
	MAX-ACCESS read-only
	STATUS     current
	DESCRIPTION 
		"Specifies the ITU-T standard supported by the QAM channel
		
		annexA - standard specified by Annex A of ITU-T J.83
		annexB - standard specified by Annex B of ITU-T J.83
		annexC - standard specified by Annex C of ITU-T J.83
		Other  - other standard that may apply."
	::= { qamChannelEntry 8 }

qamChannelCommonTable  OBJECT-TYPE
	SYNTAX SEQUENCE OF QamChannelCommonEntry
	MAX-ACCESS not-accessible
	STATUS     current
	DESCRIPTION 
		"This table decribes MPEG and DOCSIS characteristics that are
		not part of the DOCSIS-IF-MIB."
	::= { qamMIBObjects 2 }

qamChannelCommonEntry  OBJECT-TYPE
	SYNTAX 	QamChannelCommonEntry
	MAX-ACCESS not-accessible
	STATUS     current
	DESCRIPTION 
		"Each entry of this table describes attributes of an RF channel
		for both MPEG and DOCSIS QAMs."
	INDEX { ifIndex }
	::= { qamChannelCommonTable 1 }

QamChannelCommonEntry ::= SEQUENCE {
	qamChannelOutputBw
		Integer32,
	qamChannelUtilization
		Unsigned32
}

qamChannelOutputBw  OBJECT-TYPE
	SYNTAX     Integer32
	MAX-ACCESS read-only
	STATUS     current
	DESCRIPTION 
		"The QAM channel output bandwidth or capacity."
	::= { qamChannelCommonEntry 1 }

qamChannelUtilization  OBJECT-TYPE
	SYNTAX     Unsigned32 (0..1000)
	UNITS 	"0.1 %"
	MAX-ACCESS read-only
	STATUS     current
	DESCRIPTION 
		"The utilization of the QAM channel in percentage.
		This rate may be calculated as
		transport stream packets / 
		( transport stream packets + null packets )."
	::= { qamChannelCommonEntry 2 }

qamConfigTable  OBJECT-TYPE
	SYNTAX SEQUENCE OF QamConfigEntry
	MAX-ACCESS not-accessible
	STATUS     current
	DESCRIPTION 
		"This table is designed to show the IP addresses configuration
		for the QAM channels, optionally UDP port range, Program Number
		range associated with QAM channels. Configuring these parameters
		is necessary when performing session-based provisioning. A  
		session-based provisioning request must conform to the
		configurations in this table. The QAM channels within an QAM 
		device may be partitioned to support multiple UDP, QAM or
		ProgramNo ranges. Though it's helpful to partition the QAM
		channels when the total number of QAM channel increases, this is
		not a must. This table may also be used to show the reserved UDP
		ports, or program numbers for special purposes instead of using
		default ones allowed by hardware, software, or MPEG protocol."
	::= { qamMIBObjects 3 }

qamConfigEntry  OBJECT-TYPE
	SYNTAX 	QamConfigEntry
	MAX-ACCESS not-accessible
	STATUS     current
	DESCRIPTION 
		"Each entry corresponds to the configuration of a QAM channel
		range."
	INDEX { entPhysicalIndex,qamConfigIndex }
	::= { qamConfigTable 1 }

QamConfigEntry ::= SEQUENCE {
	qamConfigIndex
		Unsigned32,
	qamConfigQamChannelIdMin
		Integer32,
	qamConfigQamChannelIdMax
		Integer32,
	qamConfigIPAddrType
		InetAddressType,
	qamConfigIPAddr
		InetAddress,
	qamConfigUdpPortRangeMin
		Integer32,
	qamConfigUdpPortRangeMax
		Integer32,
	qamConfigOutputProgNoMin
		Integer32,
	qamConfigOutputProgNoMax
		Integer32
}

qamConfigIndex  OBJECT-TYPE
	SYNTAX     Unsigned32
	MAX-ACCESS not-accessible
	STATUS     current
	DESCRIPTION 
		"The table index."
	::= { qamConfigEntry 1 }

qamConfigQamChannelIdMin  OBJECT-TYPE
	SYNTAX     Integer32
	MAX-ACCESS read-only
	STATUS     current
	DESCRIPTION 
		"QAMChannelId maybe within a line card or global depending on
		qamConfigQamEntPhyIndex."
			DEFVAL { 1 }
	::= { qamConfigEntry 3 }

qamConfigQamChannelIdMax  OBJECT-TYPE
	SYNTAX     Integer32
	MAX-ACCESS read-only
	STATUS     current
	DESCRIPTION 
		"QAMChannelId maybe within a line card or global depending on
		qamConfigQamEntPhyIndex."
	::= { qamConfigEntry 4 }

qamConfigIPAddrType  OBJECT-TYPE
	SYNTAX     InetAddressType
	MAX-ACCESS read-only
	STATUS     current
	DESCRIPTION 
		"The type of the program destination address as defined by 
		inetAddressType. The default value is 1 for ipv4(1)"
			DEFVAL { ipv4 }
	::= { qamConfigEntry 5 }

qamConfigIPAddr  OBJECT-TYPE
	SYNTAX     InetAddress
	MAX-ACCESS read-only
	STATUS     current
	DESCRIPTION 
		"IP address of the QAM channel."
	::= { qamConfigEntry 6 }

qamConfigUdpPortRangeMin  OBJECT-TYPE
	SYNTAX     Integer32 (0..65535)
	MAX-ACCESS read-only
	STATUS     current
	DESCRIPTION 
		"The lowest UDP port of the UDP port range that can be used
		on this QAM channel."
	::= { qamConfigEntry 7 }

qamConfigUdpPortRangeMax  OBJECT-TYPE
	SYNTAX     Integer32 (0..65535)
	MAX-ACCESS read-only
	STATUS     current
	DESCRIPTION 
		"The highest UDP port of the UDP port range that can be used on
		this QAM channel."
	::= { qamConfigEntry 8 }

qamConfigOutputProgNoMin  OBJECT-TYPE
	SYNTAX     Integer32 (1..65535)
	MAX-ACCESS read-only
	STATUS     current
	DESCRIPTION 
		"The lowest MPEG output program number that can be used on the
		QAM channel."
			DEFVAL { 1 }
	::= { qamConfigEntry 9 }

qamConfigOutputProgNoMax  OBJECT-TYPE
	SYNTAX     Integer32 (1..65535)
	MAX-ACCESS read-only
	STATUS     current
	DESCRIPTION 
		"The highest MPEG output program number that can be used on the
		QAM channel."
			DEFVAL { 255 }
	::= { qamConfigEntry 10 }

qamSupport  MODULE-COMPLIANCE
	STATUS     current
	DESCRIPTION 
		"These objects describe the support level for QAM."
	MODULE
		MANDATORY-GROUPS { qamChannelGroup } 
		GROUP qamConfigGroup
		DESCRIPTION 
		"The qamConfigGroup is unconditionally optional"
	::= { qamMIBCompliances 1 }

docsisSupport  MODULE-COMPLIANCE
	STATUS     current
	DESCRIPTION 
		"These objects are not covered by any DOCSIS MIB, but
		they would need to be supported by a DOCSIS EQAM."
	MODULE
		MANDATORY-GROUPS { qamMpegDocsisCommonGroup } 
	::= { qamMIBCompliances 2 }

qamMpegDocsisCommonGroup  OBJECT-GROUP
	OBJECTS { qamChannelOutputBw, 
		qamChannelUtilization }
	STATUS     current
	DESCRIPTION 
		"These objects are not covered by any DOCSIS MIB. It is
		legitimate for a DOCSIS QAM to support them."
	::= { qamMIBGroups 1 }

qamChannelGroup  OBJECT-GROUP
	OBJECTS { qamChannelFrequency, 
		qamChannelModulationFormat, 
		qamChannelInterleaverLevel, 
		qamChannelInterleaverMode, 
		qamChannelPower, 
		qamChannelSquelch, 
		qamChannelContWaveMode, 
		qamChannelAnnexMode }
	STATUS     current
	DESCRIPTION 
		"The objects characterizing the RF channel and that may be
		supported by an equivalent DOCSIS MIB object."
	::= { qamMIBGroups 2 }

qamConfigGroup  OBJECT-GROUP
	OBJECTS { qamConfigQamChannelIdMin, 
		qamConfigQamChannelIdMax, 
		qamConfigIPAddrType, 
		qamConfigIPAddr, 
		qamConfigUdpPortRangeMin, 
		qamConfigUdpPortRangeMax, 
		qamConfigOutputProgNoMin, 
		qamConfigOutputProgNoMax }
	STATUS     current
	DESCRIPTION 
		"QAM configuration objects."
	::= { qamMIBGroups 3 }
END
