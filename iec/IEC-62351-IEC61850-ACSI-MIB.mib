IEC-62351-IEC61850-ACSI-MIB DEFINITIONS ::= BEGIN
    IMPORTS
    MODULE-IDENTITY,  OBJECT-IDENTITY,
    OBJECT-TYPE, Counter32, Integer32, Unsigned32, 
    Gauge32, TimeTicks, NOTIFICATION-TYPE 
        FROM SNMPv2-SMI
    TEXTUAL-CONVENTION, DisplayString, TruthValue,
    MacAddress, PhysAddress, DateAndTime
        FROM SNMPv2-TC
    OBJECT-GROUP, NOTIFICATION-GROUP, MODULE-COMPLIANCE
        FROM SNMPv2-CONF
    Float32TC 
		FROM FLOAT-TC-MIB
	AppDatStKind, PhyHealthKind, ExtKind,
    IntKind, LnkKind, PSPAccKind, ProtIdKind, EventKind,
    TimSyncIssueKind, SecurityProfileKind, TimSyncSrcKind FROM
    IEC-62351-ENUM-MIB
    InetAddressType, InetAddress
        FROM INET-ADDRESS-MIB;
		
    acsi-agent MODULE-IDENTITY
        LAST-UPDATED        "201706061000Z"
        ORGANIZATION        "IEC"
        CONTACT-INFO        "IEC TC57 WG15"
        DESCRIPTION         "Copyright (C) IEC. This version of this MIB module is part
                             of IEC 57-62351-7-Ed1. 
                             See the IEC 57-62351-7-Ed1 for full legal notices. 
                             As shown in Figure 20, the ACSI package includes
                             the IEC 61850 Abstract Communication Service
                             Interface (ACSI) classes."

        REVISION            "201706061000Z"
        DESCRIPTION         "IEC 57-62351-7-Ed1"

        ::= { iec61850 1 }

	standard  OBJECT IDENTIFIER ::= { iso 0 }
		
	iec62351  OBJECT IDENTIFIER ::= { standard 62351 } 

	part7  OBJECT IDENTIFIER ::= { iec62351 7 } 

	application  OBJECT IDENTIFIER ::= { part7 3 } 

	iec61850  OBJECT IDENTIFIER ::= { application 2 } 

	
		

          
		
    acsi OBJECT-IDENTITY
        STATUS              current
        DESCRIPTION         "The ACSISummary class includes the attributes
                             which define the information about the overall IEC
                             61850 stack running on the device ACSI."
        ::= { acsi-agent 1 }

    aCSIassocPoolMax OBJECT-TYPE
        SYNTAX              Integer32
        MAX-ACCESS          read-only
        STATUS              current
        DESCRIPTION         "ACSI::ACSISummary.assocPoolMax"
        ::= { acsi 1 }

    aCSIassocPoolUsed OBJECT-TYPE
        SYNTAX              Integer32
        MAX-ACCESS          read-only
        STATUS              current
        DESCRIPTION         "ACSI::ACSISummary.assocPoolUsed"
        ::= { acsi 2 }

    aCSICntRsTs OBJECT-TYPE
        SYNTAX              DateAndTime
        MAX-ACCESS          read-only
        STATUS              current
        DESCRIPTION         "ACSI::ACSISummary.CntRs - timestamp"
        ::= { acsi 3 }

    aCSICntRs OBJECT-TYPE
        SYNTAX              TruthValue
        MAX-ACCESS          read-write
        STATUS              current
        DESCRIPTION         "ACSI::ACSISummary.CntRs"
        ::= { acsi 4 }

    aCSICtrlPrivFailCntTs OBJECT-TYPE
        SYNTAX              DateAndTime
        MAX-ACCESS          read-only
        STATUS              current
        DESCRIPTION         "ACSI::ACSISummary.CtrlPrivFailCnt -
                             timestamp"
        ::= { acsi 5 }

    aCSICtrlPrivFailCnt OBJECT-TYPE
        SYNTAX              Counter32 
        MAX-ACCESS          read-only
        STATUS              current
        DESCRIPTION         "ACSI::ACSISummary.CtrlPrivFailCnt"
        ::= { acsi 6 }

    aCSIgsePubMax OBJECT-TYPE
        SYNTAX              Integer32
        MAX-ACCESS          read-only
        STATUS              current
        DESCRIPTION         "ACSI::ACSISummary.gsePubMax"
        ::= { acsi 7 }

    aCSIgsePubUsed OBJECT-TYPE
        SYNTAX              Integer32
        MAX-ACCESS          read-only
        STATUS              current
        DESCRIPTION         "ACSI::ACSISummary.gsePubUsed"
        ::= { acsi 8 }

    aCSIgseSubMax OBJECT-TYPE
        SYNTAX              Integer32
        MAX-ACCESS          read-only
        STATUS              current
        DESCRIPTION         "ACSI::ACSISummary.gseSubMax"
        ::= { acsi 9 }

    aCSIgseSubUsed OBJECT-TYPE
        SYNTAX              Integer32
        MAX-ACCESS          read-only
        STATUS              current
        DESCRIPTION         "ACSI::ACSISummary.gseSubUsed"
        ::= { acsi 10 }

    aCSILastEventTs OBJECT-TYPE
        SYNTAX              DateAndTime
        MAX-ACCESS          read-only
        STATUS              current
        DESCRIPTION         "ACSI::ACSISummary.LastEvent - timestamp"
        ::= { acsi 11 }

    aCSILastEvent OBJECT-TYPE
        SYNTAX              EventKind
        MAX-ACCESS          read-only
        STATUS              current
        DESCRIPTION         "ACSI::ACSISummary.LastEvent"
        ::= { acsi 12 }

    aCSIPrivFailCntTs OBJECT-TYPE
        SYNTAX              DateAndTime
        MAX-ACCESS          read-only
        STATUS              current
        DESCRIPTION         "ACSI::ACSISummary.PrivFailCnt - timestamp"
        ::= { acsi 13 }

    aCSIPrivFailCnt OBJECT-TYPE
        SYNTAX              Counter32 
        MAX-ACCESS          read-only
        STATUS              current
        DESCRIPTION         "ACSI::ACSISummary.PrivFailCnt"
        ::= { acsi 14 }

    aCSIRemoteEstAssocCntTs OBJECT-TYPE
        SYNTAX              DateAndTime
        MAX-ACCESS          read-only
        STATUS              current
        DESCRIPTION         "ACSI::ACSISummary.RemoteEstAssocCnt -
                             timestamp"
        ::= { acsi 15 }

    aCSIRemoteEstAssocCnt OBJECT-TYPE
        SYNTAX              Counter32 
        MAX-ACCESS          read-only
        STATUS              current
        DESCRIPTION         "ACSI::ACSISummary.RemoteEstAssocCnt"
        ::= { acsi 16 }

    aCSIAcsCtlFailTs OBJECT-TYPE
        SYNTAX              DateAndTime
        MAX-ACCESS          read-only
        STATUS              current
        DESCRIPTION         "ACSI::ACSISummary.AcsCtlFail - timestamp"
        ::= { acsi 17 }

    aCSIAcsCtlFail OBJECT-TYPE
        SYNTAX              Counter32 
        MAX-ACCESS          read-only
        STATUS              current
        DESCRIPTION         "ACSI::ACSISummary.AcsCtlFail"
        ::= { acsi 18 }

    aCSIsvPubMax OBJECT-TYPE
        SYNTAX              Integer32
        MAX-ACCESS          read-only
        STATUS              current
        DESCRIPTION         "ACSI::ACSISummary.svPubMax"
        ::= { acsi 19 }

    aCSIsvPubUsed OBJECT-TYPE
        SYNTAX              Integer32
        MAX-ACCESS          read-only
        STATUS              current
        DESCRIPTION         "ACSI::ACSISummary.svPubUsed"
        ::= { acsi 20 }

    aCSIsvSubMax OBJECT-TYPE
        SYNTAX              Integer32
        MAX-ACCESS          read-only
        STATUS              current
        DESCRIPTION         "ACSI::ACSISummary.svSubMax"
        ::= { acsi 21 }

    aCSIsvSubUsed OBJECT-TYPE
        SYNTAX              Integer32
        MAX-ACCESS          read-only
        STATUS              current
        DESCRIPTION         "ACSI::ACSISummary.svSubUsed"
        ::= { acsi 22 }

    acsi-agentGroupOptional OBJECT-GROUP 
	OBJECTS {
	               aCSIassocPoolMax,
               aCSIassocPoolUsed,
               aCSICntRsTs,
               aCSICntRs,
               aCSICtrlPrivFailCntTs,
               aCSICtrlPrivFailCnt,
               aCSIgsePubMax,
               aCSIgsePubUsed,
               aCSIgseSubMax,
               aCSIgseSubUsed,
               aCSILastEventTs,
               aCSILastEvent,
               aCSIPrivFailCntTs,
               aCSIPrivFailCnt,
               aCSIRemoteEstAssocCntTs,
               aCSIRemoteEstAssocCnt,
               aCSIAcsCtlFailTs,
               aCSIAcsCtlFail,
               aCSIsvPubMax,
               aCSIsvPubUsed,
               aCSIsvSubMax,
               aCSIsvSubUsed
	}
        STATUS              current
    	DESCRIPTION         "acsi-agent optional objects group"
        ::= { acsi-agent 2 }

    acsi-agentCompliance MODULE-COMPLIANCE	
        STATUS              current
        DESCRIPTION         "acsi-agent Compliance"
	MODULE
		
        ::= { acsi-agent 3 }


END
