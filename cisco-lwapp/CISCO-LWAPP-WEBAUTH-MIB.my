-- *******************************************************************
-- CISCO-LWAPP-WEBAUTH-MIB.my : 
-- Light Weight Access Point Web Authentication MIB 
-- January 2006, Devesh Pujari, Prasanna Viswakumar
--
-- Copyright (c) 2006, 2016-2017 by Cisco Systems, Inc.
-- All rights reserved.
-- *******************************************************************
--
CISCO-LWAPP-WEBAUTH-MIB DEFINITIONS ::= BEGIN

IMPORTS 
        MODULE-IDENTITY, 
        NOTIFICATION-TYPE,
        OBJECT-TYPE,
        Unsigned32,
        IpAddress
                FROM SNMPv2-SMI
        MODULE-COMPLIANCE, 
        OBJECT-GROUP,
        NOTIFICATION-GROUP
                FROM SNMPv2-CONF
        TruthValue,
        MacAddress,
        TimeStamp,
        RowStatus
                FROM SNMPv2-TC 
        InetAddressType,
        InetAddress
                FROM INET-ADDRESS-MIB
	CLWebAuthType
                FROM CISCO-LWAPP-TC-MIB
	cLWlanIndex
                FROM CISCO-LWAPP-WLAN-MIB
        CiscoURLString
                FROM CISCO-TC
        SnmpAdminString
                FROM SNMP-FRAMEWORK-MIB
        cLApName
                FROM CISCO-LWAPP-AP-MIB
        cldcClientIPAddress
                FROM CISCO-LWAPP-DOT11-CLIENT-MIB
        ciscoMgmt
                FROM CISCO-SMI;

--********************************************************************
--*  MODULE IDENTITY
--********************************************************************

ciscoLwappWebAuthMIB    MODULE-IDENTITY
        LAST-UPDATED    "200604051150Z"
        ORGANIZATION    "Cisco Systems Inc."
        CONTACT-INFO  
               "        Cisco Systems,
                        Customer Service
                Postal: 170 West Tasman Drive
                        San Jose, CA  95134
                        USA
                   Tel: +1 800 553-NETS

                 Email: cs-wnbu-snmp@cisco.com"

        DESCRIPTION             
                "This MIB is intended to be implemented on all those
                devices operating as Central controllers, that
                terminate the Light Weight Access Point Protocol
                tunnel from Cisco Light-weight LWAPP Access Points.

                This MIB is used to configure web authentication
                parameters in the controller to manage clients'
                authentication.  The mobile nodes are 
                web-authenticated if they select the WLAN that
                has web security enabled.


                The relationship between CC and the LWAPP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Central Controller ( CC )

                The central entity that terminates the LWAPP protocol
                tunnel from the LWAPP APs.  Throughout this MIB,
                this entity also referred to as 'controller'. 

                Guest User

                A guest user is a temporary user with access
                privileges for configuring the wireless network
                for a finite life time.  The wireless networks 
                are configured on the controller. The method of
                authentication to the controller can be configured
                using this MIB instrumentation.

                Light Weight Access Point Protocol ( LWAPP ) 

                This is a generic protocol that defines the 
                communication between the Access Points and the
                Central Controller.

                Mobile Node ( MN )

                A roaming 802.11 wireless device in a wireless
                network associated with an access point. Mobile Node,
                Mobile Station(Ms) and client are used interchangeably. 
                
                Web-Authentication 
                
                Clients are web authenticated, when clients open the 
                web-browser and send HTTP packets. Then user is asked
                to enter login and password. This is known as Web 
                Authentication. 
 
                REFERENCE
 
                [1] Wireless LAN Medium Access Control ( MAC ) and
                Physical Layer ( PHY ) Specifications.
  
                [2] Draft-obara-capwap-lwapp-00.txt, IETF Light 
                Weight Access Point Protocol "
        
        REVISION      "200604051150Z"
        DESCRIPTION
                "Initial version of this MIB module. "
        ::= { ciscoMgmt 515 }

ciscoLwappWebAuthMIBNotifs  OBJECT IDENTIFIER
        ::= { ciscoLwappWebAuthMIB 0 }

ciscoLwappWebAuthMIBNotifObjs  OBJECT IDENTIFIER
        ::= { ciscoLwappWebAuthMIB 1 }

ciscoLwappWebAuthMIBObjects OBJECT IDENTIFIER 
        ::= { ciscoLwappWebAuthMIB 2 }

ciscoLwappWebAuthMIBConform OBJECT IDENTIFIER
        ::= { ciscoLwappWebAuthMIB 3 }

ciscoLwappWebAuthConfig OBJECT IDENTIFIER
        ::= { ciscoLwappWebAuthMIBObjects 1 }

ciscoLwappWebAuthExtConfig OBJECT IDENTIFIER
        ::= { ciscoLwappWebAuthMIBObjects 2 }

ciscoLwappLocalNetUserConfig OBJECT IDENTIFIER
        ::= { ciscoLwappWebAuthMIBObjects 3 }

ciscoLwappWebPageList OBJECT IDENTIFIER
        ::= { ciscoLwappWebAuthMIBObjects 4 }

ciscoLwappGuestUserSessionStatus OBJECT IDENTIFIER
        ::= { ciscoLwappWebAuthMIBObjects 5 }

ciscoLwappPortalConfig OBJECT IDENTIFIER
        ::= { ciscoLwappWebAuthMIBObjects 6 }

ciscoLwappPortalStats OBJECT IDENTIFIER
        ::= { ciscoLwappWebAuthMIBObjects 7 }

ciscoLwappPortalTotalStats OBJECT IDENTIFIER
        ::= { ciscoLwappWebAuthMIBObjects 8 }

--********************************************************************
-- Web Auth config
-- Global controller level web auth configuration
--********************************************************************

cLWAWebAuthType OBJECT-TYPE
        SYNTAX     INTEGER { 
                            internalDefault(1),
                            internalCustom(2),
                            external(3)
                   }
        MAX-ACCESS read-write
        STATUS     current    
        DESCRIPTION
                "The type of web authentication for the clients.

                Web Authentication can be of three types;

                internalDefault - The default login page will be 
                presented to the client for authentication.

                internalCustom -  The administrator has created and 
                uploaded a custom login page and it will be
                presented to the clients for authentication.

                external  - This value indicates that the login page
                will be served from the external web server.  Note
                that cLWAWebAuthType can be successfully set to this
                value when the cLWAExternalWebAuthURL object has been
                set to string with non-zero length. "
        DEFVAL { internalDefault }
        ::= { ciscoLwappWebAuthConfig 1 }
           
cLWAManufacturerLogo OBJECT-TYPE
        SYNTAX     TruthValue
        MAX-ACCESS read-write
        STATUS     current    
        DESCRIPTION
                "This object is used to control the display of the
                Manufacturer Logo on the login page.

                A value of 'true' indicates that the Manufacturer
                logo will be displayed on the login page. 

                A value of 'false' indicates that the Manufacturer
                logo won't be displayed on the login page. "
        DEFVAL { true }
        ::= { ciscoLwappWebAuthConfig 2 }
           
cLWACustomLogoFileName OBJECT-TYPE
        SYNTAX     SnmpAdminString 
        MAX-ACCESS read-only
        STATUS     current    
        DESCRIPTION
                "The name of the custom logo file.  The logo
                in this file will appear on the login page
                when the value of cLWebAuthType is
                'internalDefault'. "
        ::= { ciscoLwappWebAuthConfig 3 }
           
cLWACustomWebTitle OBJECT-TYPE
        SYNTAX     SnmpAdminString (SIZE(0..128))
        MAX-ACCESS read-write
        STATUS     current    
        DESCRIPTION
                "The title text that appears on the login page
                of the clients when the value of cLWebAuthType
                is 'internalDefault'. "
        DEFVAL  {""} 
        ::= { ciscoLwappWebAuthConfig 4 }
           
cLWACustomWebMessage OBJECT-TYPE
        SYNTAX     SnmpAdminString 
        MAX-ACCESS read-write
        STATUS     deprecated    
        DESCRIPTION
                "The message that appears on the login page of
                clients when the value of cLWebAuthType is
               'internalDefault'. "
        DEFVAL  {""} 
        ::= { ciscoLwappWebAuthConfig 5 }
           
cLWACustomWebRedirectURL OBJECT-TYPE
        SYNTAX     CiscoURLString 
        MAX-ACCESS read-write
        STATUS     current    
        DESCRIPTION
                "The URL used to load client web page after
                 successful authentication. "
        ::= { ciscoLwappWebAuthConfig 6 }
     
cLWAExternalWebAuthURL OBJECT-TYPE
        SYNTAX     CiscoURLString 
        MAX-ACCESS read-write
        STATUS     current    
        DESCRIPTION
                "The URL to which the client web page will be
                directed for authentication.   This object will
                be used when the cLWebAuthType object is set to 
                'external'.  The configured URL should resolve to
                one of the Web Server IP addresses configured 
                through cLWAExternalWebServerTable. "
        ::= { ciscoLwappWebAuthConfig 7 }

cLWACustomWebMessageRev1 OBJECT-TYPE
        SYNTAX     OCTET STRING (SIZE  (0..2047))
        MAX-ACCESS read-write
        STATUS     current
        DESCRIPTION
                "The message that appears on the login page of
                clients when the value of cLWebAuthType is
               'internalDefault'. "
        DEFVAL  {""}
        ::= { ciscoLwappWebAuthConfig 9 }

cLWAProxyRedirectMode OBJECT-TYPE
        SYNTAX     TruthValue
        MAX-ACCESS read-write
        STATUS     current
        DESCRIPTION
                "This object specifies the mode of webauth proxy redirection.
                 A value of 'true' enables webauth proxy redirection.
                 A value of 'false' disables webauth proxy redirection."
        ::= { ciscoLwappWebAuthConfig 10 }

cLWAProxyRedirectPortNumber OBJECT-TYPE
        SYNTAX     Unsigned32 
        MAX-ACCESS read-write
        STATUS     current
        DESCRIPTION
                "This object specifies the port number to which the request 
		 should be redirected."
        ::= { ciscoLwappWebAuthConfig 11 }

cLWAWebAuthSecureWeb OBJECT-TYPE
        SYNTAX    TruthValue
        MAX-ACCESS read-write
        STATUS     current
        DESCRIPTION
                "This object specifies the mode of WebAuth Client.
                 A value of 'true' enables webauth client.
                 A value of 'false' disable webauth clent."
        ::= { ciscoLwappWebAuthConfig 12 }

cLWAWebAuthLoginSuccessPageMode OBJECT-TYPE
        SYNTAX     INTEGER  {
                        default(1),
                        none(2)
                    }

        MAX-ACCESS read-write
        STATUS     current
        DESCRIPTION
                "This object specifies the page that would be dispalyed after webauth is successful.
                 A value of 'default' means default page would be displayed after web-auth page success.
                 A value of 'none' means a blank page will be displayed after web-auth page success."
	DEFVAL { default }
        ::= { ciscoLwappWebAuthConfig 13 }

cLWACaptiveBypassMode OBJECT-TYPE
        SYNTAX     TruthValue
        MAX-ACCESS read-write
        STATUS     current
        DESCRIPTION
                "This object specifies the mode of webauth captive bypass.
                 A value of 'true' enables webauth captive bypass.
                 A value of 'false' disables webauth captive bypass."
        DEFVAL  { false }
        ::= { ciscoLwappWebAuthConfig 14 }

cLWebAuthWlanConfigTable OBJECT-TYPE
	SYNTAX     SEQUENCE OF CLWebAuthWlanConfigEntry
	MAX-ACCESS not-accessible 
	STATUS	   current
	DESCRIPTION
	          "This table provides the list of wlans and the
		  type of web-auth configured in each of them. If
		  web-auth type is customised, then it will also 
		  have the login page associated for that wlan. If
		  the web-auth type is external, then it will also
		  have the URL associated with it. "
	::= { ciscoLwappWebAuthConfig 8 }

cLWebAuthWlanConfigEntry OBJECT-TYPE
	SYNTAX     CLWebAuthWlanConfigEntry
	MAX-ACCESS not-accessible 
	STATUS     current
	DESCRIPTION
	          "A conceptual row in cLWebAuthWlanConfigTable.
		  Each entry represents the web-auth type for each
		  WLAN."
	INDEX      { cLWlanIndex }
	::= { cLWebAuthWlanConfigTable 1 }
		  
CLWebAuthWlanConfigEntry ::=
	SEQUENCE {
		cLWlanGlobalWebAuthConfig TruthValue, 
                cLWlanWebAuthType  CLWebAuthType,   
	    	cLWlanWebAuthLoginPage SnmpAdminString,
		cLWlanExternalWebAuthUrl  CiscoURLString, 
	    	cLWlanWebAuthLoginFailurePage SnmpAdminString,
	    	cLWlanWebAuthLogoutPage SnmpAdminString,
                cLWlanExternalWebAuthAcl SnmpAdminString,
        cLWlanWebAuthCaptiveBypassMode INTEGER 
	}

cLWlanGlobalWebAuthConfig OBJECT-TYPE
	SYNTAX	   TruthValue
	MAX-ACCESS read-write
	STATUS     current
	DESCRIPTION
		"This value is false if the web auth is set per wlan else true."
	::= { cLWebAuthWlanConfigEntry 1 }


cLWlanWebAuthType OBJECT-TYPE
        SYNTAX     CLWebAuthType  
        MAX-ACCESS read-write
        STATUS     current    
        DESCRIPTION
                "The type of web authentication for the clients.

                Web Authentication can be of three types;

                internalDefault - The default login page will be 
                presented to the client for authentication.

                internalCustom -  The administrator has created and 
                uploaded a custom login page and it will be
                presented to the clients for authentication.

                external  - This value indicates that the login page
                will be served from the external web server.  Note
                that cLWAWebAuthType can be successfully set to this
                value when the cLWAExternalWebAuthURL object has been
                set to string with non-zero length. "
        DEFVAL { internalDefault }
        ::= { cLWebAuthWlanConfigEntry 2 }

cLWlanWebAuthLoginPage OBJECT-TYPE
	SYNTAX      SnmpAdminString
	MAX-ACCESS  read-write
	STATUS      current
	DESCRIPTION 
	          "This attribute specifies the login page which will be 
		  displayed to the client  connecting to this WLAN.
		  This will be set only if the web auth type 
                   is customized."
	::= { cLWebAuthWlanConfigEntry 3 }
	
cLWlanExternalWebAuthUrl OBJECT-TYPE
	SYNTAX      CiscoURLString 
	MAX-ACCESS  read-write
	STATUS      current
	DESCRIPTION
		 "This is the URL to which the client web page will be 
                 directed for authentication when a client joins the WLAN.
		 This is applicable only when the web-auth type is external."
        ::= { cLWebAuthWlanConfigEntry  4 }

cLWlanWebAuthLoginFailurePage OBJECT-TYPE
	SYNTAX      SnmpAdminString
	MAX-ACCESS  read-write
	STATUS      current
	DESCRIPTION 
	          "This attribute specifies the login page which will be
		  displayed to the client  connecting to this WLAN.
                  This only applies when the cLWlanWebAuthType is set to
                  customized."
	::= { cLWebAuthWlanConfigEntry 5 }

cLWlanWebAuthLogoutPage OBJECT-TYPE
	SYNTAX      SnmpAdminString
	MAX-ACCESS  read-write
	STATUS      current
	DESCRIPTION 
	          "This attribute specifies the login page which will be
                   displayed to the client  connecting to this WLAN.
                   This only applies when the cLWlanWebAuthType is set to
                   customized."
	::= { cLWebAuthWlanConfigEntry 6 }

cLWlanExternalWebAuthAcl OBJECT-TYPE
	SYNTAX      SnmpAdminString (SIZE (0..32)) 
	MAX-ACCESS  read-write
	STATUS      current
	DESCRIPTION
		 "This is the ACL which is applied on the AP so the packets are
                 switched locally for reaching the External web server.
		 This is applicable only when the web-auth type is external."
        ::= { cLWebAuthWlanConfigEntry  7 }

cLWlanWebAuthCaptiveBypassMode OBJECT-TYPE
        SYNTAX     INTEGER  {
                           enabled(1),
                           disabled(2),
                           none(3)
                    }

        MAX-ACCESS read-write
        STATUS     current
        DESCRIPTION
                "This object specifies the page that would be dispalyed after webauth is successful.
                 A value of 'default' means default page would be displayed after web-auth page success.
                 A value of 'none' means a blank page will be displayed after web-auth page success."
        ::= { cLWebAuthWlanConfigEntry 8 }

	
--********************************************************************
--*    External Webserver table  
--********************************************************************
     
cLWAExternalWebServerTable OBJECT-TYPE
        SYNTAX     SEQUENCE OF CLWAExternalWebServerEntry
        MAX-ACCESS not-accessible
        STATUS     current
        DESCRIPTION
                 "This table provides the list of external web
                 servers used for external web authentication.
                 These are the addresses from which the
                 controller will allow traffic before client
                 authentication to show the login page.
                 The controller is expected to use the services
                 of these web servers for performing the
                 authentication.  The user is expected to provide
                 correct Internet addresses of those servers
                 available for authentication through this table.
                 The web authentication is done with the help of
                 only those Web Servers configured through this
                 table only when the cLWAWebAuthType is
                 configured as 'external'. "
        ::= { ciscoLwappWebAuthExtConfig 1 } 
                  
cLWAExternalWebServerEntry OBJECT-TYPE
        SYNTAX     CLWAExternalWebServerEntry
        MAX-ACCESS not-accessible
        STATUS     current
        DESCRIPTION
                "A conceptual row in cLWAExternalWebServerTable.  Each
                entry corresponds to one external web authentication
                server whose address is represented by 
                cLWAExternalWebServerAddr. "
        INDEX   { cLWAExternalWebServerIndex }              
        ::= { cLWAExternalWebServerTable 1 } 
              
CLWAExternalWebServerEntry ::= 
        SEQUENCE {
                  cLWAExternalWebServerIndex     Unsigned32,
                  cLWAExternalWebServerAddrType  InetAddressType, 
                  cLWAExternalWebServerAddr      InetAddress,
                  cLWAExternalWebServerRowStatus RowStatus
        }
     
cLWAExternalWebServerIndex OBJECT-TYPE
        SYNTAX     Unsigned32(1..32)
        MAX-ACCESS not-accessible 
        STATUS     current
        DESCRIPTION
                "This object uniquely identifies one specific entry
                in this table. "
        ::= { cLWAExternalWebServerEntry 1 } 
              
cLWAExternalWebServerAddrType OBJECT-TYPE
        SYNTAX     InetAddressType
        MAX-ACCESS read-create
        STATUS     current
        DESCRIPTION
                "The type of the Web Server address as represented 
                by the value of the corresponding instance of 
               'cLWAExternalWebServerAddr'. "
        ::= { cLWAExternalWebServerEntry 2 } 

cLWAExternalWebServerAddr OBJECT-TYPE
        SYNTAX     InetAddress
        MAX-ACCESS read-create
        STATUS     current
        DESCRIPTION
                "The Internet address of the Web Server from which
                traffic is allowed before client's authentication.
                Please note that the row creation will be
                successful only if the address of the Web Server
                represented by the values of
                cLWAExternalWebServerAddrType and
                cLWAExternalWebServerAddr is unique across all
                the entries. "
        ::= { cLWAExternalWebServerEntry 3 } 

cLWAExternalWebServerRowStatus OBJECT-TYPE
        SYNTAX     RowStatus
        MAX-ACCESS read-create
        STATUS     current
        DESCRIPTION
                "The status of the conceptual row used to create and
                delete specific instances of rows in this table.

                This object can not be set to 'active' unless the
                values of the corresponding instances of
                cLWAExternalWebServerAddr and 
                cLWAExternalWebServerAddrType are set. "
        ::= { cLWAExternalWebServerEntry 4 }


cLWALocalNetUserTable OBJECT-TYPE
      SYNTAX     SEQUENCE OF CLWALocalNetUserEntry
      MAX-ACCESS not-accessible
      STATUS     current
      DESCRIPTION
            "The table which lists Local Net User entries."
      ::= { ciscoLwappLocalNetUserConfig 1 }


cLWALocalNetUserEntry OBJECT-TYPE
      SYNTAX     CLWALocalNetUserEntry
      MAX-ACCESS not-accessible
      STATUS     current
      DESCRIPTION
            "This is a conceptual row in the cLWALocalNetUserTable"
      INDEX      { cLWALocalNetUserName }
      ::= { cLWALocalNetUserTable 1 }


CLWALocalNetUserEntry ::= 
		SEQUENCE {
                cLWALocalNetUserName             OCTET STRING,
                cLWALocalNetUserIsGuest          TruthValue,
                cLWALocalNetUserRole             OCTET STRING,
                cLWALocalNetUserLoginTime        Unsigned32,
                cLWALocalNetUserLoginCount       Unsigned32, 
                cLWALocalNetUserLifeTime         TimeTicks 
}

cLWALocalNetUserName OBJECT-TYPE
      SYNTAX     OCTET STRING (SIZE(1..24))
      MAX-ACCESS not-accessible 
      STATUS     current
      DESCRIPTION
             "Name of the net or guest user."
      ::= { cLWALocalNetUserEntry 1 }

cLWALocalNetUserIsGuest  OBJECT-TYPE
      SYNTAX     TruthValue
      MAX-ACCESS read-write
      STATUS     current
      DESCRIPTION
             "This value is true for guest user flase otherwise."

      ::= {  cLWALocalNetUserEntry 2 }

cLWALocalNetUserRole  OBJECT-TYPE
      SYNTAX     OCTET STRING
      MAX-ACCESS read-write
      STATUS     current
      DESCRIPTION
             "This object represents the Role of a Guest user. This
              object is not applicable if the user is not a Guest user
              as indicated by a value of 'false' for cLWALocalNetUserIsGuest. "

      ::= {  cLWALocalNetUserEntry 3 }

cLWALocalNetUserLoginTime  OBJECT-TYPE
      SYNTAX     Unsigned32
      UNITS      "seconds"
      MAX-ACCESS read-only
      STATUS     current
      DESCRIPTION
             "This object represents the time at which the 
              Guest user first logged in.
              This represents number of seconds elapsed since 00:00:00
              on January 1, 1970, Coordinated Universal Time (UTC).  So
              a value of '1131362704' means 'Mon Nov  7 16:55:04
              2005'. 
              This object is not applicable if the user is
              not a Guest user as indicated by a value of
              'false' for cLWALocalNetUserIsGuest."
      ::= {  cLWALocalNetUserEntry 4 }

cLWALocalNetUserLoginCount  OBJECT-TYPE
      SYNTAX     Unsigned32
      MAX-ACCESS read-only
      STATUS     current
      DESCRIPTION
             "This object represents the number of logins made 
              by a Guest user.
              This object is not applicable if the user is not 
              a Guest user as indicated by a value of 'false'
              for cLWALocalNetUserIsGuest. "
      ::= {  cLWALocalNetUserEntry 5 }

cLWALocalNetUserLifeTime OBJECT-TYPE
      SYNTAX     TimeTicks
      MAX-ACCESS read-write
      STATUS     current
      DESCRIPTION
              "This object indicates the lifetime of an
              user account expressed in hundredths of a second.

              Lifetime period other than 0 will make it a guest-user.

              Once configured as non-guest user can not be change
              to guest user and vice-versa. 
              Maximum lifetime is one year. WLAN identifiers
              which have webauth policy are valid for guest access
              user. "

      ::= {  cLWALocalNetUserEntry 6 }


cLWALocalNetUserMaxGuestRoles  OBJECT-TYPE
      SYNTAX     Unsigned32(1..32)
      MAX-ACCESS read-write
      STATUS     current
      DESCRIPTION
              "This object represents the maximum number of guest-roles
              that can be configured on the controller. "
      DEFVAL  { 10 }
      ::= { ciscoLwappLocalNetUserConfig 2 }

cLWALocalNetUserGuestRolesCount  OBJECT-TYPE
      SYNTAX     Unsigned32(1..32)
      MAX-ACCESS read-only
      STATUS     current
      DESCRIPTION
              "This object represents the count of the number of
              guest-roles currently configured on the controller. "
      ::= { ciscoLwappLocalNetUserConfig 3 }

--********************************************************************
--*    Configure role to bandwidth contract mapping
--********************************************************************
cLWALocalNetUserRoleTable OBJECT-TYPE
        SYNTAX     SEQUENCE OF CLWALocalNetUserRoleEntry
        MAX-ACCESS not-accessible
        STATUS     current
        DESCRIPTION
                 "Roles specified in cLWALocalNetUserRoleTable can be
                 assigned to guest users. This is a lookup table for
                 various roles of guest users."
        ::= { ciscoLwappLocalNetUserConfig 4 }

cLWALocalNetUserRoleEntry OBJECT-TYPE
        SYNTAX     CLWALocalNetUserRoleEntry
        MAX-ACCESS not-accessible
        STATUS     current
        DESCRIPTION
                "An entry in cLWALocalNetUserRoleTable. "
        INDEX   { cLWALocalNetUserRoleName }
        ::= { cLWALocalNetUserRoleTable 1 }

CLWALocalNetUserRoleEntry ::=
        SEQUENCE {
                  cLWALocalNetUserRoleName                   SnmpAdminString,
                  cLWALocalNetUserRoleAverageDataRate        Unsigned32,
                  cLWALocalNetUserRoleBurstDataRate          Unsigned32,
                  cLWALocalNetUserRoleAvgRealTimeDataRate    Unsigned32,
                  cLWALocalNetUserRoleBurstRealTimeDataRate  Unsigned32,
                  cLWALocalNetUserRoleRowStatus              RowStatus
        }

cLWALocalNetUserRoleName OBJECT-TYPE
        SYNTAX     SnmpAdminString
        MAX-ACCESS not-accessible
        STATUS     current
        DESCRIPTION
               "Guest user role name. This can be dynamically added. "
        ::= { cLWALocalNetUserRoleEntry 1 }

cLWALocalNetUserRoleAverageDataRate OBJECT-TYPE
        SYNTAX     Unsigned32 (0..60000)
        MAX-ACCESS read-create
        STATUS     current
        DESCRIPTION
                "This is one of the per user bandwidth contracts(kbps).
                Specifies Average Data Rate per user. "
        ::= { cLWALocalNetUserRoleEntry 2 }

cLWALocalNetUserRoleBurstDataRate OBJECT-TYPE
        SYNTAX     Unsigned32 (0..60000)
        MAX-ACCESS read-create
        STATUS     current
        DESCRIPTION
                "This is one of the per user bandwidth contracts(kbps).
                Specifies Burst Data Rate per user. "
        ::= { cLWALocalNetUserRoleEntry 3 }

cLWALocalNetUserRoleAvgRealTimeDataRate OBJECT-TYPE
        SYNTAX     Unsigned32 (0..60000)
        MAX-ACCESS read-create
        STATUS     current
        DESCRIPTION
                "This is one of the per user bandwidth contracts(kbps).
                Specifies Average Real Time Data Rate per user. "
        ::= { cLWALocalNetUserRoleEntry 4 }

cLWALocalNetUserRoleBurstRealTimeDataRate OBJECT-TYPE
        SYNTAX     Unsigned32 (0..60000)
        MAX-ACCESS read-create
        STATUS     current
        DESCRIPTION
                "This is one of the per user bandwidth contracts(kbps).
                Specifies Burst Real Time Data Rate per user. "
        ::= { cLWALocalNetUserRoleEntry 5 }

cLWALocalNetUserRoleRowStatus OBJECT-TYPE
        SYNTAX     RowStatus
        MAX-ACCESS read-create
        STATUS     current
        DESCRIPTION
                "The status of the conceptual row used to create and
                delete specific instances of rows in this table.

                This object can not be set to 'active' unless the
                values of the corresponding instances of
                cLWALocalNetUserRoleAverageDataRate or
                cLWALocalNetUserRoleBurstDataRate or
                cLWALocalNetUserRoleAvgRealTimeDataRate or
                cLWALocalNetUserRoleBurstRealTimeDataRate are set. "
        ::= { cLWALocalNetUserRoleEntry 6 }

cLWACustomizedWebPageListTable OBJECT-TYPE

        SYNTAX     SEQUENCE OF CLWACustomizedWebPageListEntry
        MAX-ACCESS not-accessible
        STATUS     current
        DESCRIPTION
               "This table can be used to view the list of
               the web pages downloaded to the controller."

        ::= {  ciscoLwappWebPageList 1 }

cLWACustomizedWebPageListEntry OBJECT-TYPE
        SYNTAX     CLWACustomizedWebPageListEntry
        MAX-ACCESS not-accessible
        STATUS        current
        DESCRIPTION
                "A conceptual row in the
                          cLWACustomizedWebPageListTable."
        INDEX  { cLWACustomizedWebLoginPage }
  	 
        ::= {  cLWACustomizedWebPageListTable 1 }
  	 
CLWACustomizedWebPageListEntry  ::=
      SEQUENCE  {
           cLWACustomizedWebLoginPage  SnmpAdminString
      }
  	 
cLWACustomizedWebLoginPage OBJECT-TYPE
     SYNTAX    SnmpAdminString
     MAX-ACCESS  read-only
     STATUS      current
     DESCRIPTION
               "This attribute specifies the login page which will be
                displayed to the client connecting to the WLANs."
     ::= {  cLWACustomizedWebPageListEntry 1}

cLGuestUserSessionStatusTable OBJECT-TYPE
        SYNTAX     SEQUENCE OF CLGuestUserSessionStatusEntry
        MAX-ACCESS not-accessible
        STATUS     current
        DESCRIPTION
                  "This table provides the information about the various sessions,
                   indicated by the cLGuestUserSessionId, for all the guest users,
                   indicated by cLGuestUserName. This table does not give info
                   regarding any ongoing sessions.  "
        ::= { ciscoLwappGuestUserSessionStatus 1 }

cLGuestUserSessionStatusEntry OBJECT-TYPE
        SYNTAX     CLGuestUserSessionStatusEntry
        MAX-ACCESS not-accessible
        STATUS     current
        DESCRIPTION
                  "A conceptual row in cLGuestUserSessionStatusTable
                  Each entry represents a particular session for a particular
                  Guest user."
        INDEX      { cLGuestUserName, cLGuestUserSessionId  }
        ::= { cLGuestUserSessionStatusTable 1 }

CLGuestUserSessionStatusEntry ::=
        SEQUENCE {
                cLGuestUserName OCTET STRING,
                cLGuestUserSessionId  Unsigned32,
                cLGuestUserClientMacAddress MacAddress,
                cLGuestUserClientIpAddressType InetAddressType,
                cLGuestUserClientIpAddress InetAddress,
                cLGuestUserApMacAddress MacAddress,
                cLGuestUserLoggedInTime Unsigned32,
                cLGuestUserLoggedOutTime Unsigned32,
                cLGuestUserBytesReceived  Counter64,
                cLGuestUserBytesTransmitted Counter64
        }

cLGuestUserName OBJECT-TYPE
        SYNTAX     OCTET STRING(SIZE(1..24))
        MAX-ACCESS not-accessible
        STATUS     current
        DESCRIPTION
                "This object represents the name of the guest user. "
        ::= { cLGuestUserSessionStatusEntry 1 }

cLGuestUserSessionId OBJECT-TYPE
        SYNTAX     Unsigned32
        MAX-ACCESS not-accessible
        STATUS     current
        DESCRIPTION
            "This object represents the session Id of a particular session, 
             used by a guest user represented by cLGuestUserName."
        ::= { cLGuestUserSessionStatusEntry 2 }

cLGuestUserClientMacAddress OBJECT-TYPE
        SYNTAX     MacAddress
        MAX-ACCESS read-only
        STATUS     current
        DESCRIPTION
            "This object represents the MAC Address of the client, 
             which logged in/out in the particular session corresponding
             to cLGuestUserSessionId."
        ::= { cLGuestUserSessionStatusEntry 3 }

cLGuestUserClientIpAddressType OBJECT-TYPE
        SYNTAX     InetAddressType
        MAX-ACCESS read-only
        STATUS     current
        DESCRIPTION
            "This object represents the type of the IP Address of the client,
             which logged in/out in the particular session corresponding
             to cLGuestUserSessionId."
        ::= { cLGuestUserSessionStatusEntry 4 }

cLGuestUserClientIpAddress OBJECT-TYPE
        SYNTAX     InetAddress
        MAX-ACCESS read-only
        STATUS     current
        DESCRIPTION
            "This object represents the IP Address of the client,
             which logged in/out in the particular session corresponding
             to cLGuestUserSessionId."
        ::= { cLGuestUserSessionStatusEntry 5 }

cLGuestUserApMacAddress OBJECT-TYPE
        SYNTAX     MacAddress
        MAX-ACCESS read-only
        STATUS     current
        DESCRIPTION
            "This object represents the MAC Address of the AP, 
             using which the client had joined to the controller using 
             the guest user account corresponding to cLGuestUserName."
        ::= { cLGuestUserSessionStatusEntry 6 }

cLGuestUserLoggedInTime OBJECT-TYPE
        SYNTAX     Unsigned32
        UNITS      "seconds" 
        MAX-ACCESS read-only
        STATUS     current
        DESCRIPTION
            "This object represents the time at which the guest client
             logged in that particular session corresponding to 
             cLGuestUserSessionId.
             This represents number of seconds elapsed since 00:00:00
             on January 1, 1970, Coordinated Universal Time (UTC).  So
             a value of '1131362704' means 'Mon Nov  7 16:55:04
             2005'."
        ::= { cLGuestUserSessionStatusEntry 7 }

cLGuestUserLoggedOutTime OBJECT-TYPE
        SYNTAX     Unsigned32
        UNITS      "seconds"
        MAX-ACCESS read-only
        STATUS     current
        DESCRIPTION
            "This object represents the time at which the guest client
             logged out of that particular session corresponding to 
             cLGuestUserSessionId.
             This represents number of seconds elapsed since 00:00:00
             on January 1, 1970, Coordinated Universal Time (UTC).  So
             a value of '1131362704' means 'Mon Nov  7 16:55:04
             2005'."
        ::= { cLGuestUserSessionStatusEntry 8 }

cLGuestUserBytesReceived  OBJECT-TYPE
        SYNTAX     Counter64
        MAX-ACCESS read-only
        STATUS     current
        DESCRIPTION
            "This object represents the number of bytes received by the
            Guest user in that particular session corresponding to 
            cLGuestUserSessionId."
        ::= { cLGuestUserSessionStatusEntry 9 }

cLGuestUserBytesTransmitted  OBJECT-TYPE
        SYNTAX     Counter64
        MAX-ACCESS read-only
        STATUS     current
        DESCRIPTION
            "This object represents the number of bytes transmitted by the
            Guest user in that particular session corresponding to 
            cLGuestUserSessionId."
        ::= { cLGuestUserSessionStatusEntry 10 }

-- ********************************************************************
-- Portal Server Configure
-- ********************************************************************

cLWAPortalConfigTable OBJECT-TYPE
    SYNTAX          SEQUENCE OF CLWAPortalConfigEntry 
    MAX-ACCESS      not-accessible
    STATUS          current
    DESCRIPTION
        "This table represents the Portal Server related 
        Configuration of the controller."
    ::= { ciscoLwappPortalConfig 1 }

cLWAPortalConfigEntry OBJECT-TYPE
    SYNTAX          CLWAPortalConfigEntry
    MAX-ACCESS      not-accessible
    STATUS          current
    DESCRIPTION
        "Each entry in this table represents the portal 
        server related configuration on the controller."
    INDEX           { cLWAPortalIndex } 
    ::= { cLWAPortalConfigTable 1 }

CLWAPortalConfigEntry ::= SEQUENCE {
        cLWAPortalIndex                  Unsigned32,
        cLWAPortalServerAddrType         InetAddressType,
        cLWAPortalServerIp               InetAddress,
        cLWAPortalUnreachSet             TruthValue
}

cLWAPortalIndex OBJECT-TYPE
        SYNTAX Unsigned32
        MAX-ACCESS not-accessible
        STATUS     current
        DESCRIPTION                
            "Index of the portal server."
        ::= { cLWAPortalConfigEntry 1 }

cLWAPortalServerAddrType OBJECT-TYPE
        SYNTAX     InetAddressType
        MAX-ACCESS read-only
        STATUS     current
        DESCRIPTION
                "This object represents the ip address type of
                portal server."
        ::= {  cLWAPortalConfigEntry 2 }

cLWAPortalServerIp OBJECT-TYPE
        SYNTAX     InetAddress
        MAX-ACCESS read-only
        STATUS     current
        DESCRIPTION
                "This object represents the ip address of
                portal server."
        ::= {  cLWAPortalConfigEntry 3 }

cLWAPortalUnreachSet OBJECT-TYPE
        SYNTAX     TruthValue
        MAX-ACCESS read-only
        STATUS     current
        DESCRIPTION
                "This object specifies whether this event is
                raise or clear.
                'TRUE' indicates this event is set.
                'FALSE' indicates this even is cleared." 
        ::= { cLWAPortalConfigEntry 4 }

-- ********************************************************************
-- Portal Server Stats Counter 
-- ********************************************************************
cLWAPortalCounterTable OBJECT-TYPE
    SYNTAX          SEQUENCE OF CLWAPortalCounterEntry 
    MAX-ACCESS      not-accessible
    STATUS          current
    DESCRIPTION
        "This table represents the Portal Server related 
        Counters of the controller."
    ::= { ciscoLwappPortalStats 1 }

cLWAPortalCounterEntry OBJECT-TYPE
    SYNTAX          CLWAPortalCounterEntry
    MAX-ACCESS      not-accessible
    STATUS          current
    DESCRIPTION
        "Each entry in this table represents the portal 
        server related Counter on the controller."
    INDEX           { cLWAPortalIndex } 
    ::= { cLWAPortalCounterTable 1 }

CLWAPortalCounterEntry ::= SEQUENCE {
        cLWAPortalChallengeReq           Counter32,
        cLWAPortalChallengeAck           Counter32,
        cLWAPortalChallengeErr           Counter32,
        cLWAPortalAuthenticationReq      Counter32,
        cLWAPortalAuthenticationAck      Counter32,
        cLWAPortalAuthenticationErr      Counter32,
        cLWAPortalLogoutReq              Counter32,
        cLWAPortalLogoutAck              Counter32,
        cLWAPortalLogoutErr              Counter32,
        cLWAPortalLogoutNTF              Counter32,
        cLWAPortalUnknownReq             Counter32,
        cLWAPortalAuthenticatedClient    Counter32,
        cLWAPortalAuthenticatedMaxClient Counter32,
        cLWAPortalHttpReq                Counter32
}

cLWAPortalChallengeReq OBJECT-TYPE
        SYNTAX     Counter32
        MAX-ACCESS read-only
        STATUS     current
        DESCRIPTION                
            "This object represents the number of 
             Challenge Request counters."
        ::= { cLWAPortalCounterEntry  1 }

cLWAPortalChallengeAck OBJECT-TYPE
        SYNTAX     Counter32
        MAX-ACCESS read-only
        STATUS     current
        DESCRIPTION                
            "This object represents the number of 
             Challenge Acknowledgement counters."
        ::= { cLWAPortalCounterEntry  2 }

cLWAPortalChallengeErr OBJECT-TYPE
        SYNTAX     Counter32
        MAX-ACCESS read-only
        STATUS     current
        DESCRIPTION                
            "This object represents the number of 
             Challenge Error counters."
        ::= { cLWAPortalCounterEntry  3 }

cLWAPortalAuthenticationReq OBJECT-TYPE
        SYNTAX     Counter32
        MAX-ACCESS read-only
        STATUS     current
        DESCRIPTION                
            "This object represents the number of 
             Authentication Request counters."
        ::= { cLWAPortalCounterEntry  4 }

cLWAPortalAuthenticationAck OBJECT-TYPE
        SYNTAX     Counter32
        MAX-ACCESS read-only
        STATUS     current
        DESCRIPTION                
            "This object represents the number of 
             Authentication Acknowledgement counters."
        ::= { cLWAPortalCounterEntry  5 }

cLWAPortalAuthenticationErr OBJECT-TYPE
        SYNTAX     Counter32
        MAX-ACCESS read-only
        STATUS     current
        DESCRIPTION                
            "This object represents the number of 
             Authentication Error counters."
        ::= { cLWAPortalCounterEntry  6 }

cLWAPortalLogoutReq OBJECT-TYPE
        SYNTAX     Counter32
        MAX-ACCESS read-only
        STATUS     current
        DESCRIPTION                
            "This object represents the number of 
             Logout Request counters."
        ::= { cLWAPortalCounterEntry  7 }

cLWAPortalLogoutAck OBJECT-TYPE
        SYNTAX     Counter32
        MAX-ACCESS read-only
        STATUS     current
        DESCRIPTION                
            "This object represents the number of 
             Logout Acknowledgement counters."
        ::= { cLWAPortalCounterEntry  8 }

cLWAPortalLogoutErr OBJECT-TYPE
        SYNTAX     Counter32
        MAX-ACCESS read-only
        STATUS     current
        DESCRIPTION                
            "This object represents the number of 
             Logout Error counters."
        ::= { cLWAPortalCounterEntry  9 }

cLWAPortalLogoutNTF OBJECT-TYPE
        SYNTAX     Counter32
        MAX-ACCESS read-only
        STATUS     current
        DESCRIPTION                
            "This object represents the number of 
             Logout Notification counters."
        ::= { cLWAPortalCounterEntry  10 }

cLWAPortalUnknownReq OBJECT-TYPE
        SYNTAX     Counter32
        MAX-ACCESS read-only
        STATUS     current
        DESCRIPTION                
            "This object represents the number of 
             unknown Request counters."
        ::= { cLWAPortalCounterEntry  11 }

cLWAPortalAuthenticatedClient OBJECT-TYPE
        SYNTAX     Counter32
        MAX-ACCESS read-only
        STATUS     current
        DESCRIPTION                
            "This object represents the number of 
             Authenticated Client counters."
        ::= { cLWAPortalCounterEntry  12 }

cLWAPortalAuthenticatedMaxClient OBJECT-TYPE
        SYNTAX     Counter32
        MAX-ACCESS read-only
        STATUS     current
        DESCRIPTION                
            "This object represents the max number of 
             Authenticated Client counters."
        ::= { cLWAPortalCounterEntry  13 }

cLWAPortalHttpReq OBJECT-TYPE
        SYNTAX     Counter32
        MAX-ACCESS read-only
        STATUS     current
        DESCRIPTION                
            "This object represents the number of 
             Http request."
        ::= { cLWAPortalCounterEntry  14 }

-- ********************************************************************
-- Portal Server Stats Counter 
-- ********************************************************************

cLWAPortalDisconnectOnlineUsersCount OBJECT-TYPE
        SYNTAX     Counter32
        MAX-ACCESS read-only
        STATUS     current
        DESCRIPTION                
            "This object represents the number of 
             NTF_LOGOUT to portal server."
        ::= { ciscoLwappPortalTotalStats  1 }

cLWAPortalConnectLostUsersCount OBJECT-TYPE
        SYNTAX     Counter32
        MAX-ACCESS read-only
        STATUS     current
        DESCRIPTION                
            "This object represents the number of abnormal 
            offline user with portal authentication attribute."
        ::= { ciscoLwappPortalTotalStats  2 }
        
cLWAPortalAuthReqCount OBJECT-TYPE
        SYNTAX     Counter32
        MAX-ACCESS read-only
        STATUS     current
        DESCRIPTION                
            "This object represents the total number of 
             Authentication Request counters to portal server."
        ::= { ciscoLwappPortalTotalStats  3 }

cLWAPortalAuthReqSucessCount OBJECT-TYPE
        SYNTAX     Counter32
        MAX-ACCESS read-only
        STATUS     current
        DESCRIPTION                
            "This object represents the total number of portal 
            Authentication Error counters."
        ::= { ciscoLwappPortalTotalStats  4 }

cLWAPortalAuthReqFailureCount OBJECT-TYPE
        SYNTAX     Counter32
        MAX-ACCESS read-only
        STATUS     current
        DESCRIPTION                
            "This object represents the total number of portal
            Authentication Error counters."
        ::= { ciscoLwappPortalTotalStats  5 }

cLWAPortalMaxAuthClient OBJECT-TYPE
        SYNTAX     Integer32
        MAX-ACCESS read-only
        STATUS     current
        DESCRIPTION               
            "This object represents the AC max number of portal
            Authenticated client."
        ::= { ciscoLwappPortalTotalStats  6 }

--********************************************************************
--*    Notification objects
--********************************************************************

cLWAGuestUserName OBJECT-TYPE
        SYNTAX     OCTET STRING(SIZE(1..24))
        MAX-ACCESS accessible-for-notify
        STATUS     current
        DESCRIPTION
                "This object indicates the name of the guest user. "
        ::= { ciscoLwappWebAuthMIBNotifObjs 1 }

--********************************************************************
--*    Notifications 
--********************************************************************
 
cLWAGuestUserRemoved  NOTIFICATION-TYPE
        OBJECTS { 
                cLWAGuestUserName 
        }
        STATUS  current
        DESCRIPTION
             "This notification is generated when the lifetime of the 
             guest-user expires and the guest-user's accounts are
             removed. " 
        ::= { ciscoLwappWebAuthMIBNotifs 1 }

cLWAGuestUserAdded  NOTIFICATION-TYPE
        OBJECTS { 
                cLWAGuestUserName 
        }
        STATUS  current
        DESCRIPTION
             "This notification is generated when the a guest user is 
             added." 
        ::= { ciscoLwappWebAuthMIBNotifs 2 }

cLWAGuestUserLoggedIn NOTIFICATION-TYPE
        OBJECTS { 
                cLWAGuestUserName,
                cLGuestUserClientMacAddress,
                cldcClientIPAddress,
                cLGuestUserApMacAddress,
                cLApName
        }
        STATUS  current
        DESCRIPTION
             "This notification is generated when the a guest user is
             logged in." 
        ::= { ciscoLwappWebAuthMIBNotifs 3 }

cLWAGuestUserLoggedOut NOTIFICATION-TYPE
        OBJECTS {
                cLWAGuestUserName,
                cLGuestUserClientMacAddress,
                cldcClientIPAddress,
                cLGuestUserApMacAddress,
                cLApName
        }
        STATUS  current
        DESCRIPTION
             "This notification is generated when the a guest user is
             logged out."
        ::= { ciscoLwappWebAuthMIBNotifs 4 }

cLWAPortalUnreachNotify NOTIFICATION-TYPE
    OBJECTS         {
                        cLWAPortalServerAddrType,
                        cLWAPortalServerIp,
                        cLWAPortalUnreachSet
                    }
    STATUS     current
    DESCRIPTION
            "This notification is generated when portal server is 
            unreachable/recovered."
    ::= { ciscoLwappWebAuthMIBNotifs 5 }

--********************************************************************
--*    Compliance statements  
--********************************************************************

ciscoLwappWebAuthMIBCompliances OBJECT IDENTIFIER
        ::= { ciscoLwappWebAuthMIBConform 1 }

ciscoLwappWebAuthMIBGroups OBJECT IDENTIFIER
        ::= { ciscoLwappWebAuthMIBConform 2 }

cLWebAuthMIBCompliance MODULE-COMPLIANCE
        STATUS     current
        DESCRIPTION
                "The compliance statement for the SNMP entities that
                implement the ciscoLwappWebAuthMIB module.  "
        MODULE MANDATORY-GROUPS {                
                cLWACustomWebAuthGroup,
                cLWAExternalWebAuthGroup,
                cLWAGuestAccessNotifObjGroup,
                cLWAGuestAccessNotifGroup 
        }

        OBJECT cLWAExternalWebServerRowStatus
                SYNTAX  INTEGER {
                              active(1),
                              createAndGo(4),
                              destroy(6)
                        }
                DESCRIPTION
                        "An implementation is only required to support
                        three of the six enumerated values of the
                        RowStatus textual convention, specifically,
                        'active', 'createAndGo' and 'destroy'. "

        ::= { ciscoLwappWebAuthMIBCompliances 1 }

--********************************************************************
--*    Units of conformance  
--********************************************************************

cLWACustomWebAuthGroup OBJECT-GROUP
        OBJECTS {
                cLWAWebAuthType,
                cLWAManufacturerLogo,
                cLWACustomLogoFileName,
                cLWACustomWebTitle,
                cLWACustomWebMessage,
                cLWACustomWebRedirectURL,
                cLWAExternalWebAuthURL,
                cLWAProxyRedirectMode,
                cLWAProxyRedirectPortNumber,
                cLWAWebAuthSecureWeb	
        }
        STATUS     current
        DESCRIPTION
                "This collection of objects is used for internal-
                default and internal-custom web-authentication. "
        ::= { ciscoLwappWebAuthMIBGroups 1 }

cLWAExternalWebAuthGroup OBJECT-GROUP
        OBJECTS {
                  cLWAExternalWebServerAddrType,
                  cLWAExternalWebServerAddr,
                  cLWAExternalWebServerRowStatus 
        }
        STATUS     current
        DESCRIPTION
                "This collection of objects is used for configuring
                Web servers for external web-authentication. "
        ::= { ciscoLwappWebAuthMIBGroups 2 }

cLWAGuestAccessNotifObjGroup OBJECT-GROUP
        OBJECTS { 
                cLWAGuestUserName
        }
        STATUS     current
        DESCRIPTION
                "This collection of objects are part of the Guest
                Access related notifications by the controller. "
        ::= { ciscoLwappWebAuthMIBGroups 3 }

        
cLWAGuestAccessNotifGroup NOTIFICATION-GROUP
        NOTIFICATIONS { 
                      cLWAGuestUserRemoved 
        }
        STATUS     current
        DESCRIPTION
                "These notifications are sent to the network
                management station to indicate the access status
                of guest users. "
        ::= { ciscoLwappWebAuthMIBGroups 4 }
   
END
