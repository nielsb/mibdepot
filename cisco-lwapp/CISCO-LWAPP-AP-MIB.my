-- *******************************************************************
-- CISCO-LWAPP-AP-MIB.my
-- January 2006, Devesh Pujari, Prasanna Viswakumar, Srinath Candadai
-- August 2010, Suja Thangaveluchamy
-- Copyright (c) 2006-2007, 2010-2012, 2016-2022 by Cisco Systems, Inc.
-- All rights reserved.
-- *******************************************************************

CISCO-LWAPP-AP-MIB DEFINITIONS ::= BEGIN

IMPORTS
    MODULE-IDENTITY,
    OBJECT-TYPE,
    NOTIFICATION-TYPE,
    Unsigned32,
    Counter32,
    Counter64,
    TimeTicks,
    Gauge32,
    Integer32
        FROM SNMPv2-SMI
    MODULE-COMPLIANCE,
    NOTIFICATION-GROUP,
    OBJECT-GROUP
        FROM SNMPv2-CONF
    TruthValue,
    MacAddress,
    TimeInterval,
    RowStatus,
    TimeStamp,
    DateAndTime
        FROM SNMPv2-TC
    SnmpAdminString
        FROM SNMP-FRAMEWORK-MIB
    PhysicalIndex
        FROM ENTITY-MIB
    InetAddressType,
    InetAddress,
    InetPortNumber
        FROM INET-ADDRESS-MIB
    IANAifType
        FROM IANAifType-MIB
    CLApIfType,
    CLDot11Channel,
    CLApAssocFailureReason,
    CLApDot11RadioSubband,
    CLApDot11RadioRole,
    CLApMode
        FROM CISCO-LWAPP-TC-MIB
    cldRegulatoryDomain
        FROM CISCO-LWAPP-DOT11-MIB
    cLWlanIndex
        FROM CISCO-LWAPP-WLAN-MIB
    Unsigned64
        FROM CISCO-TC
    cLRFProfileHighDensityMaxRadioClients,
    cLRFProfileHDClientTrapThreshold
        FROM CISCO-LWAPP-RF-MIB
    ciscoMgmt
        FROM CISCO-SMI;


-- ********************************************************************
-- *  MODULE IDENTITY
-- ********************************************************************

ciscoLwappApMIB MODULE-IDENTITY
    LAST-UPDATED    "202110010000Z"
    ORGANIZATION    "Cisco Systems Inc."
    CONTACT-INFO
            "Cisco Systems,
            Customer Service

            Postal: 170 West Tasman Drive
            San Jose, CA  95134
            USA

            Tel: +1 800 553-NETS

            Email: cs-snmp@cisco.com"
    DESCRIPTION
        "This MIB is intended to be implemented on all those
        devices operating as Central Controllers (CC) that
        terminate the Light Weight Access Point Protocol
        tunnel from Light-weight LWAPP Access Points.

        This MIB provides configuration and status information
        about the 802.11 Access Points that have joined the
        controller.                 

        The relationship between CC and the LWAPP APs
        can be depicted as follows:

        +......+     +......+     +......+           +......+
        +      +     +      +     +      +           +      +
        +  CC  +     +  CC  +     +  CC  +           +  CC  +
        +      +     +      +     +      +           +      +
        +......+     +......+     +......+           +......+
        ..            .             .                 .
        ..            .             .                 .
        .  .            .             .                 .
        .    .            .             .                 .
        .      .            .             .                 .
        .        .            .             .                 .
        +......+ +......+     +......+      +......+          +......+
        +      + +      +     +      +      +      +          +      +
        +  AP  + +  AP  +     +  AP  +      +  AP  +          +  AP  +
        +      + +      +     +      +      +      +          +      +
        +......+ +......+     +......+      +......+          +......+
        .              .             .                 .
        .  .              .             .                 .
        .    .              .             .                 .
        .      .              .             .                 .
        .        .              .             .                 .
        +......+ +......+     +......+      +......+          +......+
        +      + +      +     +      +      +      +          +      +
        +  MN  + +  MN  +     +  MN  +      +  MN  +          +  MN  +
        +      + +      +     +      +      +      +          +      +
        +......+ +......+     +......+      +......+          +......+


        The LWAPP tunnel exists between the controller and
        the APs.  The MNs communicate with the APs through
        the protocol defined by the 802.11 standard.

        LWAPP APs, upon bootup, discover and join one of the
        controllers and the controller pushes the configuration,
        that includes the WLAN parameters, to the LWAPP APs.
        The APs then encapsulate all the 802.11 frames from
        wireless clients inside LWAPP frames and forward
        the LWAPP frames to the controller.

                           GLOSSARY

        Access Point ( AP )

        An entity that contains an 802.11 medium access
        control ( MAC ) and physical layer ( PHY ) interface
        and provides access to the distribution services via
        the wireless medium for associated clients.  

        LWAPP APs encapsulate all the 802.11 frames in
        LWAPP frames and sends it to the controller to which
        it is logically connected.


        Bluetooth Low Energy  (BLE)

        Bluetooth Low Energy is a light-weight subset of classic
        bluetooth which is added in Hyper Action Location (HALO) 
        enabled APs to make use of BLE beacons to communicate 
        with wireless clients at short range.


        Basic Service Set Identifier (BSSID)

        The identifier for the service set comprising of
        all the 802.11 stations under the control of
        one coordinating Access Point.  This identifier
        happens to be the MAC address of the dot11 radio
        interface of the Access Point.  The wireless
        clients that associate with the Access Point
        get the wired uplink through this particular 
        dot11 interface. 

        Central Controller ( CC )

        The central entity that terminates the LWAPP protocol
        tunnel from the LWAPP APs.  Throughout this MIB,
        this entity also referred to as 'controller'. 

        Hyper Action Location (HALO)

         This is an external module for Cisco Access Points,
        which is responsible for high accuracy indoor 
        location. It includes smart antenna and new software
        interfaces to enable high accuracy indoor location.        

        iBeacon

        This is a low-cost transmitter which can transmit 
        its own unique identification number to the local 
        area.        

        Light Weight Access Point Protocol ( LWAPP ) 

        This is a generic protocol that defines the 
        communication between the Access Points and the
        Central Controller. 

        Mobile Node ( MN )

        A roaming 802.11 wireless device in a wireless
        network associated with an access point. 

        Station Management (SMT)

        This term refers to the internal management of the
        802.11 protocol operations by the AP to work
        cooperatively with the other APs and 802.11
        devices in the network.

        Link Latency 

        Latency is round trip time between AP and controller.
        There is a continuous heart-beat between AP and 
        controller. AP calculates latency for each time and 
        sends to controller.

        AMSDU

        Aggregate MAC Service Data Unit. A structure containing 
        multiple MSDUs, transported within a single (unfragmented)  
        or multiple (fragmented) Data MPDU. 

        DTLS

        Datagram Transport Layer Security (DTLS) protocol provides 
        communications privacy for datagram protocols. The protocol 
        allows client/server applications to communicate in a way 
        that is designed to prevent eavesdropping, tampering, or 
        message forgery. 

        WIPS

        Wireless Intrusion Prevention System (WIPS) is a network device 
        that monitors the radio spectrum for the presence of 
        unauthorized access points (intrusion detection), and can 
        automatically take countermeasures (intrusion prevention).

        SE

        Spectrum Expert is an application software, which when 
        connected to Spectrum Intelligent Access Point, provides 
        detailed RF spectrum plots and data, and assist in diagnosing 
        network problems. 

        PPPOE

        Point-to-Point Protocol Over Ethernet provides a standard 
        method to build sessions for transporting multi-protocol 
        datagrams between point-to-point links over Ethernet.

        OEAP

        Office Extended Access Point provides a method to extend their 
        office network to outside the office premises like the employee 
        homes, thereby providing a seamless experience to the employee 
        irrespective of the location of the work. This solution should 
        also support having private SSID whose data need to be switched 
        at the AP itself.

        EWC 

        Embedded Wireless Controller on AP wireless network solution comprises of at
        least one 802.11ac Wave 2 Cisco Aironet Series access point 
        (AP) with an in-built software-based wireless controller (WLC)
        managing other APs in the network. The AP acting as the WLC is
        referred to as the master AP while the other APs in the Cisco 
        Embedded Wireless Controller network, which are managed by this master AP,
        are referred to as subordinate APs. In addition to acting as a
        WLC, the master AP also operates as an AP to serve clients along
        with the subordinate APs.

        FIPS

        Federal Information Processing Standards are a set of standards
        that describe document processing, encryption algorithms and
        other information technology standards for use within
        non-military government agencies and by government contractors
        and vendors who work with the agencies.

        LAG

        Link aggregation (LAG) is a partial implementation of the
        802.3ad port aggregation standard. It bundles all of the
        controller's distribution system ports into a single 802.3ad
        port channel. This reduces the number of IP addresses required
        to configure the ports on your controller. When LAG is enabled,
        the system dynamically manages port redundancy and load
        balances access points transparently to the user.

        CAPWAP

        The Control And Provisioning of Wireless Access Points (CAPWAP) 
        protocol is a standard, interoperable networking protocol that 
        enables a central wireless LAN Access Controller (AC) to manage 
        a collection of Wireless Termination Points (WTPs),
        more commonly known as Wireless Access Points.

        Flexible Radio Assignment

        The Flexible Radio Assignment feature allows either manual
        configuration of capable APs or for these APs to intelligently
        determine the operating role of the integrated radios based on
        the available RF environment. APs with flexible radio can
        automatically detect when a high number of devices are connected
        to a network and changes the dual radios in the access point
        from 2.4 GHz/5 GHz to 5 GHz/5 GHz to serve more clients.
        The AP performs this task while monitoring the network for
        security threats and RF Interference that may affect
        performance. Flexible Radio Assignment improves mobile user
        experience for high-density networks.
        
        XOR Radio

        XOR radio is a radio that can operate on both 2.4Ghz and 5Ghz
        bandwidth.

        REFERENCE

        [1] Part 11 Wireless LAN Medium Access Control ( MAC )
        and Physical Layer ( PHY ) Specifications.

        [2] Draft-obara-capwap-lwapp-00.txt, IETF Light 
        Weight Access Point Protocol."

    REVISION        "202206060000Z"
    DESCRIPTION
        "Added new table cLApWlanSlotStatsTable."
    REVISION        "202201010000Z"
    DESCRIPTION
        "Added following scalar object
        - cLApIndoorMode."
    REVISION        "202110010000Z"
    DESCRIPTION
        "Added following scalar object
        - clApImageUpgradeHttpsEnable.
        Added cLAp11axObssPdSrgCapable to cLAp11axRadioConfigTable
	Added ciscoLwappApRadioStuck to notification objects list"
   REVISION        "202106060000Z"
    DESCRIPTION
        "Added following scalar object
        - cLApAuthorizeApMacMethodList
        - cLApAuthorizeApSerialNumMethodList
        Addition of cLApRogueDot11RadioBand
        Added followig object to AP profile table
        - cLApProfileCountryCode
        - cLApProfileOeapRogueDetectionEnable
        - cLApProfileOeapEncryptionEnable
        - cLApProfileOeapLocalAccessEnable
        - cLApProfileOeapProvSsidEnable"
    REVISION        "202010260000Z"
    DESCRIPTION
        "Added below notification objects
        - cLApBrokenAntApName
        - cLApBrokenAntInfo
        Added below notification
        - ciscoLwappBrokenAntennaDetails"
    REVISION        "202010080000Z"
    DESCRIPTION
        "Deprecated below objects from cLApDot11IfTable
        - cLApDot11IfDualRadioOperation      
        - cLApDot11IfRadioRoleOperation        
        - cLApDot11IfRadioRole                 
        - cLApDot11IfDualRadioMode             
        - cLApDot11IfDualRadioCapable          
        - cLApDot11IfRadioFRACapable
        Deprecated compliance group ciscoLwappApMIBComplianceRev13
        Deprecated conformance group ciscoLwappApXorRadioGroupSup1        
        Added compliance group ciscoLwappApMIBComplianceRev14
        Added conformance group ciscoLwappApXorRadioGroupSup2
        Added few values to cLApDot11RadioMode
        Added slave enum to cLApDot11RadioSubType
        Added cLAp11axObssPdCapable in cLAp11axRadioConfigTable"
    REVISION        "202009290000Z"
    DESCRIPTION
        "Added following scalar object
        - cLApGlobalAPConnectCount
        Depecated following object in the cLApEntry table
        - cLApConnectCount
        Deprecated the following compliance groups
        - ciscoLwappApProfileGroupSup12                               
        - ciscoLwappApMIBComplianceRev12                                         
        Added following compliance groups
        - ciscoLwappApProfileGroupSup14                                        
        - ciscoLwappApMIBComplianceRev13"
    REVISION        "202004280000Z"
    DESCRIPTION
        "Added following scalar object
        - cLApGlobalAPAuditReport
        - cLApGlobalAPAuditReportInterval
        Added following objects to the cLApProfileEntry table
        - cLApProfilePersistentSsidBroadcastEnable
        - cLApProfileDhcpFallback
        Added few values to cLApLastRebootReason"
    REVISION        "202003310000Z"
    DESCRIPTION
        "Added following objects to the cLApDot11IfEntry table
        - cLApDot11IfDualRadioMode
        - cLApDot11IfDualRadioCapable
        - cLApDot11IfRadioFRACapable
        - cLApDot11IfDualRadioOperation
        - cLApDot11IfRadioRole
        - cLApDot11IfRadioRoleOperation
        Added following objects to the cLApProfileEntry table
        - cLApProfileWindowSize
        - cLApProfileCredentialGlobalSecretType
        - cLApProfileCredentialGlobalPasswordType
        - cLApProfile802dot1xSupplicantPasswordType
        - cLApProfileBssidEnableStats
        - cLApProfileBssidStatsFrequency"
    REVISION        "201911080000Z"
    DESCRIPTION
         "Addition of new table cLAPNtpInfoTable.
          Added new group ciscoLwappApNtpInfo.
          Added objects to compliance ciscoLwappApGroupSup9
             -cLAPNtpInfoState
             -cLAPNtpInfoStatus
             -cLAPNtpInfoStratum
             -cLAPNtpInfoLastSync
             -cLAPNtpInfoOffset
             -cLAPNtpInfoIPAddressType
             -cLAPNtpInfoIPAddress"
    REVISION        "201910160000Z"
    DESCRIPTION
        "Addition of following new table
        - cLAp11axRadioConfigTable
        Addition of following object to cLApDot11IfTable
         - cLApDot11IfPhyS80EightyChannelNumber
        Addition of cLApProfileHaloBleBeaconRowStatus to
          cLApProfileHaloBleBeaconTable to allow creation
          of entries."
    REVISION        "201906250000Z"
    DESCRIPTION
        "Added following object to the cLApProfileTable
        - cLApProfileClientRssiStatsEnabled                                     
        - cLApProfileClientRssiStatsReportInterval                              
        - cLApProfileGasRateLimitEnable                                         
        - cLApProfileGasRateLimitNumReqPerInterval                              
        - cLApProfileGasRateLimitIntervalMsec                                   
        - cLApProfileQoSMapApTrustsUpstreamDSCP                        
                Added following object to the CLApEntry table
                - cLApLagConfigStatus
                - cLApMonitorModeOptStatus
        Deprecated the following compliance group
                - ciscoLwappApProfileGroupSup1                               
        - ciscoLwappApMIBComplianceRev9                                         
        Added following compliance group
                - ciscoLwappApProfileGroupSup2                                        
        - ciscoLwappApMIBComplianceRev10"
    REVISION        "201904080000Z"
    DESCRIPTION
        "Deprecatred following entries
        - cLApProfileCredentialEnableGlobalCredentials
        - cLApProfileOeapDisableLocalAccess
        - cLApProfileRadioInterfaceShutdownEnabled
        - cLApProfileEthernetInterfaceDowntime
        - cLApProfile802dot1xAuthenticationEnabled
        - cLApProfileVlanTagging
        - cLApProfileApCountryCode
         Updated cLApDot11IfAntennaId range"
    REVISION        "201809170000Z"
    DESCRIPTION
         "Addition of following new table
            - cLApProfileTable
            - cLApProfileHaloBleBeaconTable
            - cLApPacketCaptureProfileTable
            - cLApPacketCaptureClientTable
            - cLApPacketCaptureApTable
         Added following object to the cLApTable
            - cLApModeClear
            - cLApSiteTagName
            - cLApRfTagName
            - cLApPolicyTagName
            - cLApTagSource
            - cLApUsbModuleName
            - cLApUsbModuleState
            - cLApUsbModuleProductId
            - cLApUsbDescription
            - cLApUsbStateInfo
            - cLApUsbOverride
            - cLApUsbSerialNumber
            - cLApUsbMaxPower
         Added following object to the cLApBleBeaconTable
            - cLApBleBeaconAdvTxPower
         Added following scalar object
            - cLApAuthorizeApMacAuth
            - cLApAuthorizeApSerialNumAuth
            - cLApAuthorizeApMethodList
         deprecated the following compliance group
            - ciscoLwappApMIBComplianceRev7
         Added following compliance group
            - ciscoLwappApMIBComplianceRev8
         Added following conformance group
            - ciscoLwappApProfileHaloBleGroup
            - ciscoLwappApProfileGroup
            - ciscoLwappApPacketCaptureProfileGroup
            - ciscoLwappApPacketCaptureClientProfileGroup."
    REVISION        "201807260000Z"
    DESCRIPTION
        "Added following objects to cLApDot11IfTable :
        - cLApFraSuggestedMode
        - cLApFraCoverageOverlapFactor."
    REVISION        "201806260000Z"
    DESCRIPTION
        "Added enums bleTxRx and bleRxOnly to cLApDot11RadioSubType."
    REVISION        "201804240101Z"
    DESCRIPTION
        "Added the following objects
        -  cLApGlobal802dot1xSupplicantEapType
        -  cLAp802dot1xSupplicantOverrideEapType"
    REVISION        "201804240000Z"
    DESCRIPTION
        "Added the following deprecated objects to
        ciscoLwappApGroupSup4 :
        -  cLApExtensionChannel
        -  cLAdjChannelRogueEnabled
        -  cLApWipsEnable
        -  cLApNwLegacyBeamForming."
    REVISION        "201803280000Z"
    DESCRIPTION
        "Added new object cLApDot11axSupport to the table
        cLApDot11IfTable.
        Added new group ciscoLwappApGroupSup11."
    REVISION        "201707070000Z"
    DESCRIPTION
        "Updated the descriptions."
    REVISION        "201705070000Z"
    DESCRIPTION
        "Added attribute cLApSecureCipher.
        Added global attribute cLApGlobalMaxApsSupported."
    REVISION        "201608300000Z"
    DESCRIPTION
        "Added following objects to cLApDot11IfTable :
        - cLApDot11XorRadioMode     
        - cLApDot11XorRadioBand     
        - cLApDot11XorRadioRoleAssignment
        Added onesixty enum option to cLAp11ChannelBandwidth.
        Added enums remoteLan and xorTxRx to cLApDot11RadioSubType.
        Added cLApDot11XorRadioRoleChangeReason,
        ciscoLwappRadioRoleChangeNotify and 
        ciscoLwappXorRadioRoleChangeEnabled.
        Added following new groups 
         - ciscoLwappApXorRadioGroup.
         - ciscoLwappApNotifsXorGroup."
    REVISION        "201604070000Z"
    DESCRIPTION
        "Added new object cLApLEDState to the table
        cLApTable.
        Addition of new tables cLAplanStatsTable, cLHaloBleBeaconTable 
        and cLApBleBeaconTable."
    REVISION        "201509210000Z"
    DESCRIPTION
        "Added new object cLApLEDState to the table
        cLApTable.
        Addition of new table cLAplanStatsTable as part of VLAN tagging
        feature.
        Added  cLApIsUniversal and cLApUniversalPrimeStatus  objects to
        cLApTable."
    REVISION        "201407150000Z"
    DESCRIPTION
        "Add new enumeration twentyFiveDotFive(7)
        to cLApPowerStatus. 
        Added following OBJECT-GROUP 
        - ciscoLwappApGroupSup8 
        - ciscoLwappApNotifsGroupVer2 
        - ciscoLwappApGroupSup9 
        - ciscoLwappApRadioGroupSup1"
    REVISION        "201206130000Z"
    DESCRIPTION
        "Added ciscoLwappDot11IfAntennaGroup and
        ciscoLwappRetransmitGroup"
    REVISION        "201102070000Z"
    DESCRIPTION
        "Addressed Approver's comments."
    REVISION        "201101210000Z"
    DESCRIPTION
        "Addressed reviwer's comments."
    REVISION        "201101100000Z"
    DESCRIPTION
        "Addressed reviewer's comments."
    REVISION        "201012130000Z"
    DESCRIPTION
        "Addressed Reviwer's comments"
    REVISION        "201008190000Z"
    DESCRIPTION
        "Added cLApGlobal, cLApCredentials, cLSpectrum,
        cLAp802dot1xSupplicant mib objects.
        Added link latency tables, cLApEncryptionEnable.
        cLApDot11RadioTable have been added to provide support
        for subband radios.
        AP uptime, join time, join taken time and Ethernet slot info
        have been added to clApTable.  cLApEthernetIfTable which
        provides Ethernet interface status and statistics information
        has been added.
        The group ciscoLwappApGroupSup3, ciscoLwappApGroupSup4,
        ciscoLwappApNotifObjsGroup and ciscoLwappApNotifsGroup 
        have been added."
    REVISION        "200701030000Z"
    DESCRIPTION
        "The object cLApName has been added."
    REVISION        "200607180000Z"
    DESCRIPTION
        "Added cLApEntPhysicalIndex object."
    REVISION        "200603300000Z"
    DESCRIPTION
        "Initial version of this MIB module."
    ::= { ciscoMgmt 513 }


ciscoLwappApMIBNotifs  OBJECT IDENTIFIER
    ::= { ciscoLwappApMIB 0 }

ciscoLwappApMIBObjects  OBJECT IDENTIFIER
    ::= { ciscoLwappApMIB 1 }

ciscoLwappApMIBConform  OBJECT IDENTIFIER
    ::= { ciscoLwappApMIB 2 }

ciscoLwappApMIBNotifObjects  OBJECT IDENTIFIER
    ::= { ciscoLwappApMIB 3 }

ciscoLwappAp  OBJECT IDENTIFIER
    ::= { ciscoLwappApMIBObjects 1 }

ciscoLwappApIf  OBJECT IDENTIFIER
    ::= { ciscoLwappApMIBObjects 2 }

ciscoLwappApGlobal  OBJECT IDENTIFIER
    ::= { ciscoLwappApMIBObjects 3 }

ciscoLwappApCredentials  OBJECT IDENTIFIER
    ::= { ciscoLwappApMIBObjects 4 }

ciscoLwappLinkLatency  OBJECT IDENTIFIER
    ::= { ciscoLwappApMIBObjects 5 }

ciscoLwappSpectrum  OBJECT IDENTIFIER
    ::= { ciscoLwappApMIBObjects 6 }

ciscoLwappAp802dot1xSupplicant  OBJECT IDENTIFIER
    ::= { ciscoLwappApMIBObjects 7 }

ciscoLwappApWlanStats  OBJECT IDENTIFIER
    ::= { ciscoLwappApMIBObjects 9 }

ciscoLwappApWlanInfo  OBJECT IDENTIFIER
    ::= { ciscoLwappApMIBObjects 10 }

ciscoLwappPacketDumpInfo  OBJECT IDENTIFIER
    ::= { ciscoLwappApMIBObjects 11 }

ciscoLwappAplanStats  OBJECT IDENTIFIER
    ::= { ciscoLwappApMIBObjects 12 }

ciscoLwappApGlobalBleBeacon  OBJECT IDENTIFIER
    ::= { ciscoLwappApMIBObjects 13 }

ciscoLwappApHyperlocation  OBJECT IDENTIFIER
    ::= { ciscoLwappApMIBObjects 14 }

ciscoLwappApSecureCipher  OBJECT IDENTIFIER
    ::= { ciscoLwappApMIBObjects 15 }

ciscoLwappApProfile  OBJECT IDENTIFIER
    ::= { ciscoLwappApMIBObjects 16 }

ciscoLwappApPacketCapture  OBJECT IDENTIFIER
    ::= { ciscoLwappApMIBObjects 17 }

ciscoLwappApNtpInfo  OBJECT IDENTIFIER
    ::= { ciscoLwappApMIBObjects 18 }
ciscoLwappAp11axRadioConfig  OBJECT IDENTIFIER
    ::= { ciscoLwappApMIBObjects 21 }

ciscoLwappApSlotWlanStats  OBJECT IDENTIFIER
    ::= { ciscoLwappApMIBObjects 22 }

-- ********************************************************************
-- APs that have joined the controller
-- ********************************************************************

cLApTable OBJECT-TYPE
    SYNTAX          SEQUENCE OF CLApEntry 
    MAX-ACCESS      not-accessible
    STATUS          current
    DESCRIPTION
        "This table represents the information about the
        802.11 LWAPP Access Points that have joined the
        controller.

        LWAPP APs exchange configuration messages with the
        controller and get the required configuration for
        their 802.11 related operations, after they join the
        controller."
    ::= { ciscoLwappAp 1 }

cLApEntry OBJECT-TYPE
    SYNTAX          CLApEntry
    MAX-ACCESS      not-accessible
    STATUS          current
    DESCRIPTION
        "Each entry in this table provides information about
        one 802.11 LWAPP Access Point that has joined the
        controller.

        Entries are removed when the APs lose their
        association with the controller due to loss
        of communication."
    INDEX           { cLApSysMacAddress } 
    ::= { cLApTable 1 }

CLApEntry ::= SEQUENCE {
        cLApSysMacAddress                  MacAddress,
        cLApIfMacAddress                   MacAddress,
        cLApMaxNumberOfDot11Slots          Unsigned32,
        cLApEntPhysicalIndex               PhysicalIndex,
        cLApName                           SnmpAdminString,
        cLApUpTime                         TimeTicks,
        cLLwappUpTime                      TimeTicks,
        cLLwappJoinTakenTime               TimeTicks,
        cLApMaxNumberOfEthernetSlots       Unsigned32,
        cLApPrimaryControllerAddressType   InetAddressType,
        cLApPrimaryControllerAddress       InetAddress,
        cLApSecondaryControllerAddressType InetAddressType,
        cLApSecondaryControllerAddress     InetAddress,
        cLApTertiaryControllerAddressType  InetAddressType,
        cLApTertiaryControllerAddress      InetAddress,
        cLApLastRebootReason               INTEGER,
        cLApEncryptionEnable               TruthValue,
        cLApFailoverPriority               INTEGER,
        cLApPowerStatus                    INTEGER,
        cLApTelnetEnable                   TruthValue,
        cLApSshEnable                      TruthValue,
        cLApPreStdStateEnabled             TruthValue,
        cLApPwrInjectorStateEnabled        TruthValue,
        cLApPwrInjectorSelection           INTEGER,
        cLApPwrInjectorSwMacAddr           MacAddress,
        cLApWipsEnable                     TruthValue,
        cLApMonitorModeOptimization        INTEGER,
        cLApDomainName                     SnmpAdminString,
        cLApNameServerAddressType          InetAddressType,
        cLApNameServerAddress              InetAddress,
        cLApAMSDUEnable                    TruthValue,
        cLApEncryptionSupported            TruthValue,
        cLApRogueDetectionEnabled          TruthValue,
        cLApTcpMss                         Integer32,
        cLApDataEncryptionStatus           TruthValue,
        cLApNsiKey                         SnmpAdminString,
        cLApAdminStatus                    TruthValue,
        cLApPortNumber                     InetPortNumber,
        cLApRetransmitCount                Unsigned32,
        cLApRetransmitTimeout              Unsigned32,
        cLApVenueConfigVenueGroup          INTEGER,
        cLApVenueConfigVenueType           INTEGER,
        cLApVenueConfigVenueName           SnmpAdminString,
        cLApVenueConfigLanguage            SnmpAdminString,
        cLApLEDState                       TruthValue,
        cLApTrunkVlan                      Unsigned32,
        cLApTrunkVlanStatus                TruthValue,
        cLApLocation                       SnmpAdminString,
        cLApSubMode                        INTEGER,
        cLApAssocCount                     Unsigned32,
        cLApAssocFailResourceCount         Unsigned32,
        cLApRealTimeStatsModeEnabled       TruthValue,
        cLApAssociatedClientCount          Unsigned32,
        cLApMemoryCurrentUsage             Unsigned32,
        cLApMemoryAverageUsage             Unsigned32,
        cLApCpuCurrentUsage                Unsigned32,
        cLApCpuAverageUsage                Unsigned32,
        cLApUpgradeFromVersion             SnmpAdminString,
        cLApUpgradeToVersion               SnmpAdminString,
        cLApUpgradeFailureCause            SnmpAdminString,
        cLApMaxClientLimitNumberTrap       Unsigned32,
        cLApMaxClientLimitCause            SnmpAdminString,
        cLApMaxClientLimitSet              TruthValue,
        cLApFloorLabel                     Unsigned64,
        cLApConnectCount                   Unsigned32,
        cLApReassocSuccCount               Counter32,
        cLApReassocFailCount               Counter32,
        cLAdjChannelRogueEnabled           TruthValue,
        cLApAssocFailCountByRate           Unsigned32,
        cLApAbnormalOfflineCount           Unsigned32,
        cLApActiveClientCount              Unsigned32,
        cLApAssocFailCountForRssiLow       Unsigned32,
        cLApSysNetId                       SnmpAdminString,
        cLApAssocFailTimes                 Counter32,
        cLApAntennaBandMode                INTEGER,
        cLApHeartBeatRspAvgTime            Integer32,
        cLApEchoRequestCount               Counter32,
        cLApEchoResponseLossCount          Counter32,
        cLApModuleInserted                 SnmpAdminString,
        cLApEnableModule                   TruthValue,
        cLApIsUniversal                    TruthValue,
        cLApUniversalPrimeStatus           SnmpAdminString,
        cLApIsMaster                       TruthValue,
        cLApBleFWDownloadStatus            TruthValue,
        cLApDot11XorDartConnectorStatus    SnmpAdminString,
        cLApCtsSxpDefaultPassword          SnmpAdminString,
        cLApCtsSxpState                    TruthValue,
        cLApCtsSxpMode                     TruthValue,
        cLApCtsSxpListenerMinHoldtime      Unsigned32,
        cLApCtsSxpListenerMaxHoldtime      Unsigned32,
        cLApCtsSxpReconcilePeriod          Unsigned32,
        cLApCtsSxpRetryPeriod              Unsigned32,
        cLApCtsSxpSpeakerHoldTime          Unsigned32,
        cLApCtsSxpSpeakerKeepAlive         Unsigned32,
        cLApCtsInlineTagStatus             TruthValue,
        cLApCtsSgaclStatus                 TruthValue,
        cLApCtsOverrideStatus              TruthValue,
        cLApModeClear                      TruthValue,
        cLApSiteTagName                    SnmpAdminString,
        cLApRfTagName                      SnmpAdminString,
        cLApPolicyTagName                  SnmpAdminString,
        cLApTagSource                      INTEGER,
        cLApUsbModuleName                  SnmpAdminString,
        cLApUsbModuleState                 SnmpAdminString,
        cLApUsbModuleProductId             SnmpAdminString,
        cLApUsbDescription                 SnmpAdminString,
        cLApUsbStateInfo                   TruthValue,
        cLApUsbOverride                    TruthValue,
        cLApUsbSerialNumber                SnmpAdminString,
        cLApUsbMaxPower                    Unsigned32,
        cLApLagConfigStatus                TruthValue,
        cLApMonitorModeOptStatus           TruthValue,
        cLApFilterName                     SnmpAdminString
}

cLApSysMacAddress OBJECT-TYPE
    SYNTAX          MacAddress
    MAX-ACCESS      not-accessible
    STATUS          current
    DESCRIPTION
        "This object represents the radio MAC address
        common to the dot11 interfaces of the AP
        and uniquely identifies an entry in this table." 
    ::= { cLApEntry 1 }

cLApIfMacAddress OBJECT-TYPE
    SYNTAX          MacAddress
    MAX-ACCESS      read-only
    STATUS          current
    DESCRIPTION
        "This object represents the Ethernet MAC address of
        the AP." 
    ::= { cLApEntry 2 }

cLApMaxNumberOfDot11Slots OBJECT-TYPE
    SYNTAX          Unsigned32
    MAX-ACCESS      read-only
    STATUS          current
    DESCRIPTION
        "This object represents the maximum number of
        802.11 radio interface slots in this AP." 
    ::= { cLApEntry 3 }

cLApEntPhysicalIndex OBJECT-TYPE
    SYNTAX          PhysicalIndex
    MAX-ACCESS      read-only
    STATUS          current
    DESCRIPTION
        "This object provides the index value in the
        entPhysicalEntry corresponding to this AP." 
    ::= { cLApEntry 4 }

cLApName OBJECT-TYPE
    SYNTAX          SnmpAdminString (SIZE  (0..32))
    MAX-ACCESS      read-write
    STATUS          current
    DESCRIPTION
        "This object specifies the administrative name
        assigned to the AP by the user. If an AP is not configured, 
        its factory default name will be ap:<last three byte 
        of MACAddress> eg. ap:af:12:be." 
    ::= { cLApEntry 5 }

cLApUpTime OBJECT-TYPE
    SYNTAX          TimeTicks
    MAX-ACCESS      read-only
    STATUS          current
    DESCRIPTION
        "This object represents the time in hundredths
        of a second since the last time the AP rebooted." 
    ::= { cLApEntry 6 }

cLLwappUpTime OBJECT-TYPE
    SYNTAX          TimeTicks
    MAX-ACCESS      read-only
    STATUS          current
    DESCRIPTION
        "This object represents the time in hundredths
        of a second since the last time the AP joined 
        the controller." 
    ::= { cLApEntry 7 }

cLLwappJoinTakenTime OBJECT-TYPE
    SYNTAX          TimeTicks
    MAX-ACCESS      read-only
    STATUS          current
    DESCRIPTION
        "This object represents the time taken in hundredths
        of a second for the AP to join the controller. This 
        could be a significant value in Mesh environments." 
    ::= { cLApEntry 8 }

cLApMaxNumberOfEthernetSlots OBJECT-TYPE
    SYNTAX          Unsigned32
    MAX-ACCESS      read-only
    STATUS          current
    DESCRIPTION
        "This object represents the maximum number of
        Ethernet slots in this AP." 
    ::= { cLApEntry 9 }

cLApPrimaryControllerAddressType OBJECT-TYPE
    SYNTAX          InetAddressType
    MAX-ACCESS      read-write
    STATUS          current
    DESCRIPTION
        "This object specifies the type of the primary
        controller's address made available through 
        cLApPrimaryControllerAddress." 
    ::= { cLApEntry 10 }

cLApPrimaryControllerAddress OBJECT-TYPE
    SYNTAX          InetAddress
    MAX-ACCESS      read-write
    STATUS          current
    DESCRIPTION
        "This object specifies the address of the primary
        controller that the APs will join." 
    ::= { cLApEntry 11 }

cLApSecondaryControllerAddressType OBJECT-TYPE
    SYNTAX          InetAddressType
    MAX-ACCESS      read-write
    STATUS          current
    DESCRIPTION
        "This object specifies the type of the secondary
        controller's address made available through 
        cLApSecondaryControllerAddress." 
    ::= { cLApEntry 12 }

cLApSecondaryControllerAddress OBJECT-TYPE
    SYNTAX          InetAddress
    MAX-ACCESS      read-write
    STATUS          current
    DESCRIPTION
        "This object specifies the address of the secondary
        controller that the APs will join." 
    ::= { cLApEntry 13 }

cLApTertiaryControllerAddressType OBJECT-TYPE
    SYNTAX          InetAddressType
    MAX-ACCESS      read-write
    STATUS          current
    DESCRIPTION
        "This object specifies the type of the tertiary
        controller's address made available through 
        cLApTertiaryControllerAddress." 
    ::= { cLApEntry 14 }

cLApTertiaryControllerAddress OBJECT-TYPE
    SYNTAX          InetAddress
    MAX-ACCESS      read-write
    STATUS          current
    DESCRIPTION
        "This object specifies the address of the tertiary
        controller that the APs will join." 
    ::= { cLApEntry 15 }

cLApLastRebootReason OBJECT-TYPE
    SYNTAX          INTEGER  {
                        none(0),
                        dot11gModeChange(1),
                        ipAddressSet(2),
                        ipAddressReset(3),
                        rebootFromController(4),
                        dhcpFallbackFail(5),
                        discoveryFail(6),
                        noJoinResponse(7),
                        denyJoin(8),
                        noConfigResponse(9),
                        configController(10),
                        imageUpgradeSuccess(11),
                        imageOpcodeInvalid(12),
                        imageCheckSumInvalid(13),
                        imageDataTimeout(14),
                        configFileInvalid(15),
                        imageDownloadError(16),
                        rebootFromConsole(17),
                        rapOverAir(18),
                        powerLow(19),
                        crash(20),
                        powerHigh(21),
                        powerLoss(22),
                        powerChange(23),
                        componentFailure(24),
                        watchdog(25),
                        lscEnabled(26),
                        lscDisabled(27),
                        lscProvTimeout(28),
                        lscMaxProvReqRetries(29),
                        lscLoadFailure(30),
                        lscJoinFailure(31),
                        capwapTimerFailure(32),
                        staticIpFailover(33),
                        vlanTagFailover(34),
                        capwapDiscoveryRequest(35),
                        capwapDiscoveryResponse(36),
                        capwapJoinRequest(37),
                        capwapJoinResponse(38),
                        capwapConfigurationStatus(39),
                        capwapConfigurationStatusResponse(40),
                        capwapConfigurationUpdateRequest(41),
                        capwapConfigurationUpdateResponse(42),
                        capwapWtpEventRequest(43),
                        capwapWtpEventResponse(44),
                        capwapChangeStateEventRequest(45),
                        capwapChangeStateEventResponse(46),
                        capwapEchoRequest(47),
                        capwapEchoResponse(48),
                        capwapImageDataRequest(49),
                        capwapImageDataResponse(50),
                        capwapResetRequest(51),
                        capwapResetResponse(52),
                        capwapPrimaryDiscoveryRequest(53),
                        capwapPrimaryDiscoveryResponse(54),
                        capwapDataTransferRequest(55),
                        capwapDataTransferResponse(56),
                        capwapClearConfigurationRequest(57),
                        capwapClearConfigurationResponse(58),
                        capwapMobileConfigurationRequest(59),
                        capwapMobileConfigurationResponse(60),
                        capwapPathMtuRequest(61),
                        capwapPathMtuResponse(62),
                        vlanTagRetry(63),
                        ipv6AddrSet(64),
                        modeChange(65),
                        typeChangedToCapwap(66),
                        typeChangedToMe(67),
                        eraseCfgCommand(68),
                        oeapModeCfgUpload(69),
                        lagCfg(70),
                        fipsModeChange(71),
                        diminishedPowerChange(72),
                        slubDebug(73),
                        lscModeCapwap(74),
                        lscModeDot1x(75),
                        lscModeAll(76),
                        apTypeCloud(77),
                        dtlsInitFailure(78),
                        pnpNoCapwapBackOff(79),
                        day0CfgFail(80),
                        day1CfgFail(81),
                        pnpTriggeredReload(82),
                        triRadioSupport(83),
                        indoorDeployment(84),
                        apTypeWgbToCapwap(85),
                        apTypeCloudToCapwap(86),
                        apTypeWgb(87)
                    }
    MAX-ACCESS      read-only
    STATUS          current
    DESCRIPTION
        "This object represents the reason for the last
        reboot of the AP.
                 none                 - ap reported a reboot reason code
                                        unknown to the controller.
                 dot11gModeChange     - 11g mode change
                 ipAddressSet         - set static ip address
                 ipAddressReset       - reset static ip address
                 rebootFromController - ap reboot initiated 
                                        from controller
                 dhcpFallbackFail     - could not fallback to dhcp
                 discoveryFail        - could not send discovery
                 noJoinResponse       - did not receive join response
                 denyJoin             - deny join attempt at 
                                        the controller
                 noConfigResponse     - did not get config response
                 configController     - found configured or master 
                                        controller
                 imageUpgradeSuccess  - image upgraded successfully
                 imageOpcodeInvalid   - invalid image data opcode
                 imageCheckSumInvalid - invalid image md5 checksum
                 imageDataTimeout     - image data message timeout
                 configFileInvalid    - invalid config file
                 imageDownloadError   - image download process error
                 rebootFromConsole    - reboot command from ap console
                 rapOverAir           - root access point is connected 
                                        over the air
                 brownout             - ap rebooted due to power failure
                 powerLow             - ap rebooted dued to low power
                                        also called as brownout
                 crash                - crashed due to software failure
                 powerHigh            - rebooted due to power spike
                 powerLoss            - rebooted due to power loss
                 powerChange          - rebooted due to change in 
                                        power source
                 componentFailure     - rebooted due to component 
                                        failure
                 watchdog             - rebooted due to watch dog 
                                        timer reset.
                 lscEnabled  - rebooted as LSC was enabled
                 lscDisabled - rebooted as LSC was disabled
                 lscProvTimeout - rebooted due to LSC provision timeout
                 lscMaxProvReqRetries - rebooted due to maximum retries
                                 of LSC provision request
                 lscLoadFailure - rebooted due to LSC load failure
                 lscJoinFailure - rebooted due to LSC join failure.
                 capwapTimerFailure - rebooted due to capwap timer
                                    failure
                 staticIpFailover - rebooted due to static IP failover
                 vlanTagFailover - rebooted due to vlan tag failover
                 capwapDiscoveryRequest - link failure while processing
                                         capwap discovery request
                 capwapDiscoveryResponse - link failure while processing
                                         capwap discovery response
                 capwapJoinRequest     - rebooted due to capwap
                                          join request
                 capwapJoinResponse    - rebooted due to capwap
                                          join response
                 capwapConfigurationStatus- rebooted due to capwap
                                            configuration status request
                 capwapConfigurationStatusResponse - rebooted due to 
                                   capwap configuration status response
                 capwapConfigurationUpdateRequest- rebooted due to 
                                   capwap configuration update request
                 capwapConfigurationUpdateResponse - rebooted due to 
                                   capwap configuration update response
                 capwapWtpEventRequest - rebooted due to capwap WTP
                                            event request
                 capwapWtpEventResponse - rebooted due to capwap WTP
                                            event response
                 capwapChangeStateEventRequest - rebooted due to capwap
                                         change state event request
                 capwapChangeStateEventResponse - rebooted due to capwap
                                         change state event response
                 capwapEchoRequest      - rebooted due to capwap 
                                          echo request
                 capwapEchoResponse     - rebooted due to capwap
                                          echo response
                 capwapImageDataRequest - rebooted due to capwap
                                            image data request
                 capwapImageDataResponse - rebooted due to capwap
                                            image data response
                 capwapResetRequest - rebooted due to capwap 
                                            reset request
                 capwapResetResponse - rebooted due to capwap
                                            reset response
                 capwapPrimaryDiscoveryRequest - rebooted due to capwap
                                        primary discovery request
                 capwapPrimaryDiscoveryResponse - rebooted due to capwap
                                        primary discovery response
                 capwapDataTransferRequest - rebooted due to capwap
                                        data transfer request
                 capwapDataTransferResponse - rebooted due to capwap
                                        data transfer response
                 capwapClearConfigurationRequest-rebooted due to capwap
                                        clear configuration request
                 capwapClearConfigurationResponse-rebooted due to capwap
                                        clear configuration response
                 capwapMobileConfigurationRequest-rebooted due to capwap
                                        mobile configuration request
                 capwapMobileConfigurationResponse-rebooted due to 
                                        capwap mobile configuration 
                                        response
                 capwapPathMtuRequest   - rebooted due to capwap
                                          path MTU request
                 capwapPathMtuResponse  - rebooted due to capwap
                                          path MTU response. 
                 vlanTagRetry - rebooted due to vlan tag retry
                 ipv6AddrSet - rebooted due to setting of static ipv6 
                                        address
                 modeChange - rebooted due to mode change
                 typeChangedToCapwap - rebooted due to type changed from
                                        EWC(Embedded Wireless Controller) to CAPWAP
                 typeChangedToMe - rebooted due to type changed from 
                                   CAPWAP to EWC(Embedded Wireless Controller)
                 eraseCfgCommand - rebooted due to erase config command
                 oeapModeCfgUpload - rebooted due to OEAP(Office
                              Extended Access Point) mode config upload
                 lagCfg - rebooted due to LAG(Link Aggregate Group) 
                                    configuration change
                 fipsModeChange - rebooted due to FIPS(Federal 
                         Information Processing Standards) mode change
                 diminishedPowerChange - rebooted due to change in 
                                        diminished power
                 slubDebug - rebooted due to slub debug
                 lscModeCapwap - LSC for CAPWAP
                 lscModeDot1x - LSC for Dot1x
                 lscModeAll - LSC for all
                 apTypeCloud - AP type changed to cloud
                 dtlsInitFailure - DTLS init failure
                 pnpNoCapwapBackOff - In PNP, no CAPWAP backoff for more than 24hrs
                 day0CfgFail - Day 0 config failure
                 day1CfgFail - Day 1 config failure
                 pnpTriggeredReload - Reboot triggered by PnP server
                 triRadioSupport - Tri-radio support change
                 indoorDeployment - Indoor Deployment
                 apTypeWgbToCapwap - AP type changed from WGB to CAPWAP
                 apTypeCloudToCapwap - AP type changed from cloud to CAPWAP
                 apTypeWgb - AP type changed from CAPWAP to WGB"
    ::= { cLApEntry 16 }

cLApEncryptionEnable OBJECT-TYPE
    SYNTAX          TruthValue
    MAX-ACCESS      read-write
    STATUS          current
    DESCRIPTION
        "This object specifies whether encyrption between
        controller and AP is enabled or not. Encryption
        can only be enabled if ESM card in controller is 
        pluged in.

        A value of 'true' enables encryption between 
        controller and AP.

        A value of 'false' disables encryption between 
        controller and AP."
    DEFVAL          { false } 
    ::= { cLApEntry 18 }

cLApFailoverPriority OBJECT-TYPE
    SYNTAX          INTEGER  {
                        low(1),
                        medium(2),
                        high(3),
                        critical(4)
                    }
    MAX-ACCESS      read-write
    STATUS          current
    DESCRIPTION
        "This object specifies the AP failover priority
        for an AP. If a higher priority AP wishes to join 
        the controller, it will be given preference over 
        a join request from a lower priority AP. Also if the 
        number of AP joined has reached the limit that the 
        controller can support then the controller can disassociate
        an already joined lower priority AP. This priority will be 
        considered only if the cLApGlobalFailoverPriority is 
        Enabled on the controller.
        low - AP failover priority is low for this controller.
        medium - AP failover priority is medium for this controller.
        high - AP failover priority is high for this controller.
        critical - AP failover priority is critical for this 
        controller."
    DEFVAL          { low } 
    ::= { cLApEntry 19 }

cLApPowerStatus OBJECT-TYPE
    SYNTAX          INTEGER  {
                        low(1),
                        fifteendotfour(2),
                        sixteendoteight(3),
                        full(4),
                        external(5),
                        twentyfivedotfive(6),
                        mixedmode(7)
                    }
    MAX-ACCESS      read-only
    STATUS          current
    DESCRIPTION
        "This object represents the power status of the AP
        low             - The AP is drawing low power from 
                          Ethernet 
        fifteendotfour  - The AP is drawing 15.4 watts from 
                          Ethernet
        sixteendoteight - The AP is drawing 16.8 watts from
                          Ethernet
        twentyfivedotfive - The AP is drawing 25.5 watts from
                          Ethernet
        full            - The power is high enough for 
                          normal operation of the AP. 
                          The power source could be 
                          Ethernet or external
        external        - The power source is not from
                          Ethernet.
        mixedmode       - The power is high enough for 
              operation of AP. In this state 
              one radio will operate in full 
              power mode while the other radio 
              will be powered off or operate 
              at reduced capacity." 
    ::= { cLApEntry 20 }

cLApTelnetEnable OBJECT-TYPE
    SYNTAX          TruthValue
    MAX-ACCESS      read-write
    STATUS          current
    DESCRIPTION
        "This object specifies whether telnet session
        can be established to the AP. 

        A value of 'true' indicates an telnet session
        can be established to the AP. 

        A value of 'false' indicates an telnet session
        cannot be established to the AP."
    DEFVAL          { false } 
    ::= { cLApEntry 21 }

cLApSshEnable OBJECT-TYPE
    SYNTAX          TruthValue
    MAX-ACCESS      read-write
    STATUS          current
    DESCRIPTION
        "This object specifies whether SSH session
        can be established to the AP. 

        A value of 'true' indicates an SSH session
        can be established to the AP. 

        A value of 'false' indicates an SSH session
        cannot be established to the AP."
    DEFVAL          { false } 
    ::= { cLApEntry 22 }

cLApPreStdStateEnabled OBJECT-TYPE
    SYNTAX          TruthValue
    MAX-ACCESS      read-write
    STATUS          current
    DESCRIPTION
        "This object specifies whether the pre-standard state
        of the AP is enabled or disabled.

        A value of 'true' indicates that the pre-standard state
        of the AP is enabled,

        A value of 'false' indicates that the pre-standard state
        of the AP is disabled" 
    ::= { cLApEntry 23 }

cLApPwrInjectorStateEnabled OBJECT-TYPE
    SYNTAX          TruthValue
    MAX-ACCESS      read-write
    STATUS          current
    DESCRIPTION
        "This object specifies whether the power injector state
        of the AP is enabled or disabled.

        A value of 'true' indicates that the power injector state
        of the AP is enabled,

        A value of 'false' indicates that the power injector state
        of the AP is disabled" 
    ::= { cLApEntry 24 }

cLApPwrInjectorSelection OBJECT-TYPE
    SYNTAX          INTEGER  {
                        unknown(1),
                        installed(2),
                        override(3)
                    }
    MAX-ACCESS      read-write
    STATUS          current
    DESCRIPTION
        "This object specifies the power injector selection
        value of the AP.

        'unknown'   - is returned if 
              'cLApPwrInjectorStateEnabled'is set to false.
        'installed' - configure the MAC address of the 
              switch port that has a Power Injector.
        'override'  - override the safety checks and assume 
              a power injector is always installed." 
    ::= { cLApEntry 25 }

cLApPwrInjectorSwMacAddr OBJECT-TYPE
    SYNTAX          MacAddress
    MAX-ACCESS      read-write
    STATUS          current
    DESCRIPTION
        "This object specifies the MAC address of the
        switch port that has a power Injector and is 
        valid only when the 'cLApPwrInjectorSelection' 
        is in 'installed' mode.
        if SET to 00:00:00:00:00:00, AP will detect the 
        MAC address of the current switch port that has 
        a Power Injector" 
    ::= { cLApEntry 26 }

cLApWipsEnable OBJECT-TYPE
    SYNTAX          TruthValue
    MAX-ACCESS      read-write
    STATUS          deprecated
    DESCRIPTION
        "This object represents if this AP is used
        as WIPS AP.
        A value of 'true' indicates that this AP is
        a WIPS AP.
        A value of 'false' indicates that this AP is
        not a WIPS AP. This applies only when the 
        AP is either in local or monitor mode."
    DEFVAL          { false } 
    ::= { cLApEntry 27 }

cLApMonitorModeOptimization OBJECT-TYPE
    SYNTAX          INTEGER  {
                        all(1),
                        tracking(2),
                        wips(3),
                        none(4)
                    }
    MAX-ACCESS      read-write
    STATUS          current
    DESCRIPTION
        "This object specifies the monitor mode optimization
        on this device.
            all      - All optimization is enabled 
            tracking - Tracking is optimized 
            wips     - WIPS optimization is enabled
            none     - No optimization is enabled" 
    ::= { cLApEntry 28 }

cLApDomainName OBJECT-TYPE
    SYNTAX          SnmpAdminString
    MAX-ACCESS      read-write
    STATUS          current
    DESCRIPTION
        "This object specifies the domain, to which the AP belongs.
        This attribute can be configured only if the static IP
        option is turned on in the AP." 
    ::= { cLApEntry 29 }

cLApNameServerAddressType OBJECT-TYPE
    SYNTAX          InetAddressType
    MAX-ACCESS      read-write
    STATUS          current
    DESCRIPTION
        "This object specifies the type of the IP address of the
        name server, made available through cLApNameServerAddress." 
    ::= { cLApEntry 30 }

cLApNameServerAddress OBJECT-TYPE
    SYNTAX          InetAddress
    MAX-ACCESS      read-write
    STATUS          current
    DESCRIPTION
        "This object specifies the IP Address of the name server.
        This attribute can be configured only if the static IP
        option is turned on in the AP." 
    ::= { cLApEntry 31 }

cLApAMSDUEnable OBJECT-TYPE
    SYNTAX          TruthValue
    MAX-ACCESS      read-write
    STATUS          current
    DESCRIPTION
        "This object specifies the AMSDU status.
        A value of 'true' indicates AMSDU is enabled.
        A value of 'false' indicates AMSDU is disabled."
    DEFVAL          { false } 
    ::= { cLApEntry 32 }

cLApEncryptionSupported OBJECT-TYPE
    SYNTAX          TruthValue
    MAX-ACCESS      read-write
    STATUS          current
    DESCRIPTION
        "This object specifies whether AP Supports
        DTLS encryption.                 
        A value of 'true' indicates encryption is supported.
        A value of 'false' indicates encryption is not supported."
    DEFVAL          { false } 
    ::= { cLApEntry 33 }

cLApRogueDetectionEnabled OBJECT-TYPE
    SYNTAX          TruthValue
    MAX-ACCESS      read-write
    STATUS          current
    DESCRIPTION
        "This object specifies whether Rogue Detection
        is enabled in this AP.                 
        A value of 'true' indicates rogue detection is enabled.
        A value of 'false' indicates rogue detection is disabled.
        Rogue detection is not supported on sniffer 
        and rogue detector mode APs."
    DEFVAL          { false } 
    ::= { cLApEntry 34 }

cLApTcpMss OBJECT-TYPE
    SYNTAX          Integer32 (0 | 536..1363)
    MAX-ACCESS      read-write
    STATUS          current
    DESCRIPTION
        "This object specifies the TCP Maximum Segment Size
        for this AP.
        Permissible value are between 536 and 1363. This will
        also enable the TCP MSS flag for this AP.
        Value of 0 will disable the TCP MSS flag for this AP.
        Any change of value for cLApGlobalTcpMss will be 
        reflected to this object. 
        Value for this object can be change only when value of 
        cLApGlobalTcpMss is set as 0." 
    ::= { cLApEntry 35 }

cLApDataEncryptionStatus OBJECT-TYPE
    SYNTAX          TruthValue
    MAX-ACCESS      read-only
    STATUS          current
    DESCRIPTION
        "This object represents the data encryption
        status of AP.

        A value of 'true' indicates data is encrypted between
                        AP and WLC.

        A value of 'false' indicates data is plain text between
                        AP and WLC."
    DEFVAL          { false } 
    ::= { cLApEntry 36 }

cLApNsiKey OBJECT-TYPE
    SYNTAX          SnmpAdminString (SIZE  (0..32))
    MAX-ACCESS      read-only
    STATUS          current
    DESCRIPTION
        "This object represents the network spectrum interface key
        used when the AP is in spectrum expert Only monitor mode
        (SOMM).This object returns a non-zero value only when the 
        AP is SOMM mode." 
    ::= { cLApEntry 37 }

cLApAdminStatus OBJECT-TYPE
    SYNTAX          TruthValue
    MAX-ACCESS      read-write
    STATUS          current
    DESCRIPTION
        "This object specifies the admin state of the AP,
        A value of 'true' indicates AP admin status is up.
        A value of 'false' indicates AP admin status is down."
    DEFVAL          { false } 
    ::= { cLApEntry 38 }

cLApPortNumber OBJECT-TYPE
    SYNTAX          InetPortNumber
    MAX-ACCESS      read-only
    STATUS          current
    DESCRIPTION
        "This object represents the port number on which
        the AP's traffic is coming through." 
    ::= { cLApEntry 39 }

cLApRetransmitCount OBJECT-TYPE
    SYNTAX          Unsigned32
    UNITS           "retries"
    MAX-ACCESS      read-write
    STATUS          current
    DESCRIPTION
        "This object specifies the retransmission count for the access
        point control packet.This value specifies the number of packets
        retransmitted after which the Access Point falls back to another
        controller in case of failover.
        The global retransmit parameters are applicable for all access 
        points within a controller. The individual paramters per access 
        point, if configured takes precedence over the global values. 
        If an access point falls back from another controller(in case of
        failover), the values at the AP level has more precedence over 
        the global values in the controller with which it has joined." 
    ::= { cLApEntry 40 }

cLApRetransmitTimeout OBJECT-TYPE
    SYNTAX          Unsigned32
    UNITS           "seconds"
    MAX-ACCESS      read-write
    STATUS          current
    DESCRIPTION
        "This object specifies the retransmission timeout for the access
        point control packet. This value specifies the timeout for each
        retransmission, during the fallback of access point to another 
        controller in case of failover.
        The global retransmit parameters are applicable for all access 
        points within a controller. The individual paramters per access
        point, if configured takes precedence over the global values. 
        If an access point falls back from another controller(in case of
        failover), the values at the AP level has more precedence over 
        the global values in the controller with which it has joined." 
    ::= { cLApEntry 41 }

cLApVenueConfigVenueGroup OBJECT-TYPE
    SYNTAX          INTEGER  {
                        unspecified(1),
                        assembly(2),
                        business(3),
                        educational(4),
                        factoryAndIndustrial(5),
                        institutional(6),
                        mercantile(7),
                        residential(8),
                        storage(9),
                        utilityAndMisc(10),
                        vehicular(11),
                        outdoor(12)
                    }
    MAX-ACCESS      read-write
    STATUS          current
    DESCRIPTION
        "This object specifies the venue group
        for this WLAN."
    DEFVAL          { unspecified } 
    ::= { cLApEntry 42 }

cLApVenueConfigVenueType OBJECT-TYPE
    SYNTAX          INTEGER  {
                        unspecified(1),
                        unspecifiedAssembly(2),
                        arena(3),
                        stadium(4),
                        passengerTerminal(5),
                        amphitheater(6),
                        amusementPark(7),
                        placeOfWorship(8),
                        conventionCenter(9),
                        library(10),
                        museum(11),
                        restaurant(12),
                        theater(13),
                        bar(14),
                        coffeeShop(15),
                        zooOrAquarium(16),
                        emergencyCoordinationCenter(17),
                        unspecifiedBusiness(18),
                        doctorOrDentistOffice(19),
                        bank(20),
                        fireStation(21),
                        policeStation(22),
                        postOffice(23),
                        professionalOffice(24),
                        researchAndDevelopmentFacility(25),
                        attorneyOffice(26),
                        unspecifiedEducational(27),
                        schoolPrimary(28),
                        schoolSecondary(29),
                        universityOrCollege(30),
                        unspecifiedFactoryAndIndustrial(31),
                        factory(32),
                        unspecifiedInstitutional(33),
                        hospital(34),
                        longTermCareFacility(35),
                        alcoholAndDrugRehabilitationCenter(36),
                        groupHome(37),
                        prisonOrJail(38),
                        unspecifiedMercantile(39),
                        retailStore(40),
                        groceryMarket(41),
                        atomotiveServiceStation(42),
                        shoppingMall(43),
                        gasStation(44),
                        unspecifiedResidential(45),
                        privateResidence(46),
                        hotelOrMotel(47),
                        dormitory(48),
                        boardingHouse(49),
                        unspecifiedStorage(50),
                        unspecifiedUtility(51),
                        unspecifiedVehicular(52),
                        automobileOrTruck(53),
                        airplane(54),
                        bus(55),
                        ferry(56),
                        shipOrBoat(57),
                        train(58),
                        motorBike(59),
                        unspecifiedOutdoor(60),
                        muniMeshNetwork(61),
                        cityPark(62),
                        restArea(63),
                        trafficControl(64),
                        busStop(65),
                        kiosk(66)
                    }
    MAX-ACCESS      read-write
    STATUS          current
    DESCRIPTION
        "This object specifies the venue type within
        a particular venue group,for this WLAN.
        The venue group-venue type relationship is per
        the following table:
        Venue Group Venue Type Code Venue Description
        =========== =============== =================
         0            0         Unspecified
         0            1-255     Reserved
         1            0         Unspecified Assembly
         1            1         Arena
         1            2         Stadium
         1            3         Passenger Terminal (e.g.,
                                airport, port, bus station, ferry
                                terminal, train station)
         1            4         Amphitheater
         1            5         Amusement Park
         1            6         Place of Worship
         1            7         Convention Center
         1            8         Library
         1            9         Museum
         1            10        Restaurant
         1            11        Theater
         1            12        Bar
         1            13        Coffee Shop
         1            14        Zoo or Aquarium
         1            15        Emergency Coordination Center
         1            16-255    Reserved
         2            0         Unspecified Business
         2            1         Doctor or Dentist office
         2            2         Bank
         2            3         Fire Station
         2            4         Police Station
         2            6         Post Office
         2            7         Professional Office
         2            8         Research and Development Facility
         2            9         Attorney Office
         2            10-255    Reserved
         3            0         Unspecified Educational
         3            1         School, Primary
         3            2         School, Secondary
         3            3         University or College
         3            4-255     Reserved
         4            0         Unspecified Factory and Industrial
         4            1         Factory
         4            2-255     Reserved
         5            0         Unspecified Institutional
         5            1         Hospital
         5            2         Long-Term Care Facility (e.g.,
                                Nursing home, Hospice, etc.)
         5            3         Alcohol and Drug Re-habilitation
                                Center
         5            4         Group Home
         5            5         Prison or Jail
         5            6-255     Reserved
         6            0         Unspecified Mercantile
         6            1         Retail Store
         6            2         Grocery Market
         6            3         Automotive Service Station
         6            4-255     Reserved
         7            0         Unspecified Residential
         7            1         Hotel or Motel
         7            2         Dormitory
         7            3         Boarding House
         7            4-255     Reserved
         8            0-255     Reserved
         9            0-255     Reserved
        10           0         Unspecified Vehicular
        10           1         Automobile or Truck
        10           2         Airplane
        10           3         Bus
        10           4         Ferry
        10           5         Ship or Boat
        10           6         Train
        10           7-255     Reserved
        11           0         Unspecified Outdoor
        11           1         Muni-mesh Network
        11           2         City Park
        11           3-255     Reserved"
    DEFVAL          { unspecified } 
    ::= { cLApEntry 43 }

cLApVenueConfigVenueName OBJECT-TYPE
    SYNTAX          SnmpAdminString
    MAX-ACCESS      read-write
    STATUS          current
    DESCRIPTION
        "This object specifies the venue name defined for this AP
        group." 
    ::= { cLApEntry 44 }

cLApVenueConfigLanguage OBJECT-TYPE
    SYNTAX          SnmpAdminString
    MAX-ACCESS      read-write
    STATUS          current
    DESCRIPTION
        "This object specifies the language defined for this AP group." 
    ::= { cLApEntry 45 }

cLApLEDState OBJECT-TYPE
    SYNTAX          TruthValue
    MAX-ACCESS      read-write
    STATUS          current
    DESCRIPTION
        "This object specifies whether the LED state of this access
        point should be enabled or disabled.
        A value of 'true' indicates LED status is enabled.
        A value of 'false' indicates LED status is disabled." 
    ::= { cLApEntry 46 }

cLApTrunkVlan OBJECT-TYPE
    SYNTAX          Unsigned32
    MAX-ACCESS      read-write
    STATUS          current
    DESCRIPTION
        "This object specifies the trunk VLAN ID
        assigned to this AP's ethernet interface.
        When a non-zero value is assigned for this
        Object, the management packets will be 
        tagged with this VLAN ID. When the value of
        trunk VLAN ID is zero, the packets will be untagged" 
    ::= { cLApEntry 47 }

cLApTrunkVlanStatus OBJECT-TYPE
    SYNTAX          TruthValue
    MAX-ACCESS      read-only
    STATUS          current
    DESCRIPTION
        "This object specifies whether the trunk VLAN ID
        assigned to this AP's is effective. If the AP is unable
        to route the management frames through the trunk
        vlan, it will revert back to untagged mode. A value of  
        true indicates that the configured trunk VLAN has taken
        effect and  a value of false indicates that the management
        packets will be untagged" 
    ::= { cLApEntry 48 }

cLApLocation OBJECT-TYPE
    SYNTAX          SnmpAdminString
    MAX-ACCESS      read-write
    STATUS          current
    DESCRIPTION
        "This object specifies the user specified location of this AP.
        While configuring AP, user should specify a location for
        the AP so that its easy to figure out for some one where
        the AP is located." 
    ::= { cLApEntry 49 }

cLApSubMode OBJECT-TYPE
    SYNTAX          INTEGER  {
                        none(1),
                        wips(2),
                        pppoe(3),
                        pppoeWips(4)
                    }
    MAX-ACCESS      read-write
    STATUS          current
    DESCRIPTION
        "This object specifies the sub mode of the AP.
        The option 'wips' applies only when the
        AP is in local, flexConnect or monitor mode. 
        This 'pppoe' options apply only when the 
        AP is in flexConnect mode."
    DEFVAL          { none } 
    ::= { cLApEntry 50 }

cLApAssocCount OBJECT-TYPE
    SYNTAX          Unsigned32
    MAX-ACCESS      read-only
    STATUS          current
    DESCRIPTION
        "This object specifies the association count for the access
        point. This counter includes both successful and failed 
        associate attempts, but does NOT include the re-associate 
        attempts." 
    ::= { cLApEntry 51 }

cLApAssocFailResourceCount OBJECT-TYPE
    SYNTAX          Unsigned32
    MAX-ACCESS      read-only
    STATUS          current
    DESCRIPTION
        "This object specifies the association failure count for the
        access point due to the resource limits, i.e. the max clients
        of the WLAN/Radio is reached." 
    ::= { cLApEntry 52 }

cLApRealTimeStatsModeEnabled OBJECT-TYPE
    SYNTAX          TruthValue
    MAX-ACCESS      read-write
    STATUS          current
    DESCRIPTION
        "This object specifies whether current stats mode is
        'realtime'. There are two stats-mode, realtime and normal which
        specifies the stats-timer range to be 10-180 sec and 2-5 sec 
        each. 
        A value of 'true' indicates current mode is realtime.
        A value of 'false' indicates current mode is not realtime."
    DEFVAL          { false } 
    ::= { cLApEntry 53 }

cLApAssociatedClientCount OBJECT-TYPE
    SYNTAX          Unsigned32
    MAX-ACCESS      read-only
    STATUS          current
    DESCRIPTION
        "This object represents the associated client number for the
        access point." 
    ::= { cLApEntry 54 }

cLApMemoryCurrentUsage OBJECT-TYPE
    SYNTAX          Unsigned32
    MAX-ACCESS      read-only
    STATUS          current
    DESCRIPTION
        "This object represents the percent of current memory usage
        of the access point." 
    ::= { cLApEntry 55 }

cLApMemoryAverageUsage OBJECT-TYPE
    SYNTAX          Unsigned32
    MAX-ACCESS      read-only
    STATUS          current
    DESCRIPTION
        "This object represents the percent of average memory usage
        of the access point. The statistics window is defined by
        clsSysStatisticsInterval." 
    ::= { cLApEntry 56 }

cLApCpuCurrentUsage OBJECT-TYPE
    SYNTAX          Unsigned32
    MAX-ACCESS      read-only
    STATUS          current
    DESCRIPTION
        "This object represents the percent of current CPU usage
        of the access point." 
    ::= { cLApEntry 57 }

cLApCpuAverageUsage OBJECT-TYPE
    SYNTAX          Unsigned32
    MAX-ACCESS      read-only
    STATUS          current
    DESCRIPTION
        "This object represents the percent of average CPU usage
        of the access point. The statistics window is defined by
        clsSysStatisticsInterval." 
    ::= { cLApEntry 58 }

cLApUpgradeFromVersion OBJECT-TYPE
    SYNTAX          SnmpAdminString
    MAX-ACCESS      read-only
    STATUS          current
    DESCRIPTION
        "This object represents the AP image upgrade
        from version." 
    ::= { cLApEntry 59 }

cLApUpgradeToVersion OBJECT-TYPE
    SYNTAX          SnmpAdminString
    MAX-ACCESS      read-only
    STATUS          current
    DESCRIPTION
        "This object represents the AP image upgrade
        to version." 
    ::= { cLApEntry 60 }

cLApUpgradeFailureCause OBJECT-TYPE
    SYNTAX          SnmpAdminString
    MAX-ACCESS      read-only
    STATUS          current
    DESCRIPTION
        "This object represents the cause of the
        AP image upgrade failure." 
    ::= { cLApEntry 61 }

cLApMaxClientLimitNumberTrap OBJECT-TYPE
    SYNTAX          Unsigned32
    MAX-ACCESS      read-only
    STATUS          current
    DESCRIPTION
        "This object represents the max client limit number." 
    ::= { cLApEntry 62 }

cLApMaxClientLimitCause OBJECT-TYPE
    SYNTAX          SnmpAdminString
    MAX-ACCESS      read-only
    STATUS          current
    DESCRIPTION
        "This object represents the cause of the
        max client limit reach." 
    ::= { cLApEntry 63 }

cLApMaxClientLimitSet OBJECT-TYPE
    SYNTAX          TruthValue
    MAX-ACCESS      read-only
    STATUS          current
    DESCRIPTION
        "This object represents whether this event is
        raised or cleared.
          A value of 'true' indicates this event is set.
          A value of 'false' indicates this even is cleared." 
    ::= { cLApEntry 64 }

cLApFloorLabel OBJECT-TYPE
    SYNTAX          Unsigned64
    MAX-ACCESS      read-write
    STATUS          current
    DESCRIPTION
        "This object specifies the floor label for the Access Point." 
    ::= { cLApEntry 65 }

cLApConnectCount OBJECT-TYPE
    SYNTAX          Unsigned32
    MAX-ACCESS      read-only
    STATUS          deprecated
    DESCRIPTION
        "This object represents the Count of AP's that are connected
        to the Controller." 
    ::= { cLApEntry 66 }

cLApReassocSuccCount OBJECT-TYPE
    SYNTAX          Counter32
    MAX-ACCESS      read-only
    STATUS          current
    DESCRIPTION
        "This object represents the successful re-association
        count for the Access Point." 
    ::= { cLApEntry 67 }

cLApReassocFailCount OBJECT-TYPE
    SYNTAX          Counter32
    MAX-ACCESS      read-only
    STATUS          current
    DESCRIPTION
        "This object represents the failed re-association
        count for the Access Point." 
    ::= { cLApEntry 68 }

cLAdjChannelRogueEnabled OBJECT-TYPE
    SYNTAX          TruthValue
    MAX-ACCESS      read-write
    STATUS          deprecated
    DESCRIPTION
        "This object specifies if rogue AP
        detection and removed Traps need to be sent.
        A value of 'true' indicates adjacent rogue detection
        is enabled.
        A value of 'false' indicates adjacent rogue detection 
        is disabled.
        To Enable this trap it is requested to disable the
        bsnRogueAPTrapEnable in order to avoid the duplicates." 
    ::= { cLApEntry 69 }

cLApAssocFailCountByRate OBJECT-TYPE
    SYNTAX          Unsigned32
    MAX-ACCESS      read-only
    STATUS          current
    DESCRIPTION
        "This object represents the failed association
        count for the access point caused by rate mismatch." 
    ::= { cLApEntry 70 }

cLApAbnormalOfflineCount OBJECT-TYPE
    SYNTAX          Unsigned32
    MAX-ACCESS      read-only
    STATUS          current
    DESCRIPTION
        "This object represents the abnormal offline count for the
        access point." 
    ::= { cLApEntry 71 }

cLApActiveClientCount OBJECT-TYPE
    SYNTAX          Unsigned32
    MAX-ACCESS      read-only
    STATUS          current
    DESCRIPTION
        "This object represents the active client number for the access
        point." 
    ::= { cLApEntry 72 }

cLApAssocFailCountForRssiLow OBJECT-TYPE
    SYNTAX          Unsigned32
    MAX-ACCESS      read-only
    STATUS          current
    DESCRIPTION
        "This object represents the failed association
        count for the access point caused by RSSI low." 
    ::= { cLApEntry 73 }

cLApSysNetId OBJECT-TYPE
    SYNTAX          SnmpAdminString
    MAX-ACCESS      read-write
    STATUS          current
    DESCRIPTION
        "This object specifies the ApSysNetId which is the numeric
        string to identify the system information like ApName." 
    ::= { cLApEntry 74 }

cLApAssocFailTimes OBJECT-TYPE
    SYNTAX          Counter32
    MAX-ACCESS      read-only
    STATUS          current
    DESCRIPTION
        "This object represents the counts of client failed association
        to the access point." 
    ::= { cLApEntry 75 }

cLApAntennaBandMode OBJECT-TYPE
    SYNTAX          INTEGER  {
                        notApplicable(1),
                        single(2),
                        dual(3)
                    }
    MAX-ACCESS      read-write
    STATUS          current
    DESCRIPTION
        "This object specifies the mode of antenna band.
        notApplicable - will return for unsuppported APs. 
        single - configure the AP to use single band for antenna. 
        dual - configure the AP to use both bands for antenna." 
    ::= { cLApEntry 76 }

cLApHeartBeatRspAvgTime OBJECT-TYPE
    SYNTAX          Integer32 (1..100000)
    UNITS           "milliseconds"
    MAX-ACCESS      read-only
    STATUS          current
    DESCRIPTION
        "This object represents the average interval between sending
        the echo request and receiving the echo response in AP." 
    ::= { cLApEntry 77 }

cLApEchoRequestCount OBJECT-TYPE
    SYNTAX          Counter32
    MAX-ACCESS      read-only
    STATUS          current
    DESCRIPTION
        "This object represents the echo request packet
        count sent from AP to access controller." 
    ::= { cLApEntry 78 }

cLApEchoResponseLossCount OBJECT-TYPE
    SYNTAX          Counter32
    MAX-ACCESS      read-only
    STATUS          current
    DESCRIPTION
        "This object represents the echo response loss
        count from access controller to AP." 
    ::= { cLApEntry 79 }

cLApModuleInserted OBJECT-TYPE
    SYNTAX          SnmpAdminString
    MAX-ACCESS      read-only
    STATUS          current
    DESCRIPTION
        "This object represents the type of the module
        inserted in to the AP." 
    ::= { cLApEntry 80 }

cLApEnableModule OBJECT-TYPE
    SYNTAX          TruthValue
    MAX-ACCESS      read-write
    STATUS          current
    DESCRIPTION
        "This object specifies the status of the external
        module .
        A value of 'true' indicates module is enabled. 
        A value of 'false' indicates module is disabled." 
    ::= { cLApEntry 81 }

cLApIsUniversal OBJECT-TYPE
    SYNTAX          TruthValue
    MAX-ACCESS      read-only
    STATUS          current
    DESCRIPTION
        "This object represents the if the AP is
        universal AP. 
        A value of 'true' indicates AP is universal SKU based AP. 
        A value of 'false' indicates AP is non-Universal SKU AP." 
    ::= { cLApEntry 82 }

cLApUniversalPrimeStatus OBJECT-TYPE
    SYNTAX          SnmpAdminString
    MAX-ACCESS      read-only
    STATUS          current
    DESCRIPTION
        "This object represents the method of Priming
        of the Universal AP." 
    ::= { cLApEntry 83 }

cLApIsMaster OBJECT-TYPE
    SYNTAX          TruthValue
    MAX-ACCESS      read-only
    STATUS          current
    DESCRIPTION
        "This object represents whether the flex AP is a
        master AP. This applies only to FlexExpress controllers. 
        A value of 'true' indicates AP is a master AP. 
        A value of 'false' indicates AP is not a master AP." 
    ::= { cLApEntry 84 }

cLApBleFWDownloadStatus OBJECT-TYPE
    SYNTAX          TruthValue
    MAX-ACCESS      read-only
    STATUS          current
    DESCRIPTION
        "This object represents the list of APs in which BLE
        firmware download is in progress.
        A value of 'true' indicates BLE download is in progress.
        A value of 'false' indicates BLE download is not in progress." 
    ::= { cLApEntry 85 }

cLApDot11XorDartConnectorStatus OBJECT-TYPE
    SYNTAX          SnmpAdminString
    MAX-ACCESS      read-only
    STATUS          current
    DESCRIPTION
        "This object represents the XOR dart connector status." 
    ::= { cLApEntry 86 }

cLApCtsSxpDefaultPassword OBJECT-TYPE
    SYNTAX          SnmpAdminString
    MAX-ACCESS      read-write
    STATUS          current
    DESCRIPTION
        "This object specifies the SXP(Security Group Tag Exchange
        Protocol) default password."
    DEFVAL          { "" } 
    ::= { cLApEntry 87 }

cLApCtsSxpState OBJECT-TYPE
    SYNTAX          TruthValue
    MAX-ACCESS      read-write
    STATUS          current
    DESCRIPTION
        "This object specifies SXP(Security Group Tag Exchange
        Protocol) state.
         A value of 'true' indicates sxp state is enabled.
         A value of 'false' indicates sxp state is disabled."
    DEFVAL          { false } 
    ::= { cLApEntry 88 }

cLApCtsSxpMode OBJECT-TYPE
    SYNTAX          TruthValue
    MAX-ACCESS      read-write
    STATUS          current
    DESCRIPTION
        "This object specifies SXP(Security Group Tag Exchange
        Protocol) mode.
         A value of 'true' indicates sxp mode is enabled.
         A value of 'false' indicates sxp mode is disabled."
    DEFVAL          { false } 
    ::= { cLApEntry 89 }

cLApCtsSxpListenerMinHoldtime OBJECT-TYPE
    SYNTAX          Unsigned32
    MAX-ACCESS      read-write
    STATUS          current
    DESCRIPTION
        "This object specifies SXP(Security Group Tag Exchange
        Protocol) listener hold time.
        It specifies the global maximum hold-time for
        SXP connections in 'listener' mode.

        Value of this object must be lesser than
        cLApCtsSxpListenerMinHoldTime."
    DEFVAL          { 90 } 
    ::= { cLApEntry 90 }

cLApCtsSxpListenerMaxHoldtime OBJECT-TYPE
    SYNTAX          Unsigned32
    MAX-ACCESS      read-write
    STATUS          current
    DESCRIPTION
        "This object specifies SXP(Security Group Tag Exchange
        Protocol) listener hold time.
        It specifies the global maximum hold-time for
        SXP connections in 'listener' mode.

        Value of this object must be greater than
        cLApCtsSxpListenerMinHoldTime."
    DEFVAL          { 180 } 
    ::= { cLApEntry 91 }

cLApCtsSxpReconcilePeriod OBJECT-TYPE
    SYNTAX          Unsigned32
    MAX-ACCESS      read-write
    STATUS          current
    DESCRIPTION
        "This object specifies SXP(Security Group Tag Exchange
        Protocol) reconcile period."
    DEFVAL          { 120 } 
    ::= { cLApEntry 92 }

cLApCtsSxpRetryPeriod OBJECT-TYPE
    SYNTAX          Unsigned32
    MAX-ACCESS      read-write
    STATUS          current
    DESCRIPTION
        "This object specifies SXP(Security Group Tag Exchange
        Protocol) retry period."
    DEFVAL          { 120 } 
    ::= { cLApEntry 93 }

cLApCtsSxpSpeakerHoldTime OBJECT-TYPE
    SYNTAX          Unsigned32
    MAX-ACCESS      read-write
    STATUS          current
    DESCRIPTION
        "This object specifies SXP(Security Group Tag Exchange
        Protocol) speaker hold time."
    DEFVAL          { 120 } 
    ::= { cLApEntry 94 }

cLApCtsSxpSpeakerKeepAlive OBJECT-TYPE
    SYNTAX          Unsigned32
    MAX-ACCESS      read-write
    STATUS          current
    DESCRIPTION
        "This object specifies SXP(Security Group Tag Exchange
        Protocol) speaker keep alive time."
    DEFVAL          { 0 } 
    ::= { cLApEntry 95 }

cLApCtsInlineTagStatus OBJECT-TYPE
    SYNTAX          TruthValue
    MAX-ACCESS      read-write
    STATUS          current
    DESCRIPTION
        "This object specifies Cisco Trustsec inline tagging
        is enabled/disabled.
         A value 'true' indicates inline tag is enabled.
         A value 'false' indicates inline tag is disabled."
    DEFVAL          { false } 
    ::= { cLApEntry 96 }

cLApCtsSgaclStatus OBJECT-TYPE
    SYNTAX          TruthValue
    MAX-ACCESS      read-write
    STATUS          current
    DESCRIPTION
        "This object specifies Cisco Trustsec Security Group Tag
        ACL enforcement status.
         A value 'true' indicates SgACL enforcement is enabled
         A value 'false' indicates SgACL enforcement is disabled"
    DEFVAL          { false } 
    ::= { cLApEntry 97 }

cLApCtsOverrideStatus OBJECT-TYPE
    SYNTAX          TruthValue
    MAX-ACCESS      read-write
    STATUS          current
    DESCRIPTION
        "This object specifies Cisco Trustsec AP Override status.
        A value of 'true' indicates CTS AP Override is enabled.
        A value of 'false' indicates CTS AP Override is disabled."
    DEFVAL          { false } 
    ::= { cLApEntry 98 }

cLApModeClear OBJECT-TYPE
    SYNTAX          TruthValue
    MAX-ACCESS      read-write
    STATUS          current
    DESCRIPTION
        "This object specifies to clear the modes like 'Sniffer',
        'Monitor' which is not inherited from tag configuration on
        controller. Once cleared, AP may reboot and move to the AP mode
        based on current tag configuration.
        A value of 'true' indicates AP mode is cleared
        A value of 'false' indicates AP mode is set"
    ::= { cLApEntry 103 }

cLApSiteTagName OBJECT-TYPE
    SYNTAX          SnmpAdminString (SIZE  (0..32))
    MAX-ACCESS      read-only
    STATUS          current
    DESCRIPTION
        "This object specifies the site tag name of the AP"
    ::= { cLApEntry 104 }

cLApRfTagName OBJECT-TYPE
    SYNTAX          SnmpAdminString (SIZE  (0..32))
    MAX-ACCESS      read-only
    STATUS          current
    DESCRIPTION
        "This object specifies the RF tag name of the AP"
    ::= { cLApEntry 105 }

cLApPolicyTagName OBJECT-TYPE
    SYNTAX          SnmpAdminString (SIZE  (0..32))
    MAX-ACCESS      read-only
    STATUS          current
    DESCRIPTION
        "This object specifies the policy tag name of the AP."
    ::= { cLApEntry 106 }

cLApTagSource OBJECT-TYPE
    SYNTAX          INTEGER  {
                        none(1),
                        static(2),
                        filterengine(3),
                        pnpserver(4),
                        default(5),
                        location(6)
                    }
    MAX-ACCESS      read-only
    STATUS          current
    DESCRIPTION
        "This object specifies the source of the tag."
    ::= { cLApEntry 107 }

cLApUsbModuleName OBJECT-TYPE
    SYNTAX          SnmpAdminString (SIZE  (0..66))
    MAX-ACCESS      read-only
    STATUS          current
    DESCRIPTION
        "This object specifies module name of USB module
        On the AP."
    ::= { cLApEntry 108 }

cLApUsbModuleState OBJECT-TYPE
    SYNTAX          SnmpAdminString (SIZE  (0..66))
    MAX-ACCESS      read-only
    STATUS          current
    DESCRIPTION
        "This object specifies whether USB module detected or not
        detected on the AP."
    ::= { cLApEntry 109 }

cLApUsbModuleProductId OBJECT-TYPE
    SYNTAX          SnmpAdminString (SIZE  (0..19))
    MAX-ACCESS      read-only
    STATUS          current
    DESCRIPTION
        "This object specifies product Id of USB module on the AP."
    ::= { cLApEntry 110 }

cLApUsbDescription OBJECT-TYPE
    SYNTAX          SnmpAdminString (SIZE  (0..66))
    MAX-ACCESS      read-only
    STATUS          current
    DESCRIPTION
        "This object specifies description of USB module on the AP."
    ::= { cLApEntry 111 }

cLApUsbStateInfo OBJECT-TYPE
    SYNTAX          TruthValue
    MAX-ACCESS      read-write
    STATUS          current
    DESCRIPTION
        "This object specifies State(enable/disable) of USB module
        on the AP."
    ::= { cLApEntry 112 }

cLApUsbOverride OBJECT-TYPE
    SYNTAX          TruthValue
    MAX-ACCESS      read-write
    STATUS          current
    DESCRIPTION
        "This object specifies Override(enable/disable) of USB module
        on the AP."
    ::= { cLApEntry 113 }

cLApUsbSerialNumber OBJECT-TYPE
    SYNTAX          SnmpAdminString (SIZE  (0..12))
    MAX-ACCESS      read-only
    STATUS          current
    DESCRIPTION
        "This object specifies serial number of USB module
        on the AP."
    ::= { cLApEntry 114 }

cLApUsbMaxPower OBJECT-TYPE
    SYNTAX          Unsigned32
    MAX-ACCESS      read-only
    STATUS          current
    DESCRIPTION
        "This object specifies max power given to USB module
        on the AP."
    ::= { cLApEntry 115 }
 
cLApLagConfigStatus  OBJECT-TYPE
    SYNTAX           TruthValue
    MAX-ACCESS       read-only
    STATUS           current
    DESCRIPTION
        "This object specifies the configured LAG status(enable/disable)
        on the AP."
    ::= { cLApEntry 116 }

cLApMonitorModeOptStatus  OBJECT-TYPE
    SYNTAX           TruthValue
    MAX-ACCESS       read-only
    STATUS           current
    DESCRIPTION
        "This object specifies the Monitor Mode optimization support(enable/disable)
        on the AP."
    ::= { cLApEntry 117 }

cLApFilterName OBJECT-TYPE
    SYNTAX          SnmpAdminString (SIZE  (0..32))
    MAX-ACCESS      read-only
    STATUS          current
    DESCRIPTION
        "This object specifies the Filter name applied on this AP"
    ::= { cLApEntry 118 }


-- ********************************************************************
-- *  AP Dot11 Interface Information
-- ********************************************************************

cLApDot11IfTable OBJECT-TYPE
    SYNTAX          SEQUENCE OF CLApDot11IfEntry 
    MAX-ACCESS      not-accessible
    STATUS          current
    DESCRIPTION
        "This table represents the information about the
        basic functional parameters corresponding to
        the dot11 interfaces of the APs that have joined
        the controller."
    ::= { ciscoLwappApIf 1 }

cLApDot11IfEntry OBJECT-TYPE
    SYNTAX          CLApDot11IfEntry
    MAX-ACCESS      not-accessible
    STATUS          current
    DESCRIPTION
        "An entry in this table represents the 802.11
        functional parameters of the dot11 interface of
        an AP that has joined the controller.

        Entries are added when the APs associate to this
        controller and deleted when they lose their
        association."
    INDEX           {
                        cLApSysMacAddress,
                        cLApDot11IfSlotId
                    } 
    ::= { cLApDot11IfTable 1 }

CLApDot11IfEntry ::= SEQUENCE {
        cLApDot11IfSlotId               Unsigned32,
        cLApDot11IfType                 CLApIfType,
        cLApDot11IfRegDomain            SnmpAdminString,
        cLApDot11nSupport               TruthValue,
        cLAp11nChannelBandwidth         INTEGER,
        cLApLomEnabled                  TruthValue,
        cLApLomFirstChannel             CLDot11Channel,
        cLApLomSecondChannel            CLDot11Channel,
        cLApLomThirdChannel             CLDot11Channel,
        cLApLomFourthChannel            CLDot11Channel,
        cLApExtensionChannel            CLDot11Channel,
        cLApLegacyBeamForming           INTEGER,
        cLApCdpOverAirEnabled           TruthValue,
        cLApDot11IfAdminStatus          TruthValue,
        cLApDot11IfLinkChangeCount      Unsigned32,
        cLApDot11MaxClients             Unsigned32,
        cLApPromiscuousModeDwelling     Unsigned32,
        cLApDot11IfStaKeepingTime       TimeTicks,
        cLApDot11IfLinkSpeed            Gauge32,
        cLApDot11IfMtu                  Unsigned32,
        cLApDot11IfDesc                 SnmpAdminString,
        cLApDot11acSupport              TruthValue,
        cLAp11ChannelBandwidth          INTEGER,
        cLApExtensionChannels           SnmpAdminString,
        cLAPDot11IfMinTxPowerStep       Unsigned32,
        cLApDot11XorRadioMode           INTEGER,
        cLApDot11XorRadioBand           INTEGER,
        cLApDot11XorRadioRoleAssignment INTEGER,
        cLApDot11IfMaxDataRate          Unsigned32,
        cLApDot11IfSensorReachability   Unsigned32,
        cLApDot11axSupport              TruthValue,
        cLApFraCoverageOverlapFactor    Integer32,
        cLApFraSuggestedMode            INTEGER,
        cLApDot11IfDualRadioMode        INTEGER,
        cLApDot11IfDualRadioCapable     INTEGER,
        cLApDot11IfRadioFRACapable      INTEGER,
        cLApDot11IfPhyS80EightyChannelNumber INTEGER,
        cLApDot11IfDualRadioOperation   INTEGER,
        cLApDot11IfRadioRoleOperation   INTEGER,
        cLApDot11IfRadioRole            INTEGER,
        cLApDot11IfRptncPresent         TruthValue,
        cLApDot11IfDartPresent          TruthValue
}

cLApDot11IfSlotId OBJECT-TYPE
    SYNTAX          Unsigned32
    MAX-ACCESS      not-accessible
    STATUS          current
    DESCRIPTION
        "This object represents the slot ID of a dot11
        interface on an AP. 

        The slot ID for a particular dot11 interface as
        represented by this object ranges from 0 to 
        cLApMaxNumberOfDot11Slots - 1." 
    ::= { cLApDot11IfEntry 1 }

cLApDot11IfType OBJECT-TYPE
    SYNTAX          CLApIfType
    MAX-ACCESS      read-only
    STATUS          current
    DESCRIPTION
        "This object represents the type of this dot11
        interface." 
    ::= { cLApDot11IfEntry 2 }

cLApDot11IfRegDomain OBJECT-TYPE
    SYNTAX          SnmpAdminString (SIZE  (1..255))
    MAX-ACCESS      read-only
    STATUS          current
    DESCRIPTION
        "This object represents the regulatory domain for
        this radio type on this AP." 
    ::= { cLApDot11IfEntry 3 }

cLApDot11nSupport OBJECT-TYPE
    SYNTAX          TruthValue
    MAX-ACCESS      read-only
    STATUS          current
    DESCRIPTION
        "This objects represents whether 11n support is enabled
        on this radio.
        A value of 'true' indicates 11n support is enabled.
        A value of 'false' indicates 11n support is disabled." 
    ::= { cLApDot11IfEntry 4 }

cLAp11nChannelBandwidth OBJECT-TYPE
    SYNTAX          INTEGER  {
                        five(1),
                        ten(2),
                        twenty(3),
                        forty(4)
                    }
    UNITS           "mhz"
    MAX-ACCESS      read-write
    STATUS          current
    DESCRIPTION
        "This object specifies the channel bandwidth for
        this AP. This applies to 802.11n networks only.
        This has been deprecated for cLAp11ChannelBandwidth." 
    ::= { cLApDot11IfEntry 5 }

cLApLomEnabled OBJECT-TYPE
    SYNTAX          TruthValue
    MAX-ACCESS      read-write
    STATUS          deprecated
    DESCRIPTION
        "This object indicates whether this AP is being monitored
        by the location server. A value of 'true' indicates that 
        the monitoring is enabled. A value of 'false' indicates 
        that the monitoring is disabled."
    DEFVAL          { false } 
    ::= { cLApDot11IfEntry 6 }

cLApLomFirstChannel OBJECT-TYPE
    SYNTAX          CLDot11Channel
    MAX-ACCESS      read-write
    STATUS          current
    DESCRIPTION
        "This object specifies the first location channel that is
        being monitored." 
    ::= { cLApDot11IfEntry 7 }

cLApLomSecondChannel OBJECT-TYPE
    SYNTAX          CLDot11Channel
    MAX-ACCESS      read-write
    STATUS          current
    DESCRIPTION
        "This object specifies the second location channel that
        is being monitored." 
    ::= { cLApDot11IfEntry 8 }

cLApLomThirdChannel OBJECT-TYPE
    SYNTAX          CLDot11Channel
    MAX-ACCESS      read-write
    STATUS          current
    DESCRIPTION
        "This object specifies the third location
        channel that is being monitored." 
    ::= { cLApDot11IfEntry 9 }

cLApLomFourthChannel OBJECT-TYPE
    SYNTAX          CLDot11Channel
    MAX-ACCESS      read-write
    STATUS          current
    DESCRIPTION
        "This object specifies the fourth location
        channel that is being monitored." 
    ::= { cLApDot11IfEntry 10 }

cLApExtensionChannel OBJECT-TYPE
    SYNTAX          CLDot11Channel
    MAX-ACCESS      read-only
    STATUS          deprecated
    DESCRIPTION
        "This object specifies the extension channel. This is
        applicable when the channel bandwidth is set to 40mhz." 
    ::= { cLApDot11IfEntry 11 }

cLApLegacyBeamForming OBJECT-TYPE
    SYNTAX          INTEGER  {
                        enable(1),
                        disable(2),
                        notApplicable(3)
                    }
    MAX-ACCESS      read-write
    STATUS          current
    DESCRIPTION
        "This object indicates the status of legacy beam forming
        in this AP. This object is applicable only for
        11n supported APs.
        For APs that does not support legacy beam forming,
        a get request on this attribute will return 
        the value 'notApplicable'.
        A value of 'enable' indicates that the legacy
        Beam forming is enabled in this AP. 
        A value of 'false' indicates that the legacy
        Beam forming is disabled in this AP."
    DEFVAL          { notApplicable } 
    ::= { cLApDot11IfEntry 12 }

cLApCdpOverAirEnabled OBJECT-TYPE
    SYNTAX          TruthValue
    MAX-ACCESS      read-write
    STATUS          current
    DESCRIPTION
        "This object specifies the status of Cisco Discovery
        Protocol(CDP) in this interface, represented by
        cLApDot11IfSlotId of the AP, represented by
        cLApSysMacAddress.
        A value of 'true' indicates that CDP is enabled in
        the dot11 interface(s) of this AP.
        A value of 'false' indicates that CDP is disabled in
        the dot11 interface(s) of this AP." 
    ::= { cLApDot11IfEntry 13 }

cLApDot11IfAdminStatus OBJECT-TYPE
    SYNTAX          TruthValue
    MAX-ACCESS      read-write
    STATUS          current
    DESCRIPTION
        "This object specifies the AP's interface admin
        status.
        A value of 'true' indicates admin state is up.
        A value of 'false' indicates admin state is down." 
    ::= { cLApDot11IfEntry 14 }

cLApDot11IfLinkChangeCount OBJECT-TYPE
    SYNTAX          Unsigned32
    MAX-ACCESS      read-only
    STATUS          current
    DESCRIPTION
        "This object represents the link change count of a dot11
        interface on an AP." 
    ::= { cLApDot11IfEntry 15 }

cLApDot11MaxClients OBJECT-TYPE
    SYNTAX          Unsigned32 (1..200)
    MAX-ACCESS      read-write
    STATUS          current
    DESCRIPTION
        "This object specifies the max supported associated clients
        of a dot11 interface on an AP."
    DEFVAL          { 200 } 
    ::= { cLApDot11IfEntry 16 }

cLApPromiscuousModeDwelling OBJECT-TYPE
    SYNTAX          Unsigned32
    UNITS           "percentage"
    MAX-ACCESS      read-only
    STATUS          current
    DESCRIPTION
        "This object represents the percentage of time for the dot11
        interface of an Access Point spent in promiscuous mode 
        dwelling." 
    ::= { cLApDot11IfEntry 17 }

cLApDot11IfStaKeepingTime OBJECT-TYPE
    SYNTAX          TimeTicks
    MAX-ACCESS      read-only
    STATUS          current
    DESCRIPTION
        "This object represents the time in hundredths
        of a second since the last dot11 interface state changed." 
    ::= { cLApDot11IfEntry 18 }

cLApDot11IfLinkSpeed OBJECT-TYPE
    SYNTAX          Gauge32
    UNITS           "bps"
    MAX-ACCESS      read-only
    STATUS          current
    DESCRIPTION
        "This object represents the speed of the interface
        in units of 1,000,000 bits per second." 
    ::= { cLApDot11IfEntry 19 }

cLApDot11IfMtu OBJECT-TYPE
    SYNTAX          Unsigned32
    MAX-ACCESS      read-only
    STATUS          current
    DESCRIPTION
        "This object represents interface's MTU value." 
    ::= { cLApDot11IfEntry 20 }

cLApDot11IfDesc OBJECT-TYPE
    SYNTAX          SnmpAdminString
    MAX-ACCESS      read-only
    STATUS          current
    DESCRIPTION
        "This object represents the description of this interface." 
    ::= { cLApDot11IfEntry 21 }

cLApDot11acSupport OBJECT-TYPE
    SYNTAX          TruthValue
    MAX-ACCESS      read-only
    STATUS          current
    DESCRIPTION
        "This objects represents whether 802.11ac support is
        enabled on this AP.
        A value of 'true' indicates 11ac support for slot is
        enabled.
        A value of 'false' indicates 11ac support for slot is
        disabled." 
    ::= { cLApDot11IfEntry 22 }

cLAp11ChannelBandwidth OBJECT-TYPE
    SYNTAX          INTEGER  {
                        five(1),
                        ten(2),
                        twenty(3),
                        fourty(4),
                        eighty(5),
                        onesixty(6),
                        eightyeighty(7)
                    }
    UNITS           "mhz"
    MAX-ACCESS      read-write
    STATUS          current
    DESCRIPTION
        "This object specifies the channel bandwidth for
        this AP. This applies to 802.11n and 802.11ac networks only." 
    ::= { cLApDot11IfEntry 23 }

cLApExtensionChannels OBJECT-TYPE
    SYNTAX          SnmpAdminString
    MAX-ACCESS      read-only
    STATUS          current
    DESCRIPTION
        "This object represents the extension channels separated by
        commas. This is applicable when the channel bandwidth is set 
        to 40mhz or 80mhz." 
    ::= { cLApDot11IfEntry 24 }

cLAPDot11IfMinTxPowerStep OBJECT-TYPE
    SYNTAX          Unsigned32
    UNITS           "dbm"
    MAX-ACCESS      read-only
    STATUS          current
    DESCRIPTION
        "This object represents minimum adjust step of the AP radio TX
        power. The power step is coded as an unsigned integer in units
        of dbm." 
    ::= { cLApDot11IfEntry 25 }

cLApDot11XorRadioMode OBJECT-TYPE
    SYNTAX          INTEGER  {
                        servingClients(1),
                        monitor(2),
                        sensor(3)
                    }
    MAX-ACCESS      read-write
    STATUS          current
    DESCRIPTION
        "This object specifies the radio mode for
        the AP which has XOR radio.
        servingClients - xor radio is configured to 
                         serve the clients (local/flexconnect/bridge).
        monitor  -xor radio is configured to operate in 
                   monitor mode.
         sensor - xor radio is configured to operate in sensor
                  mode." 
    ::= { cLApDot11IfEntry 26 }

cLApDot11XorRadioBand OBJECT-TYPE
    SYNTAX          INTEGER  {
                        radioband24G(1),
                        radioband5G(2),
                        radioband6G(3)
                    }
    MAX-ACCESS      read-write
    STATUS          current
    DESCRIPTION
        "This object specifies the operating band of
        the dot11 interface of an AP.
        radioband24G - operating band for xor radio is 2.4GHz.
        radioband5G  - operating band for xor radio is 5GHz.
        radioband6G  - operating band for xor radio is 6GHz"
    ::= { cLApDot11IfEntry 27 }

cLApDot11XorRadioRoleAssignment OBJECT-TYPE
    SYNTAX          INTEGER  {
                        auto(1),
                        manual(2)
                    }
    MAX-ACCESS      read-write
    STATUS          current
    DESCRIPTION
        "This object specifies the radio role assignment of
        XOR radio.
        auto - xor radio configured to change band/mode automatically.
        manual - xor radio's band/mode can be configured manually." 
    ::= { cLApDot11IfEntry 28 }

cLApDot11IfMaxDataRate OBJECT-TYPE
    SYNTAX          Unsigned32
    MAX-ACCESS      read-only
    STATUS          current
    DESCRIPTION
        "This object represents the maximum data rate of a dot11
        interface on an AP in Mbps." 
    ::= { cLApDot11IfEntry 29 }

cLApDot11IfSensorReachability OBJECT-TYPE
    SYNTAX          Unsigned32
    MAX-ACCESS      read-only
    STATUS          current
    DESCRIPTION
        "This object represents sensor radio's ability to cover
        localized RF neighbors.It represents value in percentage 
        which shows percentage of neighbors covered by this sensor." 
    ::= { cLApDot11IfEntry 30 }

cLApDot11axSupport OBJECT-TYPE
    SYNTAX          TruthValue
    MAX-ACCESS      read-only
    STATUS          current
    DESCRIPTION
        "This objects represents whether 802.11ax support is
        enabled on this AP.
        A value of 'true' indicates 11ax support for slot is
        enabled.
        A value of 'false' indicates 11ax support for slot is
        disabled." 
    ::= { cLApDot11IfEntry 31 }

cLApFraCoverageOverlapFactor OBJECT-TYPE
    SYNTAX          Integer32
    UNITS           "percentage"
    MAX-ACCESS      read-only
    STATUS          current
    DESCRIPTION
        "This object represents the COF(Coverage Overlap Factor) in
        percentage.COF represents overlap on a given radio's transmit
        cell size by its adjacent neighbors.When COF value is higher
        than FRA(Flexible Radio Assignment) sensitivity, given radio
        will be most likely marked as redundant by FRA algorithm." 
    ::= { cLApDot11IfEntry 32 }

cLApFraSuggestedMode OBJECT-TYPE
    SYNTAX          INTEGER  {
                        static(1),
                        none(2),
                        radioBand5GMonitor(3),
                        radioBand24G(4),
                        notApplicable(5)
                    }
    MAX-ACCESS      read-only
    STATUS          current
    DESCRIPTION
        "This object represents the band/mode XOR radio can move to,
        for better performance.
        static - XOR radio's band/mode is in manual assignment.
        none - FRA(Flexible Radio Assignment) algorithm is disabled.
        radioBand5GMonitor - FRA suggested mode/band is 5GHz or Monitor role.
        radioBand24G - XOR radio is not redundant.
        notApplicable - Radio is not XOR." 
    ::= { cLApDot11IfEntry 33 }
 
cLApDot11IfDualRadioMode OBJECT-TYPE
    SYNTAX          INTEGER {
                        none(1),
                        enabled(2),
                        disabled(3)
                    }
    MAX-ACCESS      read-write
    STATUS          deprecated
    DESCRIPTION
        "This object represents dual radio mode status of radio 
        enabled - Dual radio mode is enabled.
        disabled- Dual radio mode is disabled.
        None - Radio is not dual radio mode capable."
    ::= { cLApDot11IfEntry 34 }

cLApDot11IfDualRadioCapable OBJECT-TYPE
    SYNTAX          INTEGER {
                        notcapable(0),
                        dualmodecapable(1)
                    }
    MAX-ACCESS      read-only
    STATUS          deprecated
    DESCRIPTION
        "This object represents whether radio is dual radio capable or 
         not"
    ::= { cLApDot11IfEntry 35 }

cLApDot11IfRadioFRACapable OBJECT-TYPE
    SYNTAX          INTEGER {
                        notcapable(0),
                        capable(1)
                    }
    MAX-ACCESS      read-only
    STATUS          deprecated
    DESCRIPTION
        "This object represents whether radio is FRA capable or not."
    ::= { cLApDot11IfEntry 36 }

cLApDot11IfPhyS80EightyChannelNumber OBJECT-TYPE
    SYNTAX          INTEGER
    MAX-ACCESS      read-write
    STATUS          current
    DESCRIPTION
        "Secondary 80MHz channel number of the AP Interface.
        Allowed channel numbers also depends on the current
        Country Code set in the Switch."
    ::= { cLApDot11IfEntry 37 }

--cLApDot11IfChannelWidthCapability OBJECT-TYPE
--    SYNTAX          INTEGER {
--                        notsupported(0),
--                        eightycontiguous(1),
--                        eightynoncontiguous(2),
--                        onesixty(4)
--                    }
--    MAX-ACCESS      read-only
--    STATUS          current
--    DESCRIPTION
--        "This Object represents channel width capability."
--    ::= { cLApDot11IfEntry 38 }

cLApDot11IfDualRadioOperation OBJECT-TYPE
    SYNTAX          INTEGER {
                        none(1),
                        auto(2),
                        manual(3)
                    }
    MAX-ACCESS      read-write
    STATUS          deprecated
    DESCRIPTION
        "This object represents dual radio mode operation of
        the slot.
        auto - Dual radio mode is automatic.
        manual - Dual radio mode is configurable manually.
        none - Radio is not dual radio mode capable."
    ::= { cLApDot11IfEntry 39 }

cLApDot11IfRadioRoleOperation OBJECT-TYPE
    SYNTAX          INTEGER {
                        none(1),
                        auto(2),
                        manual(3)
                    }
    MAX-ACCESS      read-write
    STATUS          deprecated
    DESCRIPTION
        "This object represents the radio role operation
        of the slot.
        auto - Radio role assignment is automatic.
        manual - Radio role assignment is manual."
    ::= { cLApDot11IfEntry 40 }

    
cLApDot11IfRadioRole OBJECT-TYPE
    SYNTAX          INTEGER {
                        none(1),
                        local(2),
                        monitor(3)
                    }
    MAX-ACCESS      read-write
    STATUS          deprecated
    DESCRIPTION
        "This object represents the role for the slot.
        local - The means the slot is capable of serving clients.
        monitor - The slot does not serves client, only monitors."
    ::= { cLApDot11IfEntry 41 }

cLApDot11IfRptncPresent OBJECT-TYPE
    SYNTAX          TruthValue
    MAX-ACCESS      read-only
    STATUS          current
    DESCRIPTION
        "This object represents whether Self Identifying Antenna RP-TNC is
        present for the radio.
        A value of 'true' indicates SIA RP-TNC is present.
        A value of 'false' indicates SIA RP-TNC is not present." 
    ::= { cLApDot11IfEntry 42 }

cLApDot11IfDartPresent OBJECT-TYPE
    SYNTAX          TruthValue
    MAX-ACCESS      read-only
    STATUS          current
    DESCRIPTION
        "This object represents whether Self Identifying Antenna DART is
        present for the radio
        A value of 'true' indicates SIA DART is present.
        A value of 'false' indicates SIA DART is not present." 
    ::= { cLApDot11IfEntry 43 }


-- ********************************************************************
-- *  AP Ethernet Interface Information
-- ********************************************************************

cLApEthernetIfTable OBJECT-TYPE
    SYNTAX          SEQUENCE OF CLApEthernetIfEntry 
    MAX-ACCESS      not-accessible
    STATUS          current
    DESCRIPTION
        "This table represents the information about the
        basic functional parameters corresponding to
        the Ethernet interfaces of the APs that have joined
        the controller."
    ::= { ciscoLwappApIf 2 }

cLApEthernetIfEntry OBJECT-TYPE
    SYNTAX          CLApEthernetIfEntry
    MAX-ACCESS      not-accessible
    STATUS          current
    DESCRIPTION
        "An entry in this table represents the functional
        parameters of the Ethernet interface of an AP that
        has joined the controller.

        Entries are added when the APs associate to this
        controller and deleted when they lose their
        association."
    INDEX           {
                        cLApSysMacAddress,
                        cLApEthernetIfSlotId
                    } 
    ::= { cLApEthernetIfTable 1 }

CLApEthernetIfEntry ::= SEQUENCE {
        cLApEthernetIfSlotId           Unsigned32,
        cLApEthernetIfName             SnmpAdminString,
        cLApEthernetIfMacAddress       MacAddress,
        cLApEthernetIfAdminStatus      INTEGER,
        cLApEthernetIfOperStatus       INTEGER,
        cLApEthernetIfRxUcastPkts      Counter32,
        cLApEthernetIfRxNUcastPkts     Counter32,
        cLApEthernetIfTxUcastPkts      Counter32,
        cLApEthernetIfTxNUcastPkts     Counter32,
        cLApEthernetIfDuplex           INTEGER,
        cLApEthernetIfLinkSpeed        Gauge32,
        cLApEthernetIfPOEPower         INTEGER,
        cLApEthernetIfRxTotalBytes     Counter32,
        cLApEthernetIfTxTotalBytes     Counter32,
        cLApEthernetIfInputCrc         Counter32,
        cLApEthernetIfInputAborts      Counter32,
        cLApEthernetIfInputErrors      Counter32,
        cLApEthernetIfInputFrames      Counter32,
        cLApEthernetIfInputOverrun     Counter32,
        cLApEthernetIfInputDrops       Counter32,
        cLApEthernetIfInputResource    Counter32,
        cLApEthernetIfUnknownProtocol  Counter32,
        cLApEthernetIfRunts            Counter32,
        cLApEthernetIfGiants           Counter32,
        cLApEthernetIfThrottle         Counter32,
        cLApEthernetIfResets           Counter32,
        cLApEthernetIfOutputCollision  Counter32,
        cLApEthernetIfOutputNoBuffer   Counter32,
        cLApEthernetIfOutputResource   Counter32,
        cLApEthernetIfOutputUnderrun   Counter32,
        cLApEthernetIfOutputErrors     Counter32,
        cLApEthernetIfOutputTotalDrops Counter32,
        cLApEthernetIfCdpEnabled       TruthValue,
        cLApEthernetIfMtu              Unsigned32,
        cLApEthernetIfType             IANAifType,
        cLApEthernetIfLinkChangeCount  Counter32
}

cLApEthernetIfSlotId OBJECT-TYPE
    SYNTAX          Unsigned32
    MAX-ACCESS      not-accessible
    STATUS          current
    DESCRIPTION
        "This object represents the slot ID of an Ethernet
        interface on an AP. 

        The slot ID for a particular Ethernet interface as
        represented by this object ranges from 0 to 
        cLApMaxNumberOfEthernetSlots - 1." 
    ::= { cLApEthernetIfEntry 1 }

cLApEthernetIfName OBJECT-TYPE
    SYNTAX          SnmpAdminString (SIZE  (0..32))
    MAX-ACCESS      read-only
    STATUS          current
    DESCRIPTION
        "This object represents the name of the
        ethernet interface." 
    ::= { cLApEthernetIfEntry 2 }

cLApEthernetIfMacAddress OBJECT-TYPE
    SYNTAX          MacAddress
    MAX-ACCESS      read-only
    STATUS          current
    DESCRIPTION
        "This object represents MAC address of the ethernet
        interface in the slot represented by 
        cLApEthernetIfSlotId." 
    ::= { cLApEthernetIfEntry 3 }

cLApEthernetIfAdminStatus OBJECT-TYPE
    SYNTAX          INTEGER  {
                        up(1),
                        down(2)
                    }
    MAX-ACCESS      read-write
    STATUS          current
    DESCRIPTION
        "This object specifies the admin state of the physical
        ethernet interface on the AP.
        up - Admin state of ethernet interface is up.
        down - Admin state of ethernet interface is down." 
    ::= { cLApEthernetIfEntry 4 }

cLApEthernetIfOperStatus OBJECT-TYPE
    SYNTAX          INTEGER  {
                        up(1),
                        down(2)
                    }
    MAX-ACCESS      read-only
    STATUS          current
    DESCRIPTION
        "This object represents the operational state
        of the physical Ethernet interface on the AP.
        up - Operational state of ethernet interface is up.
        down - Operational state of ethernet interface is down." 
    ::= { cLApEthernetIfEntry 5 }

cLApEthernetIfRxUcastPkts OBJECT-TYPE
    SYNTAX          Counter32
    UNITS           "packets"
    MAX-ACCESS      read-only
    STATUS          current
    DESCRIPTION
        "This object represents the total number of unicast packets
        received on the interface." 
    ::= { cLApEthernetIfEntry 6 }

cLApEthernetIfRxNUcastPkts OBJECT-TYPE
    SYNTAX          Counter32
    UNITS           "packets"
    MAX-ACCESS      read-only
    STATUS          current
    DESCRIPTION
        "This object represents the total number of non-unicast or
        multicast packets received on the interface" 
    ::= { cLApEthernetIfEntry 7 }

cLApEthernetIfTxUcastPkts OBJECT-TYPE
    SYNTAX          Counter32
    UNITS           "packets"
    MAX-ACCESS      read-only
    STATUS          current
    DESCRIPTION
        "This object represents the total number of unicast packets
        transmitted on the interface." 
    ::= { cLApEthernetIfEntry 8 }

cLApEthernetIfTxNUcastPkts OBJECT-TYPE
    SYNTAX          Counter32
    UNITS           "packets"
    MAX-ACCESS      read-only
    STATUS          current
    DESCRIPTION
        "This object represents the total number of non-unicast or
        multicast packets transmitted on the interface" 
    ::= { cLApEthernetIfEntry 9 }

cLApEthernetIfDuplex OBJECT-TYPE
    SYNTAX          INTEGER  {
                        unknown(1),
                        halfduplex(2),
                        fullduplex(3),
                        auto(4)
                    }
    MAX-ACCESS      read-only
    STATUS          current
    DESCRIPTION
        "This object represents the interface's duplex mode" 
    ::= { cLApEthernetIfEntry 10 }

cLApEthernetIfLinkSpeed OBJECT-TYPE
    SYNTAX          Gauge32
    MAX-ACCESS      read-only
    STATUS          current
    DESCRIPTION
        "This object represents the speed of the interface in units of
        1,000,000 bits per second" 
    ::= { cLApEthernetIfEntry 11 }

cLApEthernetIfPOEPower OBJECT-TYPE
    SYNTAX          INTEGER  {
                        none(1),
                        drawn(2),
                        notdrawn(3)
                    }
    MAX-ACCESS      read-only
    STATUS          current
    DESCRIPTION
        "This object represents whether this interface supports
        Power Over Ethernet (POE)
        none     - POE is not supported
        drawn    - This interface supports POE, and power is
                   being drawn
        notdrawn - POE power is not drawn" 
    ::= { cLApEthernetIfEntry 12 }

cLApEthernetIfRxTotalBytes OBJECT-TYPE
    SYNTAX          Counter32
    UNITS           "Bytes"
    MAX-ACCESS      read-only
    STATUS          current
    DESCRIPTION
        "This object represents the total number of bytes in the
        error-free packets received on the interface." 
    ::= { cLApEthernetIfEntry 13 }

cLApEthernetIfTxTotalBytes OBJECT-TYPE
    SYNTAX          Counter32
    UNITS           "Bytes"
    MAX-ACCESS      read-only
    STATUS          current
    DESCRIPTION
        "This object represents the total number of bytes in the
        error-free packets transmitted on the interface." 
    ::= { cLApEthernetIfEntry 14 }

cLApEthernetIfInputCrc OBJECT-TYPE
    SYNTAX          Counter32
    UNITS           "packets"
    MAX-ACCESS      read-only
    STATUS          current
    DESCRIPTION
        "This object represents the total number of CRC error in
        packets received on the interface." 
    ::= { cLApEthernetIfEntry 15 }

cLApEthernetIfInputAborts OBJECT-TYPE
    SYNTAX          Counter32
    UNITS           "packets"
    MAX-ACCESS      read-only
    STATUS          current
    DESCRIPTION
        "This object represents the total number of packet aborted
        while receiving on the interface." 
    ::= { cLApEthernetIfEntry 16 }

cLApEthernetIfInputErrors OBJECT-TYPE
    SYNTAX          Counter32
    UNITS           "packets"
    MAX-ACCESS      read-only
    STATUS          current
    DESCRIPTION
        "This object represents the sum of all errors in the packets
        while receiving on the interface." 
    ::= { cLApEthernetIfEntry 17 }

cLApEthernetIfInputFrames OBJECT-TYPE
    SYNTAX          Counter32
    UNITS           "packets"
    MAX-ACCESS      read-only
    STATUS          current
    DESCRIPTION
        "This object represents the total number of packet received
        incorrectly having a CRC error and a noninteger number 
        of octets on the interface." 
    ::= { cLApEthernetIfEntry 18 }

cLApEthernetIfInputOverrun OBJECT-TYPE
    SYNTAX          Counter32
    UNITS           "packets"
    MAX-ACCESS      read-only
    STATUS          current
    DESCRIPTION
        "This object represents the number of times the receiver
        hardware was incapable of handing received data to a 
        hardware buffer because the input rate exceeded the 
        receiver's capability to handle the data." 
    ::= { cLApEthernetIfEntry 19 }

cLApEthernetIfInputDrops OBJECT-TYPE
    SYNTAX          Counter32
    UNITS           "packets"
    MAX-ACCESS      read-only
    STATUS          current
    DESCRIPTION
        "This object represents the total number of packets dropped
        while receiving on the interface because the queue 
        was full." 
    ::= { cLApEthernetIfEntry 20 }

cLApEthernetIfInputResource OBJECT-TYPE
    SYNTAX          Counter32
    UNITS           "packets"
    MAX-ACCESS      read-only
    STATUS          current
    DESCRIPTION
        "This object represents the total number of resource errors in
        packets received on the interface." 
    ::= { cLApEthernetIfEntry 21 }

cLApEthernetIfUnknownProtocol OBJECT-TYPE
    SYNTAX          Counter32
    UNITS           "packets"
    MAX-ACCESS      read-only
    STATUS          current
    DESCRIPTION
        "This object represents the total number of packet discarded on
        the interface due to unknown protocol." 
    ::= { cLApEthernetIfEntry 22 }

cLApEthernetIfRunts OBJECT-TYPE
    SYNTAX          Counter32
    UNITS           "packets"
    MAX-ACCESS      read-only
    STATUS          current
    DESCRIPTION
        "This object represents the number of packets that
        are discarded because they are smaller than the 
        medium's minimum packet size." 
    ::= { cLApEthernetIfEntry 23 }

cLApEthernetIfGiants OBJECT-TYPE
    SYNTAX          Counter32
    UNITS           "packets"
    MAX-ACCESS      read-only
    STATUS          current
    DESCRIPTION
        "This object represents the number of packets that
        are discarded because they exceed the medium's 
        maximum packet size." 
    ::= { cLApEthernetIfEntry 24 }

cLApEthernetIfThrottle OBJECT-TYPE
    SYNTAX          Counter32
    MAX-ACCESS      read-only
    STATUS          current
    DESCRIPTION
        "This object represents the total number of times the
        interface advised a sending NIC that it was 
        overwhelmed by packets being sent and to slow the 
        pace of delivery." 
    ::= { cLApEthernetIfEntry 25 }

cLApEthernetIfResets OBJECT-TYPE
    SYNTAX          Counter32
    MAX-ACCESS      read-only
    STATUS          current
    DESCRIPTION
        "This object represents number of times that an
        interface has been completely reset." 
    ::= { cLApEthernetIfEntry 26 }

cLApEthernetIfOutputCollision OBJECT-TYPE
    SYNTAX          Counter32
    UNITS           "packets"
    MAX-ACCESS      read-only
    STATUS          current
    DESCRIPTION
        "This object represents the total number of packet
        retransmitted due to an Ethernet collision." 
    ::= { cLApEthernetIfEntry 27 }

cLApEthernetIfOutputNoBuffer OBJECT-TYPE
    SYNTAX          Counter32
    UNITS           "packets"
    MAX-ACCESS      read-only
    STATUS          current
    DESCRIPTION
        "This object represents the total number of packets discarded
        because there was no buffer space." 
    ::= { cLApEthernetIfEntry 28 }

cLApEthernetIfOutputResource OBJECT-TYPE
    SYNTAX          Counter32
    UNITS           "packets"
    MAX-ACCESS      read-only
    STATUS          current
    DESCRIPTION
        "This object represents the total number of resource
        errors in packets transmitted on the interface." 
    ::= { cLApEthernetIfEntry 29 }

cLApEthernetIfOutputUnderrun OBJECT-TYPE
    SYNTAX          Counter32
    UNITS           "packets"
    MAX-ACCESS      read-only
    STATUS          current
    DESCRIPTION
        "This object represents the number of times the transmitter
        has been running faster than the router can handle." 
    ::= { cLApEthernetIfEntry 30 }

cLApEthernetIfOutputErrors OBJECT-TYPE
    SYNTAX          Counter32
    UNITS           "packets"
    MAX-ACCESS      read-only
    STATUS          current
    DESCRIPTION
        "This object represents sum of all errors that prevented
        the final transmission of packets out of the interface." 
    ::= { cLApEthernetIfEntry 31 }

cLApEthernetIfOutputTotalDrops OBJECT-TYPE
    SYNTAX          Counter32
    UNITS           "packets"
    MAX-ACCESS      read-only
    STATUS          current
    DESCRIPTION
        "This object represents the total number of packets dropped
        while transmitting from the interface because the queue 
        was full." 
    ::= { cLApEthernetIfEntry 32 }

cLApEthernetIfCdpEnabled OBJECT-TYPE
    SYNTAX          TruthValue
    MAX-ACCESS      read-write
    STATUS          current
    DESCRIPTION
        "This object specifies the status of Cisco Discovery
        Protocol(CDP) in this interface represented by
        cLApEthernetIfSlotId of the AP represented by
        cLApSysMacAddress.
        A value of 'true' indicates that CDP is enabled in
        this interface.
        A value of 'false' indicates that CDP is disabled in
        this interface."
    DEFVAL          { true } 
    ::= { cLApEthernetIfEntry 33 }

cLApEthernetIfMtu OBJECT-TYPE
    SYNTAX          Unsigned32
    MAX-ACCESS      read-only
    STATUS          current
    DESCRIPTION
        "This object represents interface's MTU value" 
    ::= { cLApEthernetIfEntry 34 }

cLApEthernetIfType OBJECT-TYPE
    SYNTAX          IANAifType
    MAX-ACCESS      read-only
    STATUS          current
    DESCRIPTION
        "This object represents the type of interface.  Additional
        values for ifType are assigned by the Internet Assigned Numbers
        Authority (IANA), through updating the syntax of the
        IANAifType textual convention." 
    ::= { cLApEthernetIfEntry 35 }

cLApEthernetIfLinkChangeCount OBJECT-TYPE
    SYNTAX          Counter32
    MAX-ACCESS      read-only
    STATUS          current
    DESCRIPTION
        "This object represents the link change count of
        ethernet interface on the AP." 
    ::= { cLApEthernetIfEntry 36 }
 

-- ********************************************************************
-- *  AP Dot11 radio Information
-- ********************************************************************

cLApDot11RadioTable OBJECT-TYPE
    SYNTAX          SEQUENCE OF CLApDot11RadioEntry 
    MAX-ACCESS      not-accessible
    STATUS          current
    DESCRIPTION
        "This table represents the information about the
        basic functional parameters of the radios of the 
        APs that have joined the controller."
    ::= { ciscoLwappApIf 3 }

cLApDot11RadioEntry OBJECT-TYPE
    SYNTAX          CLApDot11RadioEntry
    MAX-ACCESS      not-accessible
    STATUS          current
    DESCRIPTION
        "An entry in this table represents the 802.11
        functional parameters of the radio of
        an AP that has joined the controller.

        Entries are added when the APs associate to this
        controller and deleted when they lose their
        association."
    INDEX           {
                        cLApSysMacAddress,
                        cLApDot11IfSlotId
                    } 
    ::= { cLApDot11RadioTable 1 }

CLApDot11RadioEntry ::= SEQUENCE {
        cLApDot11RadioMACAddress MacAddress,
        cLApDot11RadioSubBand    CLApDot11RadioSubband,
        cLApDot11RadioVersion    SnmpAdminString,
        cLApDot11IsBackhaul      TruthValue,
        cLApDot11RadioRole       CLApDot11RadioRole,
        cLApDot11RadioMode       INTEGER,
        cLApDot11RadioSubType    INTEGER
}

cLApDot11RadioMACAddress OBJECT-TYPE
    SYNTAX          MacAddress
    MAX-ACCESS      read-only
    STATUS          current
    DESCRIPTION
        "This object represents the base Mac address of
        the radio." 
    ::= { cLApDot11RadioEntry 1 }

cLApDot11RadioSubBand OBJECT-TYPE
    SYNTAX          CLApDot11RadioSubband
    MAX-ACCESS      read-only
    STATUS          current
    DESCRIPTION
        "This object reprsents the sub band on which
        this radio operates." 
    ::= { cLApDot11RadioEntry 2 }

cLApDot11RadioVersion OBJECT-TYPE
    SYNTAX          SnmpAdminString (SIZE  (1..50))
    MAX-ACCESS      read-only
    STATUS          current
    DESCRIPTION
        "This object represents the firmware version
        of the radio." 
    ::= { cLApDot11RadioEntry 3 }

cLApDot11IsBackhaul OBJECT-TYPE
    SYNTAX          TruthValue
    MAX-ACCESS      read-only
    STATUS          current
    DESCRIPTION
        "This object represents whether this interface
        is backhaul radio or not.
        A value of 'true' indicates backhaul access for radio is 
        enabled. A value of 'false' indicates backhaul access for 
        radio is disabled." 
    ::= { cLApDot11RadioEntry 4 }

cLApDot11RadioRole OBJECT-TYPE
    SYNTAX          CLApDot11RadioRole
    MAX-ACCESS      read-only
    STATUS          current
    DESCRIPTION
        "This object represents the role of the radio." 
    ::= { cLApDot11RadioEntry 5 }

cLApDot11RadioMode OBJECT-TYPE
    SYNTAX          INTEGER  {
                        local(1),
                        monitor(2),
                        remote(3),
                        rogueDetector(4),
                        sniffer(5),
                        bridge(6),
                        seConnect(7),
                        remoteBridge(8),
                        hybridRemote(9),
                        sensor(10)
                    }
    MAX-ACCESS      read-only
    STATUS          current
    DESCRIPTION
        "This object represents the mode of the radio.
        local(1)         : The default option. Serving WLAN  
                           clients and scanning channels for threats. 
        monitor(2)       : A monitor mode.  AP spends all of its 
                           cycles scanning channels and looking 
                           for rogues. 
        remote(3)        : This mode indicates that AP is a remote 
                           edge lightweight access point. 
        rogueDetector(4) : This mode monitors the rogue APs on wire. 
                           It does not transmit or receive frames 
                           over the air or contain rogue APs. 
        sniffer(5)       : The access point starts sniffing 
                           the air on a given channel. 
        bridge(6)        : This mode indicates that a root AP 
                           is connected.
        seConnect(7)     : AP is connected to spectrum expert. 
                           The AP is able to perform spectrum 
                           intelligence.  
        remoteBridge(8)  : This mode indicates that AP is a remote
                           lightweight access point with root AP 
                           connected.
        hybridRemote(9)  : A mode for branch office and 
                           remote office deployment.
        sensor(10)       : A sensor mode AP."
    ::= { cLApDot11RadioEntry 6 }

cLApDot11RadioSubType OBJECT-TYPE
    SYNTAX          INTEGER  {
                        main(1),
                        rxOnly(2),
                        slaveAc(3),
                        remoteLan(4),
                        xorTxRx(5),
                        bleTxRx(6),
                        bleRxOnly(7),
                        slave(8)
                    }
    MAX-ACCESS      read-only
    STATUS          current
    DESCRIPTION
        "This object represents the subtype of the radio.
        main(1)      :radio operates normally.
        rxOnly(2)    :NOS radio type,which is explicitely used
                      for monitor mode operation.
        slaveAc(3)   :x-ale radio type is only for local mode.
        remoteLan(4) :Remote-LAN supported Slot.
        xorTxRx(5)   :Xor radio capable of both TX and RX.
        bleTxRx(6)   :radio operating normally and BLE is enabled for the AP.
        bleRxOnly(7) :radio is explicitly used for monitor mode operation and BLE is enabled for the AP. 
        slave(8)     :radio operating as slave."
    ::= { cLApDot11RadioEntry 7 }
 


-- ********************************************************************
-- *  Global AP Credentials
-- ********************************************************************

cLApCredentialGlobalUserName OBJECT-TYPE
    SYNTAX          SnmpAdminString
    MAX-ACCESS      read-write
    STATUS          current
    DESCRIPTION
        "This object specifies the global username for
        all the APs already joined or will join the controller.
        This user name is used to access the console on the AP." 
    ::= { ciscoLwappApCredentials 1 }

cLApCredentialGlobalPassword OBJECT-TYPE
    SYNTAX          SnmpAdminString
    MAX-ACCESS      read-write
    STATUS          current
    DESCRIPTION
        "This object specifies the password corresponding to
        the user name represented by cLApCredentialGlobalUserName
        object." 
    ::= { ciscoLwappApCredentials 2 }

cLApCredentialGlobalSecret OBJECT-TYPE
    SYNTAX          SnmpAdminString
    MAX-ACCESS      read-write
    STATUS          current
    DESCRIPTION
        "This object specifies the secret key for
        all the APs already joined or will join the 
        controller. This provides read-write access 
        to the console on the AP." 
    ::= { ciscoLwappApCredentials 3 }
-- ********************************************************************
-- * Per AP Credentials
-- ********************************************************************

cLApCredentialsTable OBJECT-TYPE
    SYNTAX          SEQUENCE OF CLApCredentialsEntry 
    MAX-ACCESS      not-accessible
    STATUS          current
    DESCRIPTION
        "This table provides the information about the credentials
        of the 802.11 LWAPP Access Points that have joined the 
        controller. Rows are added to this table whenever, new APs 
        are joined to this controller, and rows are deleted 
        whenever APs gets disjoined from the controller."
    ::= { ciscoLwappApCredentials 4 }

cLApCredentialsEntry OBJECT-TYPE
    SYNTAX          CLApCredentialsEntry
    MAX-ACCESS      not-accessible
    STATUS          current
    DESCRIPTION
        "Each entry in this table provides information about
        one 802.11 LWAPP Access Point that has joined the
        controller. cLApSysMacAddress is the index which
        uniquely identifies every row in the table."
    INDEX           { cLApSysMacAddress } 
    ::= { cLApCredentialsTable 1 }

CLApCredentialsEntry ::= SEQUENCE {
        cLApCredentialUserName                SnmpAdminString,
        cLApCredentialPassword                SnmpAdminString,
        cLApCredentialSecret                  SnmpAdminString,
        cLApCredentialEnableGlobalCredentials TruthValue
}

cLApCredentialUserName OBJECT-TYPE
    SYNTAX          SnmpAdminString
    MAX-ACCESS      read-create
    STATUS          current
    DESCRIPTION
        "This object specifies the username for
        this AP." 
    ::= { cLApCredentialsEntry 1 }

cLApCredentialPassword OBJECT-TYPE
    SYNTAX          SnmpAdminString
    MAX-ACCESS      read-create
    STATUS          current
    DESCRIPTION
        "This object specifies the password corresponding to
        user name represented by cLApCredentialUserName object." 
    ::= { cLApCredentialsEntry 2 }

cLApCredentialSecret OBJECT-TYPE
    SYNTAX          SnmpAdminString
    MAX-ACCESS      read-create
    STATUS          current
    DESCRIPTION
        "This object specifies the secret key for
        the specific AP. This provides the read-write access
        on the console for this AP." 
    ::= { cLApCredentialsEntry 3 }

cLApCredentialEnableGlobalCredentials OBJECT-TYPE
    SYNTAX          TruthValue
    MAX-ACCESS      read-create
    STATUS          current
    DESCRIPTION
        "This object  specifies whether the global credentials
        for the AP is enabled or disabled.

        A value of 'true' indicates the global username/password
        to be used for this AP .
        A value of 'false' indicates the global
        credentials and uses the credentials specific for this
        AP is disabled." 
    ::= { cLApCredentialsEntry 4 }
 

-- ********************************************************************
-- *  Link Latency parameters
-- ********************************************************************

cLApLinkLatencyTable OBJECT-TYPE
    SYNTAX          SEQUENCE OF CLApLinkLatencyEntry 
    MAX-ACCESS      not-accessible
    STATUS          current
    DESCRIPTION
        "This table represents the link latency configuration
        for each AP. 
        An entry is automatically added to this table when 
        an Access Points Joins controller. 
        Entry is removed from this table when AP 
        disassociates from the controllers."
    ::= { ciscoLwappLinkLatency 1 }

cLApLinkLatencyEntry OBJECT-TYPE
    SYNTAX          CLApLinkLatencyEntry
    MAX-ACCESS      not-accessible
    STATUS          current
    DESCRIPTION
        "Each entry in this table provides configuration
        related to Link latency on each AP."
    INDEX           { cLApSysMacAddress } 
    ::= { cLApLinkLatencyTable 1 }

CLApLinkLatencyEntry ::= SEQUENCE {
        cLApLinkLatencyEnable TruthValue,
        cLApLinkLatencyReset  TruthValue
}

cLApLinkLatencyEnable OBJECT-TYPE
    SYNTAX          TruthValue
    MAX-ACCESS      read-write
    STATUS          current
    DESCRIPTION
        "This object specifies to configure the Link
        Latency on the AP.             
        A value of 'true' indicates that the Link Latency
        is enabled.
        A value of 'false' indicates that the Link Latency 
        is disabled."
    DEFVAL          { false } 
    ::= { cLApLinkLatencyEntry 1 }

cLApLinkLatencyReset OBJECT-TYPE
    SYNTAX          TruthValue
    MAX-ACCESS      read-write
    STATUS          current
    DESCRIPTION
        "This object specifies to reset the Link Latency
        stored at controller for an AP.             
        A value of 'true' indicates that the Link Latency stats 
        is to be reset.
        A value of 'false' on this during set will return error.
        A value of false will be returned on get."
    DEFVAL          { false } 
    ::= { cLApLinkLatencyEntry 2 }
 

-- ********************************************************************
-- *  Link Latency Stats
-- ********************************************************************

cLApLinkLatencyStatsTable OBJECT-TYPE
    SYNTAX          SEQUENCE OF CLApLinkLatencyStatsEntry 
    MAX-ACCESS      not-accessible
    STATUS          current
    DESCRIPTION
        "This table represents the link latency statistics
        calculated for each AP. 
        An entry is automatically added by the controller
        when a 'cLApLinkLatencyEnable' is enabled on an 
        Access Point. Entry is deleted when 
        'cLApLinkLatencyEnable' is disabled on the 
        Access Point."
    ::= { ciscoLwappLinkLatency 2 }

cLApLinkLatencyStatsEntry OBJECT-TYPE
    SYNTAX          CLApLinkLatencyStatsEntry
    MAX-ACCESS      not-accessible
    STATUS          current
    DESCRIPTION
        "Each entry in this table provides minimum, maximum
        and average Link latency for a Access Point. 
        Entries are removed when the Link Latency is disabled 
        on a Access Point."
    INDEX           { cLApSysMacAddress } 
    ::= { cLApLinkLatencyStatsTable 1 }

CLApLinkLatencyStatsEntry ::= SEQUENCE {
        cLApLinkLatencyStatsCurrent     TimeInterval,
        cLApLinkLatencyStatsMin         TimeInterval,
        cLApLinkLatencyStatsMax         TimeInterval,
        cLApLinkLatencyTimeStamp        TimeStamp,
        cLApDataLinkLatencyStatsCurrent TimeInterval,
        cLApDataLinkLatencyStatsMin     TimeInterval,
        cLApDataLinkLatencyStatsMax     TimeInterval,
        cLApDataLinkLatencyTimeStamp    TimeStamp
}

cLApLinkLatencyStatsCurrent OBJECT-TYPE
    SYNTAX          TimeInterval
    UNITS           "milliseconds"
    MAX-ACCESS      read-only
    STATUS          current
    DESCRIPTION
        "This object represents the current Link latency recorded for
        this Access point." 
    ::= { cLApLinkLatencyStatsEntry 1 }

cLApLinkLatencyStatsMin OBJECT-TYPE
    SYNTAX          TimeInterval
    UNITS           "milliseconds"
    MAX-ACCESS      read-only
    STATUS          current
    DESCRIPTION
        "This object represents the minimum Link latency recorded for
        this Access point." 
    ::= { cLApLinkLatencyStatsEntry 2 }

cLApLinkLatencyStatsMax OBJECT-TYPE
    SYNTAX          TimeInterval
    UNITS           "milliseconds"
    MAX-ACCESS      read-only
    STATUS          current
    DESCRIPTION
        "This object represents the maximum Link latency recorded for
        this Access point." 
    ::= { cLApLinkLatencyStatsEntry 3 }

cLApLinkLatencyTimeStamp OBJECT-TYPE
    SYNTAX          TimeStamp
    UNITS           "seconds"
    MAX-ACCESS      read-only
    STATUS          current
    DESCRIPTION
        "This object represents the timestamp, when the values are
        collected, as returned by the object 'cLApUpTime'." 
    ::= { cLApLinkLatencyStatsEntry 4 }

cLApDataLinkLatencyStatsCurrent OBJECT-TYPE
    SYNTAX          TimeInterval
    UNITS           "milliseconds"
    MAX-ACCESS      read-only
    STATUS          current
    DESCRIPTION
        "This object represents the current Data Link latency recorded
        for this Access point." 
    ::= { cLApLinkLatencyStatsEntry 5 }

cLApDataLinkLatencyStatsMin OBJECT-TYPE
    SYNTAX          TimeInterval
    UNITS           "milliseconds"
    MAX-ACCESS      read-only
    STATUS          current
    DESCRIPTION
        "This object represents the minimum Data Link latency recorded
        for this Access point." 
    ::= { cLApLinkLatencyStatsEntry 6 }

cLApDataLinkLatencyStatsMax OBJECT-TYPE
    SYNTAX          TimeInterval
    UNITS           "milliseconds"
    MAX-ACCESS      read-only
    STATUS          current
    DESCRIPTION
        "This object represents the maximum Data Link latency recorded
        for this Access point." 
    ::= { cLApLinkLatencyStatsEntry 7 }

cLApDataLinkLatencyTimeStamp OBJECT-TYPE
    SYNTAX          TimeStamp
    UNITS           "seconds"
    MAX-ACCESS      read-only
    STATUS          current
    DESCRIPTION
        "This object represents the timestamp, when the values are
        collected, as returned by the object 'cLApUpTime'." 
    ::= { cLApLinkLatencyStatsEntry 8 }
 

-- ********************************************************************
-- *  AP LAN Stats.
-- ********************************************************************

cLAplanStatsTable OBJECT-TYPE
    SYNTAX          SEQUENCE OF CLAplanStatsEntry 
    MAX-ACCESS      not-accessible
    STATUS          current
    DESCRIPTION
        "This table represents Saridinia AP LAN stats
        information that have joined the controller."
    ::= { ciscoLwappAplanStats 1 }

cLAplanStatsEntry OBJECT-TYPE
    SYNTAX          CLAplanStatsEntry
    MAX-ACCESS      not-accessible
    STATUS          current
    DESCRIPTION
        "This entry contains stats information of
        LAN stats"
    INDEX           {
                        cLApSysMacAddress,
                        cLApLanPortId
                    } 
    ::= { cLAplanStatsTable 1 }

CLAplanStatsEntry ::= SEQUENCE {
        cLApLanPortId          Integer32,
        cLApLanPortState       TruthValue,
        cLApLanPortVlanId      Unsigned32,
        cLApLanPortVlanIdValid TruthValue,
        cLApLanPoeState        TruthValue,
        cLApLanPowerLevelId    Unsigned32
}

cLApLanPortId OBJECT-TYPE
    SYNTAX          Integer32 (1..4)
    MAX-ACCESS      not-accessible
    STATUS          current
    DESCRIPTION
        "This object represents the ID of a LAN
        port of an AP." 
    ::= { cLAplanStatsEntry 1 }

cLApLanPortState OBJECT-TYPE
    SYNTAX          TruthValue
    MAX-ACCESS      read-write
    STATUS          current
    DESCRIPTION
        "This object specifies the state of an
        ethernet interface of AP.
        A value of 'true' indicates admin status of 
        ethernet interface is up.
        A value of 'false' indicates admin status of
        ethernet interface is down."
    DEFVAL          { false } 
    ::= { cLAplanStatsEntry 2 }

cLApLanPortVlanId OBJECT-TYPE
    SYNTAX          Unsigned32 (0..4094)
    MAX-ACCESS      read-write
    STATUS          current
    DESCRIPTION
        "This object specifies the Vlan Id of
        the ethernet interface. When the value is 0 ,
        the VLAN access is disabled."
    DEFVAL          { 0 } 
    ::= { cLAplanStatsEntry 3 }

cLApLanPortVlanIdValid OBJECT-TYPE
    SYNTAX          TruthValue
    MAX-ACCESS      read-only
    STATUS          current
    DESCRIPTION
        "This object represents VLAN ID is valid or not
        for an ethernet interface.
        A value of 'true' indicates vlanId is valid.
        A value of 'false' indicates vlanId is not valid."
    DEFVAL          { false } 
    ::= { cLAplanStatsEntry 4 }

cLApLanPoeState OBJECT-TYPE
    SYNTAX          TruthValue
    MAX-ACCESS      read-write
    STATUS          current
    DESCRIPTION
        "This object specifies the LAN PoE Status  of an
        ethernet interface of an AP.
        A value of 'true' indicates poe state is enabled for
        ethernet interface.
        A value of 'false' indicates poe state is disabled for
        ethernet interface."
    DEFVAL          { false } 
    ::= { cLAplanStatsEntry 5 }
 
cLApLanPowerLevelId OBJECT-TYPE
    SYNTAX          Unsigned32 (1..4)
    MAX-ACCESS      read-write
    STATUS          current
    DESCRIPTION
        "This object specifies the power level
         of the port"
    DEFVAL          { 4 } 
    ::= { cLAplanStatsEntry 6 }



cLAplanOverrideTable OBJECT-TYPE
    SYNTAX          SEQUENCE OF CLAplanOverrideEntry 
    MAX-ACCESS      not-accessible
    STATUS          current
    DESCRIPTION
        "This table represents the lan override status of an AP"
    ::= { ciscoLwappAplanStats 2 }

cLAplanOverrideEntry OBJECT-TYPE
    SYNTAX          CLAplanOverrideEntry
    MAX-ACCESS      not-accessible
    STATUS          current
    DESCRIPTION
        "This entry contains stats information of LAN override status"
    INDEX           { cLApSysMacAddress } 
    ::= { cLAplanOverrideTable 1 }

CLAplanOverrideEntry ::= SEQUENCE {
        cLApLanOverride TruthValue
}

cLApLanOverride OBJECT-TYPE
    SYNTAX          TruthValue
    MAX-ACCESS      read-write
    STATUS          current
    DESCRIPTION
        "This object specifies the LAN port override status of AP.
        A value of 'true' indicates LAN override is enabled.
        A value of 'false' indicates LAN override is disabled."
    DEFVAL          { false } 
    ::= { cLAplanOverrideEntry 1 }
 

-- ********************************************************************
-- *  AP WLAN Stats.
-- ********************************************************************

cLApWlanStatsTable OBJECT-TYPE
    SYNTAX          SEQUENCE OF CLApWlanStatsEntry 
    MAX-ACCESS      not-accessible
    STATUS          current
    DESCRIPTION
        "This table represents Per-AP, Per-Radio, Per-SSID
        Stats information of packets/bytes sent/received,
        retransmission counter, associated clients counter,
        etc."
    ::= { ciscoLwappApWlanStats 1 }

cLApWlanStatsEntry OBJECT-TYPE
    SYNTAX          CLApWlanStatsEntry
    MAX-ACCESS      not-accessible
    STATUS          current
    DESCRIPTION
        "This entry contains stats information of
        packets/bytes sent/received, retransmission counter,
        associated clients counter, and etc."
    INDEX           {
                        cLApSysMacAddress,
                        cLApDot11IfType,
                        cLWlanIndex
                    } 
    ::= { cLApWlanStatsTable 1 }

CLApWlanStatsEntry ::= SEQUENCE {
        cLApWlanStatsTxPktNum       Counter64,
        cLApWlanStatsTxOctetNum     Counter64,
        cLApWlanStatsRxPktNum       Counter64,
        cLApWlanStatsRxOctetNum     Counter64,
        cLApWlanStatsRetransmitNum  Counter64,
        cLApWlanStatsAssocClientNum Unsigned32,
        cLApWlanStatsOnlineUserNum  Unsigned32
}

cLApWlanStatsTxPktNum OBJECT-TYPE
    SYNTAX          Counter64
    UNITS           "packets"
    MAX-ACCESS      read-only
    STATUS          current
    DESCRIPTION
        "This object represents the transmitted packets counter of
        the specific radio and wlan on this access point." 
    ::= { cLApWlanStatsEntry 1 }

cLApWlanStatsTxOctetNum OBJECT-TYPE
    SYNTAX          Counter64
    UNITS           "packets"
    MAX-ACCESS      read-only
    STATUS          current
    DESCRIPTION
        "This object represents the transmitted bytes counter of
        the specific radio and wlan on this access point." 
    ::= { cLApWlanStatsEntry 2 }

cLApWlanStatsRxPktNum OBJECT-TYPE
    SYNTAX          Counter64
    UNITS           "packets"
    MAX-ACCESS      read-only
    STATUS          current
    DESCRIPTION
        "This object represents the received packets counter of
        the specific radio and wlan on this access point." 
    ::= { cLApWlanStatsEntry 3 }

cLApWlanStatsRxOctetNum OBJECT-TYPE
    SYNTAX          Counter64
    UNITS           "packets"
    MAX-ACCESS      read-only
    STATUS          current
    DESCRIPTION
        "This object represents the received bytes counter of
        the specific radio and wlan on this access point." 
    ::= { cLApWlanStatsEntry 4 }

cLApWlanStatsRetransmitNum OBJECT-TYPE
    SYNTAX          Counter64
    UNITS           "packets"
    MAX-ACCESS      read-only
    STATUS          current
    DESCRIPTION
        "This object represents the packet retransmission counter of
        the specific radio and wlan on this access point." 
    ::= { cLApWlanStatsEntry 5 }

cLApWlanStatsAssocClientNum OBJECT-TYPE
    SYNTAX          Unsigned32
    MAX-ACCESS      read-only
    STATUS          current
    DESCRIPTION
        "This object represents the associated client counter of
        the specific radio and wlan on this access point." 
    ::= { cLApWlanStatsEntry 6 }

cLApWlanStatsOnlineUserNum OBJECT-TYPE
    SYNTAX          Unsigned32
    MAX-ACCESS      read-only
    STATUS          current
    DESCRIPTION
        "This object represents the online user counter of
        the specific radio and wlan on this access point." 
    ::= { cLApWlanStatsEntry 7 }
 

-- ********************************************************************
-- *  AP slot WLAN Stats.
-- ********************************************************************

cLApSlotWlanStatsTable OBJECT-TYPE
    SYNTAX          SEQUENCE OF CLApSlotWlanStatsEntry
    MAX-ACCESS      not-accessible
    STATUS          current
    DESCRIPTION
        "This table represents Per-AP, Per-Slot, Per-SSID
        Stats information of packets/bytes sent/received,
        retransmission counter, associated clients counter,
        etc."
    ::= { ciscoLwappApSlotWlanStats 1 }

cLApSlotWlanStatsEntry OBJECT-TYPE
    SYNTAX          CLApSlotWlanStatsEntry
    MAX-ACCESS      not-accessible
    STATUS          current
    DESCRIPTION
        "This entry contains stats information of
        packets/bytes sent/received, retransmission counter,
        associated clients counter, and etc."
    INDEX           {
                        cLApSysMacAddress,
                        cLApDot11IfSlotId,
                        cLWlanIndex
                    }
    ::= { cLApSlotWlanStatsTable 1 }

CLApSlotWlanStatsEntry ::= SEQUENCE {
        cLApSlotWlanStatsTxPktNum       Counter64,
        cLApSlotWlanStatsTxOctetNum     Counter64,
        cLApSlotWlanStatsRxPktNum       Counter64,
        cLApSlotWlanStatsRxOctetNum     Counter64,
        cLApSlotWlanStatsRetransmitNum  Counter64,
        cLApSlotWlanStatsAssocClientNum Unsigned32,
        cLApSlotWlanStatsOnlineUserNum  Unsigned32
}

cLApSlotWlanStatsTxPktNum OBJECT-TYPE
    SYNTAX          Counter64
    UNITS           "packets"
    MAX-ACCESS      read-only
    STATUS          current
    DESCRIPTION
        "This object represents the transmitted packets counter of
        the specific radio and wlan on this access point."
    ::= { cLApSlotWlanStatsEntry 1 }

cLApSlotWlanStatsTxOctetNum OBJECT-TYPE
    SYNTAX          Counter64
    UNITS           "packets"
    MAX-ACCESS      read-only
    STATUS          current
    DESCRIPTION
        "This object represents the transmitted bytes counter of
        the specific radio and wlan on this access point."
    ::= { cLApSlotWlanStatsEntry 2 }

cLApSlotWlanStatsRxPktNum OBJECT-TYPE
    SYNTAX          Counter64
    UNITS           "packets"
    MAX-ACCESS      read-only
    STATUS          current
    DESCRIPTION
        "This object represents the received packets counter of
        the specific radio and wlan on this access point."
    ::= { cLApSlotWlanStatsEntry 3 }

cLApSlotWlanStatsRxOctetNum OBJECT-TYPE
    SYNTAX          Counter64
    UNITS           "packets"
    MAX-ACCESS      read-only
    STATUS          current
    DESCRIPTION
        "This object represents the received bytes counter of
        the specific radio and wlan on this access point."
    ::= { cLApSlotWlanStatsEntry 4 }

cLApSlotWlanStatsRetransmitNum OBJECT-TYPE
    SYNTAX          Counter64
    UNITS           "packets"
    MAX-ACCESS      read-only
    STATUS          current
    DESCRIPTION
        "This object represents the packet retransmission counter of
        the specific radio and wlan on this access point."
    ::= { cLApSlotWlanStatsEntry 5 }

cLApSlotWlanStatsAssocClientNum OBJECT-TYPE
    SYNTAX          Unsigned32
    MAX-ACCESS      read-only
    STATUS          current
    DESCRIPTION
        "This object represents the associated client counter of
        the specific radio and wlan on this access point."
    ::= { cLApSlotWlanStatsEntry 6 }

cLApSlotWlanStatsOnlineUserNum OBJECT-TYPE
    SYNTAX          Unsigned32
    MAX-ACCESS      read-only
    STATUS          current
    DESCRIPTION
        "This object represents the online user counter of
        the specific radio and wlan on this access point."
    ::= { cLApSlotWlanStatsEntry 7 }

-- ********************************************************************
-- *  AP Station Mgmt(SMT) Parameters
-- ********************************************************************

cLApIfSmtParamTable OBJECT-TYPE
    SYNTAX          SEQUENCE OF CLApIfSmtParamEntry 
    MAX-ACCESS      not-accessible
    STATUS          current
    DESCRIPTION
        "This table represents the station management
        information in the APs that have joined the
        controller.  Information populated through the
        entries of this table is used by the AP to
        perform the expected 802.11 operations on
        the respective dot11 interfaces to coordinate with
        other 802.11 devices in the network.

        Since this table has the indices defined in the
        tables cLApTable and cLApDot11IfTable, an entry in
        this table is automatically removed when the
        respective entry is removed in either of those
        tables."
    ::= { ciscoLwappAp 2 }

cLApIfSmtParamEntry OBJECT-TYPE
    SYNTAX          CLApIfSmtParamEntry
    MAX-ACCESS      not-accessible
    STATUS          current
    DESCRIPTION
        "An entry in this table represents the information
        pertaining to one particular dot11 interface of
        this AP used to perform the 802.11 protocol
        operations on the respective dot11 interface.

        Rows are added or deleted to this table when
        APs join or leave the controller respectively."
    INDEX           {
                        cLApSysMacAddress,
                        cLApDot11IfSlotId
                    } 
    ::= { cLApIfSmtParamTable 1 }

CLApIfSmtParamEntry ::= SEQUENCE {
        cLApIfSmtDot11Bssid MacAddress
}

cLApIfSmtDot11Bssid OBJECT-TYPE
    SYNTAX          MacAddress
    MAX-ACCESS      read-only
    STATUS          current
    DESCRIPTION
        "This object represents the base BSSID of this AP, which
        is the MAC address of the radio interface of this
        AP." 
    ::= { cLApIfSmtParamEntry 1 }
 

-- ********************************************************************
-- Country code setting for APs that have joined the controller
-- ********************************************************************

cLApCountryTable OBJECT-TYPE
    SYNTAX          SEQUENCE OF CLApCountryEntry 
    MAX-ACCESS      not-accessible
    STATUS          current
    DESCRIPTION
        "This table represents the country settings for
        the 802.11 LWAPP Access Points that have joined the
        controller.
        An entry is automatically added by the controller 
        when a Access Point joins the controller. 
        The entry is removed when Access Point disasscociates 
        from the controller."
    ::= { ciscoLwappAp 3 }

cLApCountryEntry OBJECT-TYPE
    SYNTAX          CLApCountryEntry
    MAX-ACCESS      not-accessible
    STATUS          current
    DESCRIPTION
        "Each entry in this table provides country setting
        about one 802.11 LWAPP Access Point that has joined 
        the controller.
        Entries are removed when the APs lose their
        association with the controller due to loss
        of communication."
    INDEX           { cLApSysMacAddress } 
    ::= { cLApCountryTable 1 }

CLApCountryEntry ::= SEQUENCE {
        cLApCountryCode    SnmpAdminString,
        cLApCountryAllowed SnmpAdminString
}

cLApCountryCode OBJECT-TYPE
    SYNTAX          SnmpAdminString (SIZE  (1..255))
    MAX-ACCESS      read-write
    STATUS          current
    DESCRIPTION
        "This object specifies the country in which the
        AP is operating. This value is the 3 letter country  
        code." 
    ::= { cLApCountryEntry 1 }

cLApCountryAllowed OBJECT-TYPE
    SYNTAX          SnmpAdminString (SIZE  (1..255))
    MAX-ACCESS      read-only
    STATUS          current
    DESCRIPTION
        "This object represents the country in which the
        AP is operating. This value is a list of country  
        codes sperated by comma." 
    ::= { cLApCountryEntry 2 }
 


-- ********************************************************************
-- * Halo BLE Configuration to set Beacon parameters of Halo enabled APs
-- ********************************************************************

cLHaloGlobalBleBeaconInterval OBJECT-TYPE
    SYNTAX          Unsigned32 (1..10)
    UNITS           "Hz"
    MAX-ACCESS      read-write
    STATUS          current
    DESCRIPTION
        "This object represents  the beacon interval
        between each transmissions from BLE module.
        This value is common to HALO enabled APs that
        have joined the controller."
    DEFVAL          { 1 } 
    ::= { ciscoLwappApGlobalBleBeacon 1 }

cLHaloBleBeaconTable OBJECT-TYPE
    SYNTAX          SEQUENCE OF CLHaloBleBeaconEntry 
    MAX-ACCESS      not-accessible
    STATUS          current
    DESCRIPTION
        "This table represents the BLE global configuration.It lists
        the ibeacon's identification number and attenuation value
        which is common to HALO enabled AP's that 
        have joined the controller."
    ::= { ciscoLwappApGlobalBleBeacon 2 }

cLHaloBleBeaconEntry OBJECT-TYPE
    SYNTAX          CLHaloBleBeaconEntry
    MAX-ACCESS      not-accessible
    STATUS          current
    DESCRIPTION
        "This entry contains BLE global configuration which lists
        the ibeacon's identification number and attenuation value
        of HALO enabled APs that have joined the controller."
    INDEX           { cLHaloGlobalBleBeaconId } 
    ::= { cLHaloBleBeaconTable 1 }

CLHaloBleBeaconEntry ::= SEQUENCE {
        cLHaloGlobalBleBeaconId      Unsigned32,
        cLHaloGlobalBleBeaconUuid    SnmpAdminString,
        cLHaloGlobalBleBeaconTxPower Unsigned32,
        cLHaloGlobalBleBeaconEnable  TruthValue
}

cLHaloGlobalBleBeaconId OBJECT-TYPE
    SYNTAX          Unsigned32
    MAX-ACCESS      not-accessible
    STATUS          current
    DESCRIPTION
        "This object represents the BLE ibeacon ID for
        which gloabl BLE configurations to be 
        applied." 
    ::= { cLHaloBleBeaconEntry 1 }

cLHaloGlobalBleBeaconUuid OBJECT-TYPE
    SYNTAX          SnmpAdminString (SIZE  (0..128))
    MAX-ACCESS      read-write
    STATUS          current
    DESCRIPTION
        "This object specifies the UUID (universally unique identifier)
        which is a 128-bit value." 
    ::= { cLHaloBleBeaconEntry 2 }

cLHaloGlobalBleBeaconTxPower OBJECT-TYPE
    SYNTAX          Unsigned32 (0..52)
    UNITS           "dBm"
    MAX-ACCESS      read-write
    STATUS          current
    DESCRIPTION
        "This object specifies TX power of particular ibeacon for
        HALO enabled APs that have joined the controller.The TX power
        is based on size of proximity zone needed." 
    ::= { cLHaloBleBeaconEntry 3 }

cLHaloGlobalBleBeaconEnable OBJECT-TYPE
    SYNTAX          TruthValue
    MAX-ACCESS      read-write
    STATUS          current
    DESCRIPTION
        "This object specifies the status of the BLE beacons.
        A value of 'true' indicates BLE beacon is enabled.
        A value of 'false' indicates BLE beacon is disabled." 
    ::= { cLHaloBleBeaconEntry 4 }
 


cLApBleBeaconTable OBJECT-TYPE
    SYNTAX          SEQUENCE OF CLApBleBeaconEntry 
    MAX-ACCESS      not-accessible
    STATUS          current
    DESCRIPTION
        "This table represents BLE ibeacon's AP specific configuration
        for HALO enabled APs that have joined the controller."
    ::= { ciscoLwappApGlobalBleBeacon 3 }

cLApBleBeaconEntry OBJECT-TYPE
    SYNTAX          CLApBleBeaconEntry
    MAX-ACCESS      not-accessible
    STATUS          current
    DESCRIPTION
        "This entry contains BLE Beacon's AP specific configuration."
    INDEX           {
                        cLApSysMacAddress,
                        cLHaloGlobalBleBeaconId
                    } 
    ::= { cLApBleBeaconTable 1 }

CLApBleBeaconEntry ::= SEQUENCE {
        cLApBleBeaconMajorField  Unsigned32,
        cLApBleBeaconMinorField  Unsigned32,
        cLApBleBeaconTxPower     Unsigned32,
        cLApBleBeaconStatus      TruthValue,
        cLApBleBeaconUuid        SnmpAdminString,
        cLApBleBeaconInterval    Unsigned32,
        cLApBleBeaconApplyGlobal TruthValue,
        cLApBleBeaconAdvTxPower  Unsigned32
}

cLApBleBeaconMajorField OBJECT-TYPE
    SYNTAX          Unsigned32
    MAX-ACCESS      read-write
    STATUS          current
    DESCRIPTION
        "This object specifies the Major value of ibeacon
        that is used to differentiate ibeacons that have the same
        proximity UUID." 
    ::= { cLApBleBeaconEntry 1 }

cLApBleBeaconMinorField OBJECT-TYPE
    SYNTAX          Unsigned32
    MAX-ACCESS      read-write
    STATUS          current
    DESCRIPTION
        "This object specifies the Minor value of ibeacon
        that is used to differentiate ibeacons that have the same
        proximity UUID and has same major value." 
    ::= { cLApBleBeaconEntry 2 }

cLApBleBeaconTxPower OBJECT-TYPE
    SYNTAX          Unsigned32 (0..52)
    UNITS           "dBm"
    MAX-ACCESS      read-write
    STATUS          current
    DESCRIPTION
        "This object specifies TX power of particular ibeacon for
        specified HALO enabled AP. The TX power value is based on 
        the size of proximity zone needed." 
    ::= { cLApBleBeaconEntry 3 }

cLApBleBeaconStatus OBJECT-TYPE
    SYNTAX          TruthValue
    MAX-ACCESS      read-write
    STATUS          current
    DESCRIPTION
        "This object specifies the status of the BLE beacons.
        A value of 'true' indicates BLE beacon is enabled,
        A value of 'false' indicates BLE beacon is disabled." 
    ::= { cLApBleBeaconEntry 4 }

cLApBleBeaconUuid OBJECT-TYPE
    SYNTAX          SnmpAdminString (SIZE  (0..128))
    MAX-ACCESS      read-write
    STATUS          current
    DESCRIPTION
        "This object specifies the UUID (universally unique identifier)
        which is a 128-bit value." 
    ::= { cLApBleBeaconEntry 5 }

cLApBleBeaconInterval OBJECT-TYPE
    SYNTAX          Unsigned32 (1..10)
    UNITS           "Hz"
    MAX-ACCESS      read-write
    STATUS          current
    DESCRIPTION
        "This object specifies the beacon interval
        between each transmissions from BLE module.
        This value is common to HALO enabled APs that
        have joined the controller."
    DEFVAL          { 1 } 
    ::= { cLApBleBeaconEntry 6 }

cLApBleBeaconApplyGlobal OBJECT-TYPE
    SYNTAX          TruthValue
    MAX-ACCESS      read-write
    STATUS          current
    DESCRIPTION
        "This object specifies to clear all BLE configuration at AP.
        A value of 'true' indicates configurations need to be cleared.
        A value of 'false' indicates configurations need not be 
        cleared."
    DEFVAL          { false } 
    ::= { cLApBleBeaconEntry 7 }

cLApBleBeaconAdvTxPower OBJECT-TYPE
    SYNTAX          Unsigned32 (40..100)
    UNITS           "Hz"
    MAX-ACCESS      read-write
    STATUS          current
    DESCRIPTION
        "This object specifies the beacon advertised transmission
        power in the BLE beacon payload.
        This value is common to all beacons for a single AP."
    DEFVAL          { 59 } 
    ::= { cLApBleBeaconEntry 8 }
 

-- ********************************************************************
-- * Halo BLE Module Mibs
-- ********************************************************************
-- ********************************************************************
-- * Halo Hyperlocation Config Mibs
-- ********************************************************************

cLApHyperlocationTable OBJECT-TYPE
    SYNTAX          SEQUENCE OF CLApHyperlocationEntry 
    MAX-ACCESS      not-accessible
    STATUS          current
    DESCRIPTION
        "This table represents the information about the
        APs hyperlocation state and its config nature 
        controller."
    ::= { ciscoLwappApHyperlocation 1 }

cLApHyperlocationEntry OBJECT-TYPE
    SYNTAX          CLApHyperlocationEntry
    MAX-ACCESS      not-accessible
    STATUS          current
    DESCRIPTION
        "Each entry in this table provides information about
        Hyperlocation state and config nature of APs 
        controller."
    INDEX           { cLApSysMacAddress } 
    ::= { cLApHyperlocationTable 1 }

CLApHyperlocationEntry ::= SEQUENCE {
        cLApHyperlocationAdminState TruthValue,
        cLApHyperlocationUnsetFlag  TruthValue
}

cLApHyperlocationAdminState OBJECT-TYPE
    SYNTAX          TruthValue
    MAX-ACCESS      read-write
    STATUS          current
    DESCRIPTION
        "This object specifies the hyperlocation admin state
        for an AP to be enabled or disabled.
         A value of 'true' indicates admin state of HALO module
         is up.
         A value of 'false' indicates admin state of HALO module
         is down." 
    ::= { cLApHyperlocationEntry 1 }

cLApHyperlocationUnsetFlag OBJECT-TYPE
    SYNTAX          TruthValue
    MAX-ACCESS      read-write
    STATUS          current
    DESCRIPTION
        "This object specifies explicit flag status
        for AP need to be enabled  or not.

        A value of 'true' indicates AP has an explicit per AP config.
        A value of 'false' indicates there is no AP config" 
    ::= { cLApHyperlocationEntry 2 }
 


-- ********************************************************************
-- * Halo Hyperlocation Config Mibs
-- ********************************************************************
-- ********************************************************************
-- *  Notification Control Object
-- ********************************************************************

ciscoLwappApIfRegulatoryDomainMismatchNotifEnabled OBJECT-TYPE
    SYNTAX          TruthValue
    MAX-ACCESS      read-write
    STATUS          current
    DESCRIPTION
        "The object to control the generation of
        ciscoLwappApIfRegulatoryDomainMismatchNotif 
        notification.

        A value of 'true' indicates that the agent 
        generates ciscoLwappApIfRegulatoryDomainMismatchNotif 
        notification.

                 A value of 'false' indicates that the agent doesn't
                 generate ciscoLwappApIfRegulatoryDomainMismatchNotif
                 notification."
    DEFVAL          { true } 
    ::= { ciscoLwappAp 4 }

ciscoLwappApCrashEnabled OBJECT-TYPE
    SYNTAX          TruthValue
    MAX-ACCESS      read-write
    STATUS          current
    DESCRIPTION
        "The object to control the generation of
        ciscoLwappApCrash notification.

        A value of 'true' indicates that the agent generates
        ciscoLwappApCrash notification.

        A value of 'false' indicates that the agent doesn't
        generate ciscoLwappApCrash notification."
    DEFVAL          { true } 
    ::= { ciscoLwappAp 5 }

ciscoLwappApUnsupportedEnabled OBJECT-TYPE
    SYNTAX          TruthValue
    MAX-ACCESS      read-write
    STATUS          current
    DESCRIPTION
        "The object to control the generation of
        ciscoLwappApUnsupported notification.

        A value of 'true' indicates that the agent generates
        ciscoLwappApUnsupported notification.

        A value of 'false' indicates that the agent doesn't
        generate ciscoLwappApUnsupported
        notification."
    DEFVAL          { true } 
    ::= { ciscoLwappAp 6 }

ciscoLwappApAssociatedEnabled OBJECT-TYPE
    SYNTAX          TruthValue
    MAX-ACCESS      read-write
    STATUS          current
    DESCRIPTION
        "The object to control the generation of
        ciscoLwappApAssociated notification.

        A value of 'true' indicates that the agent generates
        ciscoLwappApAssociated notification.

        A value of 'false' indicates that the agent doesn't
        generate ciscoLwappApAssociated notification."
    DEFVAL          { true } 
    ::= { ciscoLwappAp 7 }

ciscoLwappXorRadioRoleChangeEnabled OBJECT-TYPE
    SYNTAX          TruthValue
    MAX-ACCESS      read-write
    STATUS          current
    DESCRIPTION
        "The object to control the generation of
        ciscoLwappApXorRadioRoleChangeNotify notification.

        A value of 'true' indicates that the agent generates
        ciscoLwappApXorRadioRoleChangeNotify notification.

        A value of 'false' indicates that the agent doesn't 
        generate ciscoLwappApXorRadioRoleChangeNotify notification."
    DEFVAL          { true } 
    ::= { ciscoLwappAp 13 }
-- ********************************************************************
-- Spectrum Expert Connection parameters
-- ********************************************************************

cLApSeClientTable OBJECT-TYPE
    SYNTAX          SEQUENCE OF CLApSeClientEntry 
    MAX-ACCESS      not-accessible
    STATUS          current
    DESCRIPTION
        "This table represents the information about the
        details of Spectrum Expert client connected to 
        radio interface of APs"
    ::= { ciscoLwappApMIBObjects 8 }

cLApSeClientEntry OBJECT-TYPE
    SYNTAX          CLApSeClientEntry
    MAX-ACCESS      not-accessible
    STATUS          current
    DESCRIPTION
        "An entry in this table represents the details of
        Spectrum Expert client connected to APs"
    INDEX           {
                        cLApSysMacAddress,
                        cLApDot11IfSlotId,
                        cLApSeIndex
                    } 
    ::= { cLApSeClientTable 1 }

CLApSeClientEntry ::= SEQUENCE {
        cLApSeIndex            Integer32,
        cLApSeClientUserName   SnmpAdminString,
        cLApSeClientIPAddrType InetAddressType,
        cLApSeClientIPAddr     InetAddress,
        cLApSeClientDuration   TimeInterval,
        cLApSeClientPort       InetPortNumber
}

cLApSeIndex OBJECT-TYPE
    SYNTAX          Integer32 (0..2)
    MAX-ACCESS      not-accessible
    STATUS          current
    DESCRIPTION
        "This object indicates the index of the client
        running the Spectrum Expert instance." 
    ::= { cLApSeClientEntry 1 }

cLApSeClientUserName OBJECT-TYPE
    SYNTAX          SnmpAdminString
    MAX-ACCESS      read-only
    STATUS          current
    DESCRIPTION
        "This object represents the name of the
        client running the Spectrum Expert application" 
    ::= { cLApSeClientEntry 2 }

cLApSeClientIPAddrType OBJECT-TYPE
    SYNTAX          InetAddressType
    MAX-ACCESS      read-only
    STATUS          current
    DESCRIPTION
        "This object represents the client IP address type,
        that runs the SE application, made available 
        through cLApSeClientIPAddr" 
    ::= { cLApSeClientEntry 3 }

cLApSeClientIPAddr OBJECT-TYPE
    SYNTAX          InetAddress
    MAX-ACCESS      read-only
    STATUS          current
    DESCRIPTION
        "This object represents the client IP address,
        that runs the SE application" 
    ::= { cLApSeClientEntry 4 }

cLApSeClientDuration OBJECT-TYPE
    SYNTAX          TimeInterval
    MAX-ACCESS      read-only
    STATUS          current
    DESCRIPTION
        "This object represents the duration for which the SE client
        application has been up and running" 
    ::= { cLApSeClientEntry 5 }

cLApSeClientPort OBJECT-TYPE
    SYNTAX          InetPortNumber
    MAX-ACCESS      read-only
    STATUS          current
    DESCRIPTION
        "This object represents the port from which the SE client
        application is running" 
    ::= { cLApSeClientEntry 6 }
 

-- ********************************************************************
-- Global settings for APs
-- ********************************************************************

cLApFastHbTimerTable OBJECT-TYPE
    SYNTAX          SEQUENCE OF CLApFastHbTimerEntry 
    MAX-ACCESS      not-accessible
    STATUS          current
    DESCRIPTION
        "This table contains entries for AP fast heartbeat
        timers configured in the controller. At startup,
        all the entries in this table are set up by the central
        controller.  A management application can later change
        the values in this table."
    ::= { ciscoLwappApGlobal 1 }

cLApFastHbTimerEntry OBJECT-TYPE
    SYNTAX          CLApFastHbTimerEntry
    MAX-ACCESS      not-accessible
    STATUS          current
    DESCRIPTION
        "A conceptual row in cLApFastHbTimerTable. There is an entry
        in this table for each AP type, as identified by a value of
        cLApFastHbTimerApType."
    INDEX           { cLApFastHbTimerApType } 
    ::= { cLApFastHbTimerTable 1 }

CLApFastHbTimerEntry ::= SEQUENCE {
        cLApFastHbTimerApType  INTEGER,
        cLApFastHbTimerTimeout Unsigned32,
        cLApFastHbTimerEnabled TruthValue
}

cLApFastHbTimerApType OBJECT-TYPE
    SYNTAX          INTEGER  {
                        local(1),
                        hreap(2)
                    }
    MAX-ACCESS      not-accessible
    STATUS          current
    DESCRIPTION
        "This object represents the AP type for this entry.
        local      - indicates that timer is for local mode APs
        hreap      - indicates that timer is for HREAP APs" 
    ::= { cLApFastHbTimerEntry 1 }

cLApFastHbTimerTimeout OBJECT-TYPE
    SYNTAX          Unsigned32 (1..15)
    UNITS           "seconds"
    MAX-ACCESS      read-write
    STATUS          current
    DESCRIPTION
        "This object specifies the timeout value for the heart
        beat timer. This value changes to 0 when
        cLApFastHbTimerEnabled is set to 'false'." 
    ::= { cLApFastHbTimerEntry 2 }

cLApFastHbTimerEnabled OBJECT-TYPE
    SYNTAX          TruthValue
    MAX-ACCESS      read-write
    STATUS          current
    DESCRIPTION
        "This object specifies the heartbeat timer. A value of 'true'
        indicates that this timer is enabled. A value of 'false'
        indicates that this timer is disabled." 
    ::= { cLApFastHbTimerEntry 3 }
 


cLApPrimaryDiscoveryTimeout OBJECT-TYPE
    SYNTAX          Unsigned32 (30..3600)
    UNITS           "seconds"
    MAX-ACCESS      read-write
    STATUS          current
    DESCRIPTION
        "This object specifies the timeout for the primary AP
        discovery."
    DEFVAL          { 120 } 
    ::= { ciscoLwappApGlobal 3 }

cLApGlobalPrimaryControllerAddressType OBJECT-TYPE
    SYNTAX          InetAddressType
    MAX-ACCESS      read-write
    STATUS          current
    DESCRIPTION
        "This object specifies the type of the primary controller's
        address made available through cLApPrimaryControllerAddress." 
    ::= { ciscoLwappApGlobal 4 }

cLApGlobalPrimaryControllerAddress OBJECT-TYPE
    SYNTAX          InetAddress
    MAX-ACCESS      read-write
    STATUS          current
    DESCRIPTION
        "This object specifies the address of the primary controller
        that the APs will join. The name and address should be 
        provided in the same set request. An address of all zeros 
        will unset the primary controller." 
    ::= { ciscoLwappApGlobal 5 }

cLApGlobalPrimaryControllerName OBJECT-TYPE
    SYNTAX          SnmpAdminString (SIZE  (0..32))
    MAX-ACCESS      read-write
    STATUS          current
    DESCRIPTION
        "This object specifies the name of the primary controller
        that the APs will join." 
    ::= { ciscoLwappApGlobal 6 }

cLApGlobalSecondaryControllerAddressType OBJECT-TYPE
    SYNTAX          InetAddressType
    MAX-ACCESS      read-write
    STATUS          current
    DESCRIPTION
        "This object specifies the type of the secondary
        controller's address made available through 
        cLApSecondaryControllerAddress." 
    ::= { ciscoLwappApGlobal 7 }

cLApGlobalSecondaryControllerAddress OBJECT-TYPE
    SYNTAX          InetAddress
    MAX-ACCESS      read-write
    STATUS          current
    DESCRIPTION
        "This object specifies the address of the secondary
        controller that the APs will join. The name and address 
        should be provided in the same set request. An address 
        of all zeros will unset the secondary controller." 
    ::= { ciscoLwappApGlobal 8 }

cLApGlobalSecondaryControllerName OBJECT-TYPE
    SYNTAX          SnmpAdminString (SIZE  (0..32))
    MAX-ACCESS      read-write
    STATUS          current
    DESCRIPTION
        "This object specifies the name of the secondary controller
        that the APs will join." 
    ::= { ciscoLwappApGlobal 9 }

cLApGlobalFailoverPriority OBJECT-TYPE
    SYNTAX          TruthValue
    MAX-ACCESS      read-write
    STATUS          current
    DESCRIPTION
        "This object specifies the global AP failover priority.
        If Enabled, Priorities will be considered of the APs which 
        wishes to join the controller. Preference will be given to 
        the higher priority AP. If the number of associated AP has 
        already reached the limit then the controller will 
        disassociate a lower priority AP to accomodate a higher 
        priority AP. 
               Default is Disabled state."
    DEFVAL          { false } 
    ::= { ciscoLwappApGlobal 10 }

cLApGlobalTcpMss OBJECT-TYPE
    SYNTAX          Integer32 (0 | 536..1363)
    MAX-ACCESS      read-write
    STATUS          current
    DESCRIPTION
        "This object specifies the Global AP TCP MSS value.
        Permissible value are between 536 and 1363. This will
        also enable the global TCP MSS flag.
        Value of 0 will disable the global TCP MSS flag.
        Any change of value for this object will be reflected
        to cLApTcpMss" 
    ::= { ciscoLwappApGlobal 11 }

cLApGlobalDot11IfTable OBJECT-TYPE
    SYNTAX          SEQUENCE OF CLApGlobalDot11IfEntry 
    MAX-ACCESS      not-accessible
    STATUS          current
    DESCRIPTION
        "This table is used to configure the global dot11
        parameters per slot id, represented by cLApDot11IfSlotId, 
        of the radio interface in all the APs joined with 
        the controller."
    ::= { ciscoLwappApGlobal 12 }

cLApGlobalDot11IfEntry OBJECT-TYPE
    SYNTAX          CLApGlobalDot11IfEntry
    MAX-ACCESS      not-accessible
    STATUS          current
    DESCRIPTION
        "This represents an entry in the
        cLApGlobalDot11IfTable."
    INDEX           { cLApDot11IfSlotId } 
    ::= { cLApGlobalDot11IfTable 1 }

CLApGlobalDot11IfEntry ::= SEQUENCE {
        cLApGlobalDot11IfCdpEnabled TruthValue
}

cLApGlobalDot11IfCdpEnabled OBJECT-TYPE
    SYNTAX          TruthValue
    MAX-ACCESS      read-write
    STATUS          current
    DESCRIPTION
        "This object specifies to configure the Cisco Discovery
        Protocol(CDP) in the interface, represented by
        cLApDot11IfSlotId of the all the APs, joined in the 
        controller.

        Setting this object to a value of 'true' would turn on 
        the CDP on this slot.

        Setting this object to a value of 'false' would turn off the
        CDP on this slot, so that CDP advertisements are not sent.

        Read operation on this attribute will not be supported. 
        When queried this will return a value of 'false'." 
    ::= { cLApGlobalDot11IfEntry 1 }
 


cLApGlobalEthernetIfTable OBJECT-TYPE
    SYNTAX          SEQUENCE OF CLApGlobalEthernetIfEntry 
    MAX-ACCESS      not-accessible
    STATUS          current
    DESCRIPTION
        "This table is used to configure the global parameters
        on Ethernet interfaces of all the APs joined with the 
        controller."
    ::= { ciscoLwappApGlobal 13 }

cLApGlobalEthernetIfEntry OBJECT-TYPE
    SYNTAX          CLApGlobalEthernetIfEntry
    MAX-ACCESS      not-accessible
    STATUS          current
    DESCRIPTION
        "This represents an entry in
        cLApGlobalEthernetIfTable."
    INDEX           { cLApEthernetIfSlotId } 
    ::= { cLApGlobalEthernetIfTable 1 }

CLApGlobalEthernetIfEntry ::= SEQUENCE {
        cLApGlobalEthernetIfCdpEnabled TruthValue
}

cLApGlobalEthernetIfCdpEnabled OBJECT-TYPE
    SYNTAX          TruthValue
    MAX-ACCESS      read-write
    STATUS          current
    DESCRIPTION
        "This object is specifies to configure the Cisco Discovery
        Protocol(CDP) in the interface, represented by
        cLApEthernetIfSlotId of the all the APs, joined in 
        the controller.

        Setting this object to a value of 'true' would turn on 
        the CDP on this ethernet interface.

        Setting this object to a value of 'false' would turn off the
        CDP on this ethernet interface, so that CDP advertisements
        are not sent.

        Read operation on this attribute will not be supported. 
        When queried this will return a value of 'false'." 
    ::= { cLApGlobalEthernetIfEntry 1 }
 


cLApGlobalRetransmitCount OBJECT-TYPE
    SYNTAX          Unsigned32
    UNITS           "retries"
    MAX-ACCESS      read-write
    STATUS          current
    DESCRIPTION
        "This object specifies the retransmission count for the
        Control Packet of all the Access Points, joined to this 
        controller. This value specifies the number of packets 
        retransmitted after which the Access Point falls back to 
        another controller in case of failover." 
    ::= { ciscoLwappApGlobal 14 }

cLApGlobalRetransmitTimeout OBJECT-TYPE
    SYNTAX          Unsigned32
    UNITS           "seconds"
    MAX-ACCESS      read-write
    STATUS          current
    DESCRIPTION
        "This object specifies the retransmission timeout for the
        Control Packet of all the Access Points, joined to this 
        controller. This value specifies the timeout for each 
        retransmission, during the fallback of Access Point to 
        another controller in case of failover." 
    ::= { ciscoLwappApGlobal 15 }

cLApOeapDisableLocalAccess OBJECT-TYPE
    SYNTAX          TruthValue
    MAX-ACCESS      read-write
    STATUS          current
    DESCRIPTION
        "This object specifies whether the local access is supported for
        all the Office Extended Access Points, joined to this 
        controller. If set to true, the local SSID and and LAN ports 
        on the OEAP will be disabled." 
    ::= { ciscoLwappApGlobal 16 }

cLApGlobalLEDState OBJECT-TYPE
    SYNTAX          TruthValue
    MAX-ACCESS      read-write
    STATUS          current
    DESCRIPTION
        "This object specifies whether the LED state of all the access
        points should be enabled or disabled." 
    ::= { ciscoLwappApGlobal 17 }

cLApRadioInterfaceShutdownEnabled OBJECT-TYPE
    SYNTAX          TruthValue
    MAX-ACCESS      read-write
    STATUS          current
    DESCRIPTION
        "This object specifies to enable or disable AP radio Interface.
        When enabled, AP radio's will be shut down when Ethernet link 
        goes down for a duration of time set for 
        cLApEthernetInterfaceDowntime. A value of 'true' indicates the 
        AP radio interface shutdown is enabled. A value of 'false' 
        indicates the AP radio interface shutdown is disabled." 
    ::= { ciscoLwappApGlobal 18 }

cLApEthernetInterfaceDowntime OBJECT-TYPE
    SYNTAX          Unsigned32
    UNITS           "Seconds"
    MAX-ACCESS      read-write
    STATUS          current
    DESCRIPTION
        "This object specifies the ethernet interface down time after
        which the AP radio interface will be shut down." 
    ::= { ciscoLwappApGlobal 19 }

cLAPMulticastGroupAddressType OBJECT-TYPE
    SYNTAX          InetAddressType
    MAX-ACCESS      read-write
    STATUS          current
    DESCRIPTION
        "This object specifies the AP multicast group address type." 
    ::= { ciscoLwappApGlobal 20 }

cLAPMulticastGroupAddress OBJECT-TYPE
    SYNTAX          InetAddress
    MAX-ACCESS      read-write
    STATUS          current
    DESCRIPTION
        "This object specifies the AP multicast group address." 
    ::= { ciscoLwappApGlobal 21 }

cLAPMulticastMode OBJECT-TYPE
    SYNTAX          INTEGER  {
                        unicast(1),
                        multicast(2)
                    }
    MAX-ACCESS      read-write
    STATUS          current
    DESCRIPTION
        "This object specifies the switch's ethernet
        multicast support.
        unicast - Controller will convert multicast to
                  unicast packet.
        multicast - Multicast mode is enabled." 
    ::= { ciscoLwappApGlobal 22 }

cLApPrimedDiscoveryTimeout OBJECT-TYPE
    SYNTAX          Integer32 (0 | 120..43200)
    UNITS           "seconds"
    MAX-ACCESS      read-write
    STATUS          current
    DESCRIPTION
        "This object specifies the primed timeout for the AP
        discovery." 
    ::= { ciscoLwappApGlobal 23 }

cLApGlobalPreferMode OBJECT-TYPE
    SYNTAX          INTEGER  {
                        ipv4(1),
                        ipv6(2)
                    }
    MAX-ACCESS      read-write
    STATUS          current
    DESCRIPTION
        "This object specifies the global capwap prefer-mode.
        ipv4 - capwap tunnel established with ipv4 address.
        ipv6 - capwap tunnel established with ipv6 address." 
    ::= { ciscoLwappApGlobal 24 }

cLApGlobalAPLagCapability OBJECT-TYPE
    SYNTAX          TruthValue
    MAX-ACCESS      read-write
    STATUS          current
    DESCRIPTION
        "This object specifies whether the ap-lag capability state of
        all the access points should be enabled or disabled.
        A value of 'true' indicates ap-lag capapbility is enabled.
        A value of 'false' indicates ap-lag capapbility is disabled." 
    ::= { ciscoLwappApGlobal 25 }

cLApGlobalAPDtlsVersion OBJECT-TYPE
    SYNTAX          INTEGER  {
                        dtls10(1),
                        dtls12(2),
                        dtlsall(3)
                    }
    MAX-ACCESS      read-write
    STATUS          current
    DESCRIPTION
        "This object specifies the dtls version of ap" 
    ::= { ciscoLwappApGlobal 26 }

cLApGlobalAPDtlsCipherSuite OBJECT-TYPE
    SYNTAX          INTEGER  {
                        rsaaes128sha1(47),
                        dhersaaes128cbcsha(51),
                        rsaaes256sha1(53),
                        dhersaaes256cbcsha(57),
                        rsaaes256sha256(61),
                        rsagcm128sha256(156),
                        rsagcm256sha384(157),
                        ecdsaaes128gcmsha256(49195),
                        ecdsaaes256gcmsha384(49196),
                        dhersaaes256cbcsha256(49197)
                    }
    MAX-ACCESS      read-write
    STATUS          current
    DESCRIPTION
        "This object specifies the dtls cipher suite of ap" 
    ::= { ciscoLwappApGlobal 27 }

cLApGlobalMaxApsSupported OBJECT-TYPE
    SYNTAX          Integer32
    MAX-ACCESS      read-only
    STATUS          current
    DESCRIPTION
        "This object represents the maximum number of APs supported by
        this controller." 
    ::= { ciscoLwappApGlobal 28 }

cLApAuthorizeApMacAuth OBJECT-TYPE
    SYNTAX          TruthValue
    MAX-ACCESS      read-write
    STATUS          current
    DESCRIPTION
        "This flag specifies the status of mac auth"
    ::= { ciscoLwappApGlobal 30 }

cLApAuthorizeApSerialNumAuth OBJECT-TYPE
    SYNTAX          TruthValue
    MAX-ACCESS      read-write
    STATUS          current
    DESCRIPTION
        "This flag specifies the status of serial number auth"
    ::= { ciscoLwappApGlobal 31 }

cLApAuthorizeApMethodList OBJECT-TYPE
    SYNTAX          SnmpAdminString
    MAX-ACCESS      read-write
    STATUS          current
    DESCRIPTION
        "This object specifies the method list used for the AP 
        authorization when enabled.
        The default method list is default"
    ::= { ciscoLwappApGlobal 32 }

cLApGlobalAPAuditReport OBJECT-TYPE
    SYNTAX          TruthValue
    MAX-ACCESS      read-write
    STATUS          current
    DESCRIPTION
        "This object is used to enable/disable AP audit reporting.
        It is disabled by default"
    ::= { ciscoLwappApGlobal 33 }

cLApGlobalAPAuditReportInterval  OBJECT-TYPE
    SYNTAX          Unsigned32 (10..43200)
    UNITS           "Minutes"
    MAX-ACCESS      read-write
    STATUS          current
    DESCRIPTION
        "This object specifies the audit report interval in minutes.
        The default interval is 1440 minutes"
    ::= { ciscoLwappApGlobal 34 }

cLApGlobalAPConnectCount OBJECT-TYPE
    SYNTAX          Unsigned32
    MAX-ACCESS      read-only
    STATUS          current
    DESCRIPTION
        "This object represents the Count of AP's that are connected
        to the Controller." 
    ::= { ciscoLwappApGlobal 35 }

cLApAuthorizeApMacMethodList OBJECT-TYPE
    SYNTAX          SnmpAdminString
    MAX-ACCESS      read-write
    STATUS          current
    DESCRIPTION
        "This object specifies the method list used for the AP
         MAC authorization when enabled."
    ::= { ciscoLwappApGlobal 36 }

cLApAuthorizeApSerialNumMethodList OBJECT-TYPE
    SYNTAX          SnmpAdminString
    MAX-ACCESS      read-write
    STATUS          current
    DESCRIPTION
        "This object specifies the method list used for the AP
        serial number authorization when enabled."
    ::= { ciscoLwappApGlobal 37 }

clApImageUpgradeConfig OBJECT IDENTIFIER
    ::= { ciscoLwappApGlobal 38 } 

clApImageUpgradeHttpsEnable OBJECT-TYPE
    SYNTAX         TruthValue
    MAX-ACCESS     read-write
    STATUS         current
    DESCRIPTION
        "This object specifies the state of AP Image Upgrade method HTTPS 
         on the controller. 
         A value of 'true'  indicates that the AP Image Upgrade method 
         HTTPS is enabled. 
         A value of 'false' indicates that the AP Image Upgrade method 
         HTTPS is disabled."
    DEFVAL          { FALSE }
    ::= { clApImageUpgradeConfig 1 }

-- ********************************************************************
-- *  AP Dot11 Interface Antenna Information
-- ********************************************************************

cLApDot11IfAntennaTable OBJECT-TYPE
    SYNTAX          SEQUENCE OF CLApDot11IfAntennaEntry 
    MAX-ACCESS      not-accessible
    STATUS          current
    DESCRIPTION
        "This table represents the information about the
        basic functional parameters corresponding to
        the antenna on dot11 interfaces of the APs that have 
        joined the controller."
    ::= { ciscoLwappApIf 4 }

cLApDot11IfAntennaEntry OBJECT-TYPE
    SYNTAX          CLApDot11IfAntennaEntry
    MAX-ACCESS      not-accessible
    STATUS          current
    DESCRIPTION
        "An entry in this table represents the 802.11
        functional parameters of the dot11 interface of
        an AP that has joined the controller.

        Entries are added when the APs associate to this
        controller and deleted when they lose their
        association."
    INDEX           {
                        cLApSysMacAddress,
                        cLApDot11IfSlotId,
                        cLApDot11IfAntennaId
                    } 
    ::= { cLApDot11IfAntennaTable 1 }

CLApDot11IfAntennaEntry ::= SEQUENCE {
        cLApDot11IfAntennaId       Unsigned32,
        cLApDot11IfAntennaTxEnable TruthValue,
        cLApDot11IfAntennaRxEnable TruthValue,
        cLApDot11IfAntennaEnable   TruthValue
}

cLApDot11IfAntennaId OBJECT-TYPE
    SYNTAX          Unsigned32 (1..8)
    MAX-ACCESS      not-accessible
    STATUS          current
    DESCRIPTION
        "This object represents the antenna ID of a dot11
        interface on an AP. 
        The antenna Id for a particular dot11 interface on 
        a slot as represented by this object." 
    ::= { cLApDot11IfAntennaEntry 1 }

cLApDot11IfAntennaTxEnable OBJECT-TYPE
    SYNTAX          TruthValue
    MAX-ACCESS      read-write
    STATUS          current
    DESCRIPTION
        "This object specifies whether this antenna is allowed
        to trasmit or not.
        A value of 'true' enables the antenna to transmit.
        A value of 'false' disables the antenna to transmit.
        This object has been deprecated for cLApDot11IfAntennaEnable.
        cLApDot11IfAntennaTxEnable object is superseded by 
        cLApDot11IfAntennaEnable."
    DEFVAL          { true } 
    ::= { cLApDot11IfAntennaEntry 2 }

cLApDot11IfAntennaRxEnable OBJECT-TYPE
    SYNTAX          TruthValue
    MAX-ACCESS      read-write
    STATUS          current
    DESCRIPTION
        "This object specifies whether this antenna is allowed
        to recieve or not.
        A value of 'true' enables the antenna to receive.
        A value of 'false' disables the antenna to receive.
        cLApDot11IfAntennaRxEnable object is superseded by 
        cLApDot11IfAntennaEnable."
    DEFVAL          { true } 
    ::= { cLApDot11IfAntennaEntry 3 }

cLApDot11IfAntennaEnable OBJECT-TYPE
    SYNTAX          TruthValue
    MAX-ACCESS      read-write
    STATUS          current
    DESCRIPTION
        "This object specifies whether this antenna is enabled
        or not.
        A value of 'true' indicates antenna is enabled.
        A value of 'false' indicates antenna is disabled."
    DEFVAL          { true } 
    ::= { cLApDot11IfAntennaEntry 4 }
 

-- ********************************************************************
-- *  AP Vlan Tagging
-- ********************************************************************

cLApVlanIfTable OBJECT-TYPE
    SYNTAX          SEQUENCE OF CLApVlanIfEntry 
    MAX-ACCESS      not-accessible
    STATUS          current
    DESCRIPTION
        "This table represents the information about the
        basic functional parameters corresponding to
        the ethernet interfaces of the APs that have
        joined the controller."
    ::= { ciscoLwappApIf 5 }

cLApVlanIfEntry OBJECT-TYPE
    SYNTAX          CLApVlanIfEntry
    MAX-ACCESS      not-accessible
    STATUS          current
    DESCRIPTION
        "An entry in this table represents the VLAN
        functional parameters of the Ethernet interface of
        an AP that has joined the controller.
        Entries are added when the administrator creates
        an entry in this table."
    INDEX           {
                        cLApSysMacAddress,
                        cLApVlanIfEthernetId
                    } 
    ::= { cLApVlanIfTable 1 }

CLApVlanIfEntry ::= SEQUENCE {
        cLApVlanIfEthernetId   Unsigned32,
        cLApVlanIfMode         INTEGER,
        cLApVlanIfEnable       TruthValue,
        cLApVlanIfNativeVlanId Unsigned32
}

cLApVlanIfEthernetId OBJECT-TYPE
    SYNTAX          Unsigned32 (0..3)
    MAX-ACCESS      not-accessible
    STATUS          current
    DESCRIPTION
        "This object represents the ID of a ethernet
        interface on an AP." 
    ::= { cLApVlanIfEntry 1 }

cLApVlanIfMode OBJECT-TYPE
    SYNTAX          INTEGER  {
                        normal(1),
                        access(2),
                        trunk(3)
                    }
    MAX-ACCESS      read-write
    STATUS          current
    DESCRIPTION
        "This object specifies the AP's ethernet interface is
        configured for.
            normal - VLAN is not operating in access or trunk.
            access - VLAN is operating in access mode
            trunk  - VLAN is operating in trunk mode."
    DEFVAL          { normal } 
    ::= { cLApVlanIfEntry 2 }

cLApVlanIfEnable OBJECT-TYPE
    SYNTAX          TruthValue
    MAX-ACCESS      read-write
    STATUS          current
    DESCRIPTION
        "This object specifies whether this interface  is
        enabled or not.
        A value of 'true' enables the interface.
        A value of 'false' disables the interface.. This will
        delete all entries on this AP's ethernet interface."
    DEFVAL          { true } 
    ::= { cLApVlanIfEntry 3 }

cLApVlanIfNativeVlanId OBJECT-TYPE
    SYNTAX          Unsigned32
    MAX-ACCESS      read-write
    STATUS          current
    DESCRIPTION
        "This object specifies the native VLAN ID
        assigned to this AP's ethernet interface.
        This only applies when the icLApVlanIfMode
        is set to 'trunk'. For all other modes this
        return a value of zero." 
    ::= { cLApVlanIfEntry 4 }
 

-- ********************************************************************
-- *  AP Vlan Tagging
-- ********************************************************************

cLApVlanListTable OBJECT-TYPE
    SYNTAX          SEQUENCE OF CLApVlanListEntry 
    MAX-ACCESS      not-accessible
    STATUS          current
    DESCRIPTION
        "This table represents the information about the
        basic functional parameters corresponding to
        the VLAN Ethernet interfaces of the APs that have 
        joined the controller."
    ::= { ciscoLwappApIf 6 }

cLApVlanListEntry OBJECT-TYPE
    SYNTAX          CLApVlanListEntry
    MAX-ACCESS      not-accessible
    STATUS          current
    DESCRIPTION
        "An entry in this table represents the VLAN
        functional parameters of the Ethernet interface of
        an AP that has joined the controller.
        Entries are added when the administrator creates 
        an entry in this table."
    INDEX           {
                        cLApSysMacAddress,
                        cLApVlanIfEthernetId,
                        cLApVlanListVlanId
                    } 
    ::= { cLApVlanListTable 1 }

CLApVlanListEntry ::= SEQUENCE {
        cLApVlanListVlanId    Unsigned32,
        cLApVlanListRowStatus RowStatus
}

cLApVlanListVlanId OBJECT-TYPE
    SYNTAX          Unsigned32
    MAX-ACCESS      not-accessible
    STATUS          current
    DESCRIPTION
        "This object represents the ID assigned to the
        VLAN on this AP's ethernet interface." 
    ::= { cLApVlanListEntry 1 }

cLApVlanListRowStatus OBJECT-TYPE
    SYNTAX          RowStatus
    MAX-ACCESS      read-create
    STATUS          current
    DESCRIPTION
        "This object specifies to add or delete an entry in this
        table." 
    ::= { cLApVlanListEntry 2 }
 


-- ********************************************************************
-- *  Global AP 802.1x Supplicant Credentials
-- ********************************************************************

cLApGlobal802dot1xAuthenticationEnabled OBJECT-TYPE
    SYNTAX          TruthValue
    MAX-ACCESS      read-write
    STATUS          current
    DESCRIPTION
        "This object specifies the Global AP 802.1x Supplicant
        Authentication feature.
        If configured as True, user can configure 8021.1x 
        authentication between lightweight access points and the 
        switch. The access point acts as an 802.1x supplicant and is 
        authenticated by the switch using EAP-FAST with anonymous 
        PAC provisioning.User can set global authentication settings 
        that all access points inherit as they join the controller. 
        This includes all access points that are currently joined to 
        the controller and any that join in the future. If desired, 
        user can override the global authentication settings and 
        assign unique authentication settings for a specific 
           access point.
           Default state is False."
    DEFVAL          { false } 
    ::= { ciscoLwappAp802dot1xSupplicant 1 }

cLApGlobal802dot1xSupplicantUsername OBJECT-TYPE
    SYNTAX          SnmpAdminString
    MAX-ACCESS      read-write
    STATUS          current
    DESCRIPTION
        "This object specifies the 802.1x supplicant username that
        is to be inherited by all access points that join the 
        controller." 
    ::= { ciscoLwappAp802dot1xSupplicant 2 }

cLApGlobal802dot1xSupplicantPassword OBJECT-TYPE
    SYNTAX          SnmpAdminString
    MAX-ACCESS      read-write
    STATUS          current
    DESCRIPTION
        "This object specifies the 802.1x supplicant Password that
        is to be inherited by all access points that join the 
        controller. 
        A query on this OID will always return '****'." 
    ::= { ciscoLwappAp802dot1xSupplicant 3 }

cLApGlobal802dot1xSupplicantEapType OBJECT-TYPE
    SYNTAX          INTEGER  {
                        none(1),
                        eapFast(2),
                        eapTls(3),
                        peap(4)
                    }
    MAX-ACCESS      read-write
    STATUS          current
    DESCRIPTION
        "This object specifies the EAP type to be
        applied for ap port auth as Global config." 
    ::= { ciscoLwappAp802dot1xSupplicant 5 }
-- ********************************************************************
-- * Per AP 802.1x Supplicant Credentials
-- ********************************************************************

cLAp802dot1xSupplicantTable OBJECT-TYPE
    SYNTAX          SEQUENCE OF CLAp802dot1xSupplicantEntry 
    MAX-ACCESS      not-accessible
    STATUS          current
    DESCRIPTION
        "This table provides the information about the 802.1x
        Supplicant credentials of the 802.11 LWAPP Access Points 
        that have joined the controller. Rows are added to this 
        table whenever, new APs are joined to this controller, 
        and rows are deleted whenever APs gets disjoined from 
        the controller."
    ::= { ciscoLwappAp802dot1xSupplicant 4 }

cLAp802dot1xSupplicantEntry OBJECT-TYPE
    SYNTAX          CLAp802dot1xSupplicantEntry
    MAX-ACCESS      not-accessible
    STATUS          current
    DESCRIPTION
        "Each entry in this table provides information about
        one 802.11 LWAPP Access Point that has joined the
        controller. cLApSysMacAddress is the index which
        uniquely identifies every row in the table."
    INDEX           { cLApSysMacAddress } 
    ::= { cLAp802dot1xSupplicantTable 1 }

CLAp802dot1xSupplicantEntry ::= SEQUENCE {
        cLAp802dot1xSupplicantOverrideEnabled  TruthValue,
        cLAp802dot1xSupplicantOverrideUsername SnmpAdminString,
        cLAp802dot1xSupplicantOverridePassword SnmpAdminString,
        cLAp802dot1xSupplicantOverrideEapType  INTEGER
}

cLAp802dot1xSupplicantOverrideEnabled OBJECT-TYPE
    SYNTAX          TruthValue
    MAX-ACCESS      read-write
    STATUS          current
    DESCRIPTION
        "This object specifies the individual AP level 802.1x
        Supplicant Authentication override parameters.
        A value of 'true' indicates user can override the Global AP 
        8021.1x authentication credentials by providing individual 
        AP level credentials.
        A value of 'false' indicates user cannot override the 
        Global AP 802.1x authentication credentials."
    DEFVAL          { false } 
    ::= { cLAp802dot1xSupplicantEntry 1 }

cLAp802dot1xSupplicantOverrideUsername OBJECT-TYPE
    SYNTAX          SnmpAdminString
    MAX-ACCESS      read-write
    STATUS          current
    DESCRIPTION
        "This object specifies the individual AP level 802.1x
        supplicant override username." 
    ::= { cLAp802dot1xSupplicantEntry 2 }

cLAp802dot1xSupplicantOverridePassword OBJECT-TYPE
    SYNTAX          SnmpAdminString
    MAX-ACCESS      read-write
    STATUS          current
    DESCRIPTION
        "This object the individual AP level 802.1x supplicant
        override password. A query on this OID will always 
        return '****'." 
    ::= { cLAp802dot1xSupplicantEntry 3 }

cLAp802dot1xSupplicantOverrideEapType OBJECT-TYPE
    SYNTAX          INTEGER  {
                        none(1),
                        eapFast(2),
                        eapTls(3),
                        peap(4)
                    }
    MAX-ACCESS      read-write
    STATUS          current
    DESCRIPTION
        "This object specifies the EAP type to be
        applied for ap port auth as AP override config." 
    ::= { cLAp802dot1xSupplicantEntry 4 }
 

-- ********************************************************************
-- *  AP WLAN Stats.
-- ********************************************************************

cLApWlanInfoTable OBJECT-TYPE
    SYNTAX          SEQUENCE OF CLApWlanInfoEntry 
    MAX-ACCESS      not-accessible
    STATUS          current
    DESCRIPTION
        "This table represents Per-AP, Per-SSID
        information of max supported clients"
    ::= { ciscoLwappApWlanInfo 1 }

cLApWlanInfoEntry OBJECT-TYPE
    SYNTAX          CLApWlanInfoEntry
    MAX-ACCESS      not-accessible
    STATUS          current
    DESCRIPTION
        "Each entry in this table represents the information about
        clients associated to a wlan broadcasted by an access point."
    INDEX           {
                        cLApSysMacAddress,
                        cLWlanIndex
                    } 
    ::= { cLApWlanInfoTable 1 }

CLApWlanInfoEntry ::= SEQUENCE {
        cLApWlanInfoMaxClients Unsigned32
}

cLApWlanInfoMaxClients OBJECT-TYPE
    SYNTAX          Unsigned32 (1..600)
    MAX-ACCESS      read-write
    STATUS          current
    DESCRIPTION
        "This object specifies the maximum supported clients
        per WLAN ."
    DEFVAL          { 600 } 
    ::= { cLApWlanInfoEntry 1 }
 


cLApRadioWlanInfoTable OBJECT-TYPE
    SYNTAX          SEQUENCE OF CLApRadioWlanInfoEntry 
    MAX-ACCESS      not-accessible
    STATUS          current
    DESCRIPTION
        "This table represents Per-AP, Per-radio,
        Per-SSID information."
    ::= { ciscoLwappApWlanInfo 2 }

cLApRadioWlanInfoEntry OBJECT-TYPE
    SYNTAX          CLApRadioWlanInfoEntry
    MAX-ACCESS      not-accessible
    STATUS          current
    DESCRIPTION
        "This entry contains information of
        Per-AP, Per-RADIO, Per-SSID information."
    INDEX           {
                        cLApSysMacAddress,
                        cLApDot11IfSlotId,
                        cLWlanIndex
                    } 
    ::= { cLApRadioWlanInfoTable 1 }

CLApRadioWlanInfoEntry ::= SEQUENCE {
        cLApRadioWlanSsid  SnmpAdminString,
        cLApRadioWlanBssid MacAddress
}

cLApRadioWlanSsid OBJECT-TYPE
    SYNTAX          SnmpAdminString
    MAX-ACCESS      read-only
    STATUS          current
    DESCRIPTION
        "This object represents SSID of the particular WLAN,
        which is seen on the radio of the AP." 
    ::= { cLApRadioWlanInfoEntry 1 }

cLApRadioWlanBssid OBJECT-TYPE
    SYNTAX          MacAddress
    MAX-ACCESS      read-only
    STATUS          current
    DESCRIPTION
        "This object represents the BSSID of the SSID
        on this radio of this AP." 
    ::= { cLApRadioWlanInfoEntry 2 }
 

-- ********************************************************************
-- *   Radio Level Configs
-- ********************************************************************

cLApDot11GlobalConfigTable OBJECT-TYPE
    SYNTAX          SEQUENCE OF CLApDot11GlobalConfigEntry 
    MAX-ACCESS      not-accessible
    STATUS          current
    DESCRIPTION
        "This table represents the information about the
        global attributes of the radio interface, that would be
        applicable for all the APs that join the controller."
    ::= { ciscoLwappApIf 7 }

cLApDot11GlobalConfigEntry OBJECT-TYPE
    SYNTAX          CLApDot11GlobalConfigEntry
    MAX-ACCESS      not-accessible
    STATUS          current
    DESCRIPTION
        "An entry in this table represents the network
        level configurations of the radio interface.
        Entries cannot be added or deleted in this table."
    INDEX           { cLApDot11IfType } 
    ::= { cLApDot11GlobalConfigTable 1 }

CLApDot11GlobalConfigEntry ::= SEQUENCE {
        cLApNwLegacyBeamForming    INTEGER,
        cLApNwTxPowerThreshold     Integer32,
        cLApNwTxPowerThresholdVer2 Integer32
}

cLApNwLegacyBeamForming OBJECT-TYPE
    SYNTAX          INTEGER  {
                        enable(1),
                        disable(2),
                        notApplicable(3)
                    }
    MAX-ACCESS      read-write
    STATUS          deprecated
    DESCRIPTION
        "This object indicates the status of legacy beam forming
        in this AP. This object is applicable only for
        11n supported APs.
        For APs that does not support legacy beam forming,
        a get request on this attribute will return
        the value 'notApplicable'.
        A value of 'enable' indicates that the legacy
        Beam forming is enabled in this AP.
        A value of 'false' indicates that the legacy
        Beam forming is disabled in this AP."
    DEFVAL          { notApplicable } 
    ::= { cLApDot11GlobalConfigEntry 1 }

cLApNwTxPowerThreshold OBJECT-TYPE
    SYNTAX          Integer32 (-80..-50)
    UNITS           "dbm"
    MAX-ACCESS      read-write
    STATUS          current
    DESCRIPTION
        "This object specifies the Global AP Transmit Power
        Threshold value. The permissible range is -80 dbm to -50 dbm"
    DEFVAL          { -70 } 
    ::= { cLApDot11GlobalConfigEntry 2 }

cLApNwTxPowerThresholdVer2 OBJECT-TYPE
    SYNTAX          Integer32 (-80..-50)
    UNITS           "dbm"
    MAX-ACCESS      read-write
    STATUS          current
    DESCRIPTION
        "This object specifies the Global AP Transmit Power
        Threshold value when Inteference Optimal mode of 
        Tx Power Control (TPC v2) is enabled. The permissible 
        range is -80 dbm to -50 dbm"
    DEFVAL          { -67 } 
    ::= { cLApDot11GlobalConfigEntry 3 }
 


-- ********************************************************************
-- * Ap Global Cipher Configurations
-- ********************************************************************

cLApSecureCipher OBJECT-TYPE
    SYNTAX          INTEGER  {
                        disable(1),
                        aes256sha1(2),
                        aes256sha2(3)
                    }
    MAX-ACCESS      read-write
    STATUS          current
    DESCRIPTION
        "This object specifies the secure ciphers, AES256+SHA
        or AES256+SHA2 for CAPWAP control tunnel.
        disable    - This value indicates that AP and controller will 
                     continue to use default ciphers for CAPWAP 
                     tunnel.
        aes256sha1 - This value indicates that AP and controller will 
                     use AES256+SHA cipher for CAPWAP tunnel.
        aes256sha2 - This value indicates that AP and controller will 
                     use AES256+SHA2 cipher for CAPWAP tunnel." 
    ::= { ciscoLwappApSecureCipher 1 }
-- ********************************************************************
-- *  AP Dot11 radio statistics Information
-- ********************************************************************

cLApDot11RadioStatsTable OBJECT-TYPE
    SYNTAX          SEQUENCE OF CLApDot11RadioStatsEntry 
    MAX-ACCESS      not-accessible
    STATUS          current
    DESCRIPTION
        "This table represents the statistics information
        about the radios of the APs that have joined the
        controller."
    ::= { ciscoLwappApIf 8 }

cLApDot11RadioStatsEntry OBJECT-TYPE
    SYNTAX          CLApDot11RadioStatsEntry
    MAX-ACCESS      not-accessible
    STATUS          current
    DESCRIPTION
        "An entry in this table represents a statistics of
        the radio of an AP that has joined the conttroller.

        Entries are added when the APs associate to this 
        controller and deleted when they lose their 
        association."
    INDEX           {
                        cLApSysMacAddress,
                        cLApDot11IfSlotId
                    } 
    ::= { cLApDot11RadioStatsTable 1 }

CLApDot11RadioStatsEntry ::= SEQUENCE {
        cLApDot11RadioStatsRxErrorFrameCount       Counter32,
        cLApDot11RadioStatsMacMicErrFrameCount     Counter32,
        cLApDot11RadioStatsMacDecryptErrFrameCount Counter32,
        cLApDot11RadioStatsRxMgmtFrameCount        Counter32,
        cLApDot11RadioStatsRxCtrlFrameCount        Counter32,
        cLApDot11RadioStatsRxDataFrameCount        Counter32,
        cLApDot11RadioStatsTxMgmtFrameCount        Counter32,
        cLApDot11RadioStatsTxCtrlFrameCount        Counter32,
        cLApDot11RadioStatsTxDataFrameCount        Counter32,
        cLApDot11RadioStatsRxDataPacketCount       Counter32,
        cLApDot11RadioStatsTxDataPacketCount       Counter32,
        cLApDot11RadioStatsRetryFrameCount         Counter32,
        cLApDot11RadioStatsRetryPacketCount        Counter32
}

cLApDot11RadioStatsRxErrorFrameCount OBJECT-TYPE
    SYNTAX          Counter32
    UNITS           "frames"
    MAX-ACCESS      read-only
    STATUS          current
    DESCRIPTION
        "This object represents the number of error frames
        received on the radio." 
    ::= { cLApDot11RadioStatsEntry 1 }

cLApDot11RadioStatsMacMicErrFrameCount OBJECT-TYPE
    SYNTAX          Counter32
    UNITS           "frames"
    MAX-ACCESS      read-only
    STATUS          current
    DESCRIPTION
        "This object represents the number of frames
        with wrong MIC received by AP on the radio." 
    ::= { cLApDot11RadioStatsEntry 2 }

cLApDot11RadioStatsMacDecryptErrFrameCount OBJECT-TYPE
    SYNTAX          Counter32
    UNITS           "frames"
    MAX-ACCESS      read-only
    STATUS          current
    DESCRIPTION
        "This object represents the number of frames
        with destroyed encrypted data received by AP
        on the radio." 
    ::= { cLApDot11RadioStatsEntry 3 }

cLApDot11RadioStatsRxMgmtFrameCount OBJECT-TYPE
    SYNTAX          Counter32
    UNITS           "frames"
    MAX-ACCESS      read-only
    STATUS          current
    DESCRIPTION
        "This object represents the total number of
        management frame received on the radio." 
    ::= { cLApDot11RadioStatsEntry 4 }

cLApDot11RadioStatsRxCtrlFrameCount OBJECT-TYPE
    SYNTAX          Counter32
    UNITS           "frames"
    MAX-ACCESS      read-only
    STATUS          current
    DESCRIPTION
        "This object represents the total number of
        control frame received on the radio." 
    ::= { cLApDot11RadioStatsEntry 5 }

cLApDot11RadioStatsRxDataFrameCount OBJECT-TYPE
    SYNTAX          Counter32
    UNITS           "frames"
    MAX-ACCESS      read-only
    STATUS          current
    DESCRIPTION
        "This object represents the total number of
        data frame received on the radio." 
    ::= { cLApDot11RadioStatsEntry 6 }

cLApDot11RadioStatsTxMgmtFrameCount OBJECT-TYPE
    SYNTAX          Counter32
    UNITS           "frames"
    MAX-ACCESS      read-only
    STATUS          current
    DESCRIPTION
        "This object represents the total number of
        management frame transmitted on the radio." 
    ::= { cLApDot11RadioStatsEntry 7 }

cLApDot11RadioStatsTxCtrlFrameCount OBJECT-TYPE
    SYNTAX          Counter32
    UNITS           "frames"
    MAX-ACCESS      read-only
    STATUS          current
    DESCRIPTION
        "This object represents the total number of
        control frame transmitted on the radio." 
    ::= { cLApDot11RadioStatsEntry 8 }

cLApDot11RadioStatsTxDataFrameCount OBJECT-TYPE
    SYNTAX          Counter32
    UNITS           "frames"
    MAX-ACCESS      read-only
    STATUS          current
    DESCRIPTION
        "This object represents the total number of
        data frame transmitted on the radio." 
    ::= { cLApDot11RadioStatsEntry 9 }

cLApDot11RadioStatsRxDataPacketCount OBJECT-TYPE
    SYNTAX          Counter32
    UNITS           "packets"
    MAX-ACCESS      read-only
    STATUS          current
    DESCRIPTION
        "This object represents the total number of
        data packets received on the radio." 
    ::= { cLApDot11RadioStatsEntry 10 }

cLApDot11RadioStatsTxDataPacketCount OBJECT-TYPE
    SYNTAX          Counter32
    UNITS           "packets"
    MAX-ACCESS      read-only
    STATUS          current
    DESCRIPTION
        "This object represents the total number of
        data packets transmitted on the radio." 
    ::= { cLApDot11RadioStatsEntry 11 }

cLApDot11RadioStatsRetryFrameCount OBJECT-TYPE
    SYNTAX          Counter32
    UNITS           "frames"
    MAX-ACCESS      read-only
    STATUS          current
    DESCRIPTION
        "This object represents the total number of
        downstream retry frames on the radio." 
    ::= { cLApDot11RadioStatsEntry 12 }

cLApDot11RadioStatsRetryPacketCount OBJECT-TYPE
    SYNTAX          Counter32
    UNITS           "packets"
    MAX-ACCESS      read-only
    STATUS          current
    DESCRIPTION
        "This object represents the total number of
        downstream retry packets on the radio." 
    ::= { cLApDot11RadioStatsEntry 13 }
 

-- ********************************************************************
-- * AP Radio Rssi Stats
-- *******************************************************************

cLApDot11RadioRssiTable OBJECT-TYPE
    SYNTAX          SEQUENCE OF CLApDot11RadioRssiEntry 
    MAX-ACCESS      not-accessible
    STATUS          current
    DESCRIPTION
        "This table represents Per AP, Per Radio Stats information
        of Average, Highest, Lowest Rssi of all the clients update
        of the APs Radio."
    ::= { ciscoLwappApIf 9 }

cLApDot11RadioRssiEntry OBJECT-TYPE
    SYNTAX          CLApDot11RadioRssiEntry
    MAX-ACCESS      not-accessible
    STATUS          current
    DESCRIPTION
        "This entry contains stats information of
        Average, Highest and Lowest RSSI of Per AP Per Radio."
    INDEX           {
                        cLApSysMacAddress,
                        cLApDot11IfType
                    } 
    ::= { cLApDot11RadioRssiTable 1 }

CLApDot11RadioRssiEntry ::= SEQUENCE {
        cLApDot11RadioRssiHighest Integer32,
        cLApDot11RadioRssiLowest  Integer32,
        cLApDot11RadioRssiAverage Integer32
}

cLApDot11RadioRssiHighest OBJECT-TYPE
    SYNTAX          Integer32
    UNITS           "dbm"
    MAX-ACCESS      read-only
    STATUS          current
    DESCRIPTION
        "This object represents the Highest Rssi value of the specific
        radio on this access point. The value '0' dbm represents no 
        activity on this access point radio." 
    ::= { cLApDot11RadioRssiEntry 1 }

cLApDot11RadioRssiLowest OBJECT-TYPE
    SYNTAX          Integer32
    UNITS           "dbm"
    MAX-ACCESS      read-only
    STATUS          current
    DESCRIPTION
        "This object represents the Lowest Rssi value of the specific
        radio on this access point. The value '0' dbm represents no 
        activity on this access point radio." 
    ::= { cLApDot11RadioRssiEntry 2 }

cLApDot11RadioRssiAverage OBJECT-TYPE
    SYNTAX          Integer32
    UNITS           "dbm"
    MAX-ACCESS      read-only
    STATUS          current
    DESCRIPTION
        "This object represents the Average Rssi value of the specific
        radio on this access point. The value '0' dbm represents no 
        activity on this access point radio." 
    ::= { cLApDot11RadioRssiEntry 3 }
 

-- ********************************************************************
-- *  AP Crash file Info
-- ********************************************************************

cLApCrashInfoTable OBJECT-TYPE
    SYNTAX          SEQUENCE OF CLApCrashInfoEntry 
    MAX-ACCESS      not-accessible
    STATUS          current
    DESCRIPTION
        "This table represents the crash file information
        for each AP. 
        An entry is automatically added to this table when 
        an Access Points crashes and reboots. 
        Entry is removed from this table when AP 
        disassociates from the controllers."
    ::= { ciscoLwappAp 8 }

cLApCrashInfoEntry OBJECT-TYPE
    SYNTAX          CLApCrashInfoEntry
    MAX-ACCESS      not-accessible
    STATUS          current
    DESCRIPTION
        "Each entry in this table provides crash
        information available for each AP."
    INDEX           { cLApSysMacAddress } 
    ::= { cLApCrashInfoTable 1 }

CLApCrashInfoEntry ::= SEQUENCE {
        cLApCrashFileName      SnmpAdminString,
        cLApCrashFileSize      Unsigned32,
        cLApCrashFileTimeStamp DateAndTime
}

cLApCrashFileName OBJECT-TYPE
    SYNTAX          SnmpAdminString (SIZE  (1..28))
    MAX-ACCESS      read-only
    STATUS          current
    DESCRIPTION
        "This object represents the crash file name for a specific AP." 
    ::= { cLApCrashInfoEntry 1 }

cLApCrashFileSize OBJECT-TYPE
    SYNTAX          Unsigned32
    MAX-ACCESS      read-only
    STATUS          current
    DESCRIPTION
        "This object represents the size of the crash file." 
    ::= { cLApCrashInfoEntry 2 }

cLApCrashFileTimeStamp OBJECT-TYPE
    SYNTAX          DateAndTime
    MAX-ACCESS      read-only
    STATUS          current
    DESCRIPTION
        "This object represents the timestamp of the crash file." 
    ::= { cLApCrashInfoEntry 3 }
 


cLApExtTable OBJECT-TYPE
    SYNTAX          SEQUENCE OF CLApExtEntry 
    MAX-ACCESS      not-accessible
    STATUS          current
    DESCRIPTION
        "This table represents the system information
        for each AP."
    ::= { ciscoLwappAp 10 }

cLApExtEntry OBJECT-TYPE
    SYNTAX          CLApExtEntry
    MAX-ACCESS      not-accessible
    STATUS          current
    DESCRIPTION
        "Each entry in this table provides system
        information for each AP."
    INDEX           { cLApSysMacAddress } 
    ::= { cLApExtTable 1 }

CLApExtEntry ::= SEQUENCE {
        cLApLEDFlashStatus                   TruthValue,
        cLApLEDFlashDuration                 Unsigned32,
        cLApInetAddressType                  InetAddressType,
        cLApInetAddress                      InetAddress,
        cLApStaticIpv6AddressEnabled         TruthValue,
        cLApStaticIpv6InetAddressType        InetAddressType,
        cLApStaticIpv6InetAddress            InetAddress,
        cLApStaticIpv6PrefixLength           Unsigned32,
        cLApStaticIpv6GatewayInetAddressType InetAddressType,
        cLApStaticIpv6GatewayInetAddress     InetAddress,
        cLApStaticIpNetmaskType              InetAddressType,
        cLApStaticIpNetmask                  InetAddress,
        cLApPreferMode                       INTEGER,
        cLApPreferModeApplied                INTEGER,
        cLApIndoorMode                       INTEGER
}

cLApLEDFlashStatus OBJECT-TYPE
    SYNTAX          TruthValue
    MAX-ACCESS      read-write
    STATUS          current
    DESCRIPTION
        "This object specifies the state of the AP LED Flash.
        A value of 'true' indicates LED flash is enabled.
        A value of 'false' indicates LED flash is disabled." 
    ::= { cLApExtEntry 1 }

cLApLEDFlashDuration OBJECT-TYPE
    SYNTAX          Unsigned32
    UNITS           "seconds"
    MAX-ACCESS      read-write
    STATUS          current
    DESCRIPTION
        "This object specifies the duration for which the AP's LED
        should blink. This is applicable when the value of 
        cLApFlashStatus is TRUE. Value of 0 indicates the blinking 
        for infinite duration." 
    ::= { cLApExtEntry 2 }

cLApInetAddressType OBJECT-TYPE
    SYNTAX          InetAddressType
    MAX-ACCESS      read-write
    STATUS          current
    DESCRIPTION
        "This object specifies the type of the AP
        address made available through 
        cLApInetAddress." 
    ::= { cLApExtEntry 3 }

cLApInetAddress OBJECT-TYPE
    SYNTAX          InetAddress
    MAX-ACCESS      read-write
    STATUS          current
    DESCRIPTION
        "This object specifies the address of the
        Access Point." 
    ::= { cLApExtEntry 4 }

cLApStaticIpv6AddressEnabled OBJECT-TYPE
    SYNTAX          TruthValue
    MAX-ACCESS      read-write
    STATUS          current
    DESCRIPTION
        "This object specifies that AP is
        configured to use static IPv6 address.  
        A value of 'true' indicates AP can assign with static
        IP address.
        A value of 'false' indicates AP cannot assign with static
        IP address." 
    ::= { cLApExtEntry 5 }

cLApStaticIpv6InetAddressType OBJECT-TYPE
    SYNTAX          InetAddressType
    MAX-ACCESS      read-write
    STATUS          current
    DESCRIPTION
        "This object specified the address type made
        available through cLApStaticIpv6InetAddress." 
    ::= { cLApExtEntry 6 }

cLApStaticIpv6InetAddress OBJECT-TYPE
    SYNTAX          InetAddress
    MAX-ACCESS      read-write
    STATUS          current
    DESCRIPTION
        "This object specifies the static IPv6 address
        of the Access Point." 
    ::= { cLApExtEntry 7 }

cLApStaticIpv6PrefixLength OBJECT-TYPE
    SYNTAX          Unsigned32 (0..128)
    MAX-ACCESS      read-write
    STATUS          current
    DESCRIPTION
        "This object specifies the prefix length of the static IP
        Address configured on the AP." 
    ::= { cLApExtEntry 8 }

cLApStaticIpv6GatewayInetAddressType OBJECT-TYPE
    SYNTAX          InetAddressType
    MAX-ACCESS      read-write
    STATUS          current
    DESCRIPTION
        "This object specified the address type made
        available through cLApStaticIpv6GatewayInetAddress." 
    ::= { cLApExtEntry 9 }

cLApStaticIpv6GatewayInetAddress OBJECT-TYPE
    SYNTAX          InetAddress
    MAX-ACCESS      read-write
    STATUS          current
    DESCRIPTION
        "This object specifies the IPv6 Address of the Gateway server.
        This attribute can be configured only if the static IP
        option is turned on in the AP." 
    ::= { cLApExtEntry 10 }

cLApStaticIpNetmaskType OBJECT-TYPE
    SYNTAX          InetAddressType
    MAX-ACCESS      read-write
    STATUS          current
    DESCRIPTION
        "This object specifies the netmask address type for AP's
        static IP." 
    ::= { cLApExtEntry 11 }

cLApStaticIpNetmask OBJECT-TYPE
    SYNTAX          InetAddress
    MAX-ACCESS      read-write
    STATUS          current
    DESCRIPTION
        "This object specifies netmask for ipv4 address." 
    ::= { cLApExtEntry 12 }

cLApPreferMode OBJECT-TYPE
    SYNTAX          INTEGER  {
                        ipv4(1),
                        ipv6(2)
                    }
    MAX-ACCESS      read-only
    STATUS          current
    DESCRIPTION
        "This object represents the capwap prefer-mode (ipv4 or ipv6)
        of AP." 
    ::= { cLApExtEntry 13 }

cLApPreferModeApplied OBJECT-TYPE
    SYNTAX          INTEGER  {
                        apgroup(1),
                        global(2)
                    }
    MAX-ACCESS      read-only
    STATUS          current
    DESCRIPTION
        "This object represents the prefer-mode of AP applied by
        apgroup config or global config.
        apgroup - capwap prefer mode applied at ap group level.
        global - capwap prefer mode applied globally." 
    ::= { cLApExtEntry 14 }

cLApIndoorMode OBJECT-TYPE
    SYNTAX          TruthValue
    MAX-ACCESS      read-write
    STATUS          current
    DESCRIPTION
        "This object specifies the indoor/outdoor mode of the AP.
        A value of 'true' indicates AP is in Indoor Mode.
        A value of 'false' indicates AP is in Outdoor Mode." 
    ::= { cLApExtEntry 17 }

-- ********************************************************************
-- *  AP Sys Info
-- ********************************************************************

cLApSysInfoTable OBJECT-TYPE
    SYNTAX          SEQUENCE OF CLApSysInfoEntry 
    MAX-ACCESS      not-accessible
    STATUS          current
    DESCRIPTION
        "This table represents the system information
        for each AP."
    ::= { ciscoLwappAp 9 }

cLApSysInfoEntry OBJECT-TYPE
    SYNTAX          CLApSysInfoEntry
    MAX-ACCESS      not-accessible
    STATUS          current
    DESCRIPTION
        "Each entry in this table provides system
        information for each AP."
    INDEX           { cLApSysMacAddress } 
    ::= { cLApSysInfoTable 1 }

CLApSysInfoEntry ::= SEQUENCE {
        cLApSysMemType   SnmpAdminString,
        cLApSysMemSize   Unsigned32,
        cLApSysFlashSize Unsigned32,
        cLApSysCpuType   SnmpAdminString,
        cLApSysFlashType SnmpAdminString
}

cLApSysMemType OBJECT-TYPE
    SYNTAX          SnmpAdminString
    MAX-ACCESS      read-only
    STATUS          current
    DESCRIPTION
        "This object represents the AP system memory type." 
    ::= { cLApSysInfoEntry 1 }

cLApSysMemSize OBJECT-TYPE
    SYNTAX          Unsigned32
    UNITS           "KBytes"
    MAX-ACCESS      read-only
    STATUS          current
    DESCRIPTION
        "This object represents the total AP system memory size in
        Kbytes." 
    ::= { cLApSysInfoEntry 2 }

cLApSysFlashSize OBJECT-TYPE
    SYNTAX          Unsigned32
    UNITS           "KBytes"
    MAX-ACCESS      read-only
    STATUS          current
    DESCRIPTION
        "This object represents the AP flash size in Kbytes." 
    ::= { cLApSysInfoEntry 3 }

cLApSysCpuType OBJECT-TYPE
    SYNTAX          SnmpAdminString
    MAX-ACCESS      read-only
    STATUS          current
    DESCRIPTION
        "This object represents the AP cpu type" 
    ::= { cLApSysInfoEntry 4 }

cLApSysFlashType OBJECT-TYPE
    SYNTAX          SnmpAdminString
    MAX-ACCESS      read-only
    STATUS          current
    DESCRIPTION
        "This object represents the AP Flash type." 
    ::= { cLApSysInfoEntry 5 }
 

-- ********************************************************************
-- *  AP Dot11 radio rate statistics Information
-- ********************************************************************

cLApDot11RadioRateStatsTable OBJECT-TYPE
    SYNTAX          SEQUENCE OF CLApDot11RadioRateStatsEntry 
    MAX-ACCESS      not-accessible
    STATUS          current
    DESCRIPTION
        "This table represents per AP, per radio, per rate stats
        information of all the clients of the APs Radio."
    ::= { ciscoLwappApIf 10 }

cLApDot11RadioRateStatsEntry OBJECT-TYPE
    SYNTAX          CLApDot11RadioRateStatsEntry
    MAX-ACCESS      not-accessible
    STATUS          current
    DESCRIPTION
        "This entry contains stats information of Rx/Tx packets and
        bytes of per AP per radio per rate."
    INDEX           {
                        cLApSysMacAddress,
                        cLApDot11IfSlotId,
                        cLApDot11RadioRate
                    } 
    ::= { cLApDot11RadioRateStatsTable 1 }

CLApDot11RadioRateStatsEntry ::= SEQUENCE {
        cLApDot11RadioRate               Unsigned32,
        cLApDot11RadioRateStatsRxPackets Counter32,
        cLApDot11RadioRateStatsRxBytes   Counter32,
        cLApDot11RadioRateStatsTxPackets Counter32,
        cLApDot11RadioRateStatsTxBytes   Counter32,
        cLApDot11RadioRateString         SnmpAdminString
}

cLApDot11RadioRate OBJECT-TYPE
    SYNTAX          Unsigned32
    MAX-ACCESS      not-accessible
    STATUS          current
    DESCRIPTION
        "This object uniquely identifies the data rate value
        for a particular band." 
    ::= { cLApDot11RadioRateStatsEntry 1 }

cLApDot11RadioRateStatsRxPackets OBJECT-TYPE
    SYNTAX          Counter32
    MAX-ACCESS      read-only
    STATUS          current
    DESCRIPTION
        "This object represents the number of packets received for
        the specific radio and data rate on this access point." 
    ::= { cLApDot11RadioRateStatsEntry 2 }

cLApDot11RadioRateStatsRxBytes OBJECT-TYPE
    SYNTAX          Counter32
    MAX-ACCESS      read-only
    STATUS          current
    DESCRIPTION
        "This object represents the number of bytes received for
        the specific radio and data rate on this access point." 
    ::= { cLApDot11RadioRateStatsEntry 3 }

cLApDot11RadioRateStatsTxPackets OBJECT-TYPE
    SYNTAX          Counter32
    MAX-ACCESS      read-only
    STATUS          current
    DESCRIPTION
        "This object represents the number of packets transmitted from
        the specific radio and data rate on this access point." 
    ::= { cLApDot11RadioRateStatsEntry 4 }

cLApDot11RadioRateStatsTxBytes OBJECT-TYPE
    SYNTAX          Counter32
    MAX-ACCESS      read-only
    STATUS          current
    DESCRIPTION
        "This object represents the number of bytes transmitted from
        the specific radio and data rate on this access point." 
    ::= { cLApDot11RadioRateStatsEntry 5 }

cLApDot11RadioRateString OBJECT-TYPE
    SYNTAX          SnmpAdminString
    MAX-ACCESS      read-only
    STATUS          current
    DESCRIPTION
        "This object represents the data rate in a user-friendly
        text string format." 
    ::= { cLApDot11RadioRateStatsEntry 6 }
 


cLApPacketDumpFtpServerAddressType OBJECT-TYPE
    SYNTAX          InetAddressType
    MAX-ACCESS      read-write
    STATUS          current
    DESCRIPTION
        "This object specifies the address type of
        the server to which the packet dump is stored." 
    ::= { ciscoLwappPacketDumpInfo 1 }

cLApPacketDumpFtpServerAddress OBJECT-TYPE
    SYNTAX          InetAddress
    MAX-ACCESS      read-write
    STATUS          current
    DESCRIPTION
        "This object specifies the address of the server to
        which the packet dump is stored." 
    ::= { ciscoLwappPacketDumpInfo 2 }

cLApPacketDumpFtpServerPath OBJECT-TYPE
    SYNTAX          SnmpAdminString
    MAX-ACCESS      read-write
    STATUS          current
    DESCRIPTION
        "This object specifies the directory path for
        the packet dump storing.
        The controller remembers the last file path used." 
    ::= { ciscoLwappPacketDumpInfo 3 }

cLApPacketDumpFtpUsername OBJECT-TYPE
    SYNTAX          SnmpAdminString
    MAX-ACCESS      read-write
    STATUS          current
    DESCRIPTION
        "This object specifies to store the FTP username
        for transferring the packet-dump to the FTP server." 
    ::= { ciscoLwappPacketDumpInfo 4 }

cLApPacketDumpFtpPassword OBJECT-TYPE
    SYNTAX          SnmpAdminString
    MAX-ACCESS      read-write
    STATUS          current
    DESCRIPTION
        "This object specifies the FTP server login password to
        store the packet dump." 
    ::= { ciscoLwappPacketDumpInfo 5 }

cLApPacketDumpClassifier OBJECT-TYPE
    SYNTAX          BITS {
                        management(0),
                        data(1),
                        control(2),
                        dot1x(3)
                    }
    MAX-ACCESS      read-write
    STATUS          current
    DESCRIPTION
        "This object specifies the Frame Type considered
        for packet-dump." 
    ::= { ciscoLwappPacketDumpInfo 6 }

cLApPacketDumpBufferSize OBJECT-TYPE
    SYNTAX          Unsigned32
    MAX-ACCESS      read-write
    STATUS          current
    DESCRIPTION
        "This object specifies the buffer size considered
        for packet-dump." 
    ::= { ciscoLwappPacketDumpInfo 7 }

cLApPacketDumpCaptureTime OBJECT-TYPE
    SYNTAX          Unsigned32
    UNITS           "minutes"
    MAX-ACCESS      read-write
    STATUS          current
    DESCRIPTION
        "This object specifies the capture time considered
        for packet-dump." 
    ::= { ciscoLwappPacketDumpInfo 8 }

cLApPacketDumpTruncation OBJECT-TYPE
    SYNTAX          Unsigned32
    UNITS           "bytes"
    MAX-ACCESS      read-write
    STATUS          current
    DESCRIPTION
        "This object specifies the length of the packet
        after truncation" 
    ::= { ciscoLwappPacketDumpInfo 9 }

cLApPacketDumpApName OBJECT-TYPE
    SYNTAX          SnmpAdminString
    MAX-ACCESS      read-write
    STATUS          current
    DESCRIPTION
        "This object specifies the AP name on which
        we need to start packet dump." 
    ::= { ciscoLwappPacketDumpInfo 10 }

cLApPacketDumpDeviceMacAddress OBJECT-TYPE
    SYNTAX          MacAddress
    MAX-ACCESS      read-write
    STATUS          current
    DESCRIPTION
        "This object specifies the MAC address of the
        device for which we need to start packet dump on the AP." 
    ::= { ciscoLwappPacketDumpInfo 11 }

cLApPacketDumpStartStop OBJECT-TYPE
    SYNTAX          INTEGER  {
                        start(1),
                        stop(2),
                        none(3)
                    }
    MAX-ACCESS      read-write
    STATUS          current
    DESCRIPTION
        "This object specifies user to start or stop, packet dump on
        the associated AP to which the particular mobile station is
        connected.  
        start  - packet dump is started.
        stop - packet dump is stopped.
        none-  information about current session is not available to the
        controller." 
    ::= { ciscoLwappPacketDumpInfo 12 }
-- ********************************************************************
-- * AP Radio Ssid Stats
-- *******************************************************************

cLApDot11RadioSsidTable OBJECT-TYPE
    SYNTAX          SEQUENCE OF CLApDot11RadioSsidEntry 
    MAX-ACCESS      not-accessible
    STATUS          current
    DESCRIPTION
        "This table represents Per AP, Per Radio information
        of Ssid of all the neighbor APs updating
        the APs Radio."
    ::= { ciscoLwappApIf 11 }

cLApDot11RadioSsidEntry OBJECT-TYPE
    SYNTAX          CLApDot11RadioSsidEntry
    MAX-ACCESS      not-accessible
    STATUS          current
    DESCRIPTION
        "This entry contains ssid information of
        Neighbor APs of Per AP Per Radio."
    INDEX           {
                        cLApSysMacAddress,
                        cLApDot11IfType,
                        cLApSsidIndex
                    } 
    ::= { cLApDot11RadioSsidTable 1 }

CLApDot11RadioSsidEntry ::= SEQUENCE {
        cLApSsidIndex          Unsigned32,
        cLApDot11RadioSsidName OCTET STRING
}

cLApSsidIndex OBJECT-TYPE
    SYNTAX          Unsigned32
    MAX-ACCESS      not-accessible
    STATUS          current
    DESCRIPTION
        "This object indicates the index of the ssid
        detected by Per AP Per Radio." 
    ::= { cLApDot11RadioSsidEntry 1 }

cLApDot11RadioSsidName OBJECT-TYPE
    SYNTAX          OCTET STRING (SIZE  (1..32))
    MAX-ACCESS      read-only
    STATUS          current
    DESCRIPTION
        "This object represents the ssid name of the neighbor AP
        on this access point." 
    ::= { cLApDot11RadioSsidEntry 2 }
 

-- ********************************************************************
-- * AP Cable Modem Stats
-- *******************************************************************

cLApCableModemIfStatsTable OBJECT-TYPE
    SYNTAX          SEQUENCE OF CLApCableModemIfStatsEntry 
    MAX-ACCESS      not-accessible
    STATUS          current
    DESCRIPTION
        "This table represents the statistics of cable
        modem interface per AP when the CM connected to the AP."
    ::= { ciscoLwappApIf 12 }

cLApCableModemIfStatsEntry OBJECT-TYPE
    SYNTAX          CLApCableModemIfStatsEntry
    MAX-ACCESS      not-accessible
    STATUS          current
    DESCRIPTION
        "This entry contains stats information of cable modem
        per AP"
    INDEX           { cLApSysMacAddress } 
    ::= { cLApCableModemIfStatsTable 1 }

CLApCableModemIfStatsEntry ::= SEQUENCE {
        cLApCmMacAddress      MacAddress,
        cLApCmApMacAddress    MacAddress,
        cLApCmSwVersion       SnmpAdminString,
        cLApEthernetSpeed     SnmpAdminString,
        cLApEthernetStatus    SnmpAdminString,
        cLApCmStatus          SnmpAdminString,
        cLApCmSerialNumber    SnmpAdminString,
        cLApCmUsChannelStatus SnmpAdminString,
        cLApCmDsChannelStatus SnmpAdminString,
        cLApCmMaskBit         SnmpAdminString
}

cLApCmMacAddress OBJECT-TYPE
    SYNTAX          MacAddress
    MAX-ACCESS      read-only
    STATUS          current
    DESCRIPTION
        "This object represents the MAC address
        of the Cable Modem that has been connected to
        the AP." 
    ::= { cLApCableModemIfStatsEntry 1 }

cLApCmApMacAddress OBJECT-TYPE
    SYNTAX          MacAddress
    MAX-ACCESS      read-only
    STATUS          current
    DESCRIPTION
        "This object represents the ethernet MAC address
        of the AP where the Cable Modem is connected." 
    ::= { cLApCableModemIfStatsEntry 2 }

cLApCmSwVersion OBJECT-TYPE
    SYNTAX          SnmpAdminString
    MAX-ACCESS      read-only
    STATUS          current
    DESCRIPTION
        "This object represents the software version
        of the Cable Modem that has been connected to
        the AP." 
    ::= { cLApCableModemIfStatsEntry 3 }

cLApEthernetSpeed OBJECT-TYPE
    SYNTAX          SnmpAdminString
    MAX-ACCESS      read-only
    STATUS          current
    DESCRIPTION
        "This object represents the ethernet speed
        of the Cable Modem that has been connected to
        the AP." 
    ::= { cLApCableModemIfStatsEntry 4 }

cLApEthernetStatus OBJECT-TYPE
    SYNTAX          SnmpAdminString
    MAX-ACCESS      read-only
    STATUS          current
    DESCRIPTION
        "This object represents the ethernet status
        of the Cable Modem that has been connected to
        the AP." 
    ::= { cLApCableModemIfStatsEntry 5 }

cLApCmStatus OBJECT-TYPE
    SYNTAX          SnmpAdminString
    MAX-ACCESS      read-only
    STATUS          current
    DESCRIPTION
        "This object represents the status of the
        Cable Modem that has been connected to
        the AP." 
    ::= { cLApCableModemIfStatsEntry 6 }

cLApCmSerialNumber OBJECT-TYPE
    SYNTAX          SnmpAdminString
    MAX-ACCESS      read-only
    STATUS          current
    DESCRIPTION
        "This object represents the serial number
        of the Cable Modem that has been connected to
        the AP." 
    ::= { cLApCableModemIfStatsEntry 7 }

cLApCmUsChannelStatus OBJECT-TYPE
    SYNTAX          SnmpAdminString
    MAX-ACCESS      read-only
    STATUS          current
    DESCRIPTION
        "This object represents the upstream channel
        Status of the Cable Modem that has been 
        connected to the AP." 
    ::= { cLApCableModemIfStatsEntry 8 }

cLApCmDsChannelStatus OBJECT-TYPE
    SYNTAX          SnmpAdminString
    MAX-ACCESS      read-only
    STATUS          current
    DESCRIPTION
        "This object represents the downstream Channel
        Status of the Cable Modem that has been 
        connected to the AP." 
    ::= { cLApCableModemIfStatsEntry 9 }

cLApCmMaskBit OBJECT-TYPE
    SYNTAX          SnmpAdminString
    MAX-ACCESS      read-only
    STATUS          current
    DESCRIPTION
        "This object represents the mask bit
        of the Cable Modem based on the mask
        value the CM statistics is displayed 
        for the AP." 
    ::= { cLApCableModemIfStatsEntry 10 }
 

-- ********************************************************************
-- *    AP Environmental information
-- ********************************************************************

cLApEnvInfoTable OBJECT-TYPE
    SYNTAX          SEQUENCE OF CLApEnvInfoEntry 
    MAX-ACCESS      not-accessible
    STATUS          current
    DESCRIPTION
        "This table represents information about temperature
        degree state and orientation of the AP"
    ::= { ciscoLwappAp 11 }

cLApEnvInfoEntry OBJECT-TYPE
    SYNTAX          CLApEnvInfoEntry
    MAX-ACCESS      not-accessible
    STATUS          current
    DESCRIPTION
        "Each entry represents a conceptual row in this table.
        An entry is created when AP joins the controller.
        The entry is removed when the AP lose their
        association with the controller due to loss of
        communication with controller or when a AP 
        is reset."
    INDEX           { cLApSysMacAddress } 
    ::= { cLApEnvInfoTable 1 }

CLApEnvInfoEntry ::= SEQUENCE {
        cLApEnvTemperatureDegree SnmpAdminString,
        cLApEnvTemperatureState  INTEGER,
        cLApEnvOrientation       INTEGER,
        cLApEnvPoeOutStatus      INTEGER
}

cLApEnvTemperatureDegree OBJECT-TYPE
    SYNTAX          SnmpAdminString
    MAX-ACCESS      read-only
    STATUS          current
    DESCRIPTION
        "This object represents temperature
        of the AP in both celcius and fahrenheit." 
    ::= { cLApEnvInfoEntry 1 }

cLApEnvTemperatureState OBJECT-TYPE
    SYNTAX          INTEGER  {
                        unknown(0),
                        green(1),
                        yellow(2),
                        red(3)
                    }
    MAX-ACCESS      read-only
    STATUS          current
    DESCRIPTION
        "This object represents temperature state
        of the AP." 
    ::= { cLApEnvInfoEntry 2 }

cLApEnvOrientation OBJECT-TYPE
    SYNTAX          INTEGER  {
                        unknown(0),
                        vertical(1),
                        horizontal(2)
                    }
    MAX-ACCESS      read-only
    STATUS          current
    DESCRIPTION
        "This object represents orientation
        of the AP." 
    ::= { cLApEnvInfoEntry 3 }

cLApEnvPoeOutStatus OBJECT-TYPE
    SYNTAX          INTEGER  {
                        unknown(1),
                        on(2),
                        off(3)
                    }
    MAX-ACCESS      read-only
    STATUS          current
    DESCRIPTION
        "This object represents POE out status
        of the AP." 
    ::= { cLApEnvInfoEntry 4 }
 

-- ********************************************************************
-- *    GPS related information
-- ********************************************************************

cLApGpsInfoTable OBJECT-TYPE
    SYNTAX          SEQUENCE OF CLApGpsInfoEntry 
    MAX-ACCESS      not-accessible
    STATUS          current
    DESCRIPTION
        "This table represents information about location and
        velocity parameters received from the GPS module on the
        LWAPP Access Points that have joined the controller."
    ::= { ciscoLwappAp 12 }

cLApGpsInfoEntry OBJECT-TYPE
    SYNTAX          CLApGpsInfoEntry
    MAX-ACCESS      not-accessible
    STATUS          current
    DESCRIPTION
        "Each entry represents a conceptual row in this table.
        An entry is created when AP joins the controller.
        The entry is removed when the AP lose their
        association with the controller due to loss of
        communication with controller"
    INDEX           { cLApSysMacAddress } 
    ::= { cLApGpsInfoTable 1 }

CLApGpsInfoEntry ::= SEQUENCE {
        cLApGpsLocationPresent TruthValue,
        cLApGpsLocationValid   TruthValue,
        cLApGpsLatitude        SnmpAdminString,
        cLApGpsLongitude       SnmpAdminString,
        cLApGpsAltitude        SnmpAdminString,
        cLApGpsCollectionTime  TimeStamp
}

cLApGpsLocationPresent OBJECT-TYPE
    SYNTAX          TruthValue
    MAX-ACCESS      read-only
    STATUS          current
    DESCRIPTION
        "This object represents whether the access point
        has the GPS module installed or not.
        A value of 'true' indicates GPS module is present in
        AP.
        A value of 'false' indicates GPS module is not 
        present in AP." 
    ::= { cLApGpsInfoEntry 1 }

cLApGpsLocationValid OBJECT-TYPE
    SYNTAX          TruthValue
    MAX-ACCESS      read-only
    STATUS          current
    DESCRIPTION
        "This object represents whether the location
        information is valid or not. 
        A value of 'true' indicates GPS location
        is valid.
        A value of 'false' indicates GPS location 
        is not valid." 
    ::= { cLApGpsInfoEntry 2 }

cLApGpsLatitude OBJECT-TYPE
    SYNTAX          SnmpAdminString
    MAX-ACCESS      read-only
    STATUS          current
    DESCRIPTION
        "This object represents latitude information
        in the GPS data received." 
    ::= { cLApGpsInfoEntry 3 }

cLApGpsLongitude OBJECT-TYPE
    SYNTAX          SnmpAdminString
    MAX-ACCESS      read-only
    STATUS          current
    DESCRIPTION
        "This object represents longitude information
        in the GPS data received." 
    ::= { cLApGpsInfoEntry 4 }

cLApGpsAltitude OBJECT-TYPE
    SYNTAX          SnmpAdminString
    MAX-ACCESS      read-only
    STATUS          current
    DESCRIPTION
        "This object represents altitude information
        in the GPS data received." 
    ::= { cLApGpsInfoEntry 5 }

cLApGpsCollectionTime OBJECT-TYPE
    SYNTAX          TimeStamp
    MAX-ACCESS      read-only
    STATUS          current
    DESCRIPTION
        "This object represents the time when GPS
        data was collected." 
    ::= { cLApGpsInfoEntry 6 }
 

-- ********************************************************************
-- * AP Profile Configuration
-- ********************************************************************

cLApProfileTable OBJECT-TYPE
    SYNTAX          SEQUENCE OF CLApProfileEntry 
    MAX-ACCESS      not-accessible
    STATUS          current
    DESCRIPTION
        "This table provides the information about the Access Point
        profiles. Access Point profile is a set of configuration which
        can be different for APs at different site/location.
        Rows are added or deleted by explicit management actions
        initiated by the user from a network management station through
        the cLApProfileRowStatus object."
    ::= { ciscoLwappApProfile 1 }

cLApProfileEntry OBJECT-TYPE
    SYNTAX          CLApProfileEntry
    MAX-ACCESS      not-accessible
    STATUS          current
    DESCRIPTION
        "Each entry in this table represents the AP profile
        configuration which can be applied to set of APs based on the
        controller configuration. Entries can be added/deleted by
        explicit management actions by NMS or by user console."
    INDEX           { cLApProfileName } 
    ::= { cLApProfileTable 1 }

CLApProfileEntry ::= SEQUENCE {
        cLApProfileName                                 SnmpAdminString,
        cLApProfileRowStatus                            RowStatus,
        cLApProfileCredentialGlobalUserName             SnmpAdminString,
        cLApProfileCredentialGlobalPassword             SnmpAdminString,
        cLApProfileCredentialGlobalSecret               SnmpAdminString,
        cLApProfileCredentialEnableGlobalCredentials    TruthValue,
        cLApProfileLinkLatencyEnable                    INTEGER,
        cLApProfileHaloBleBeaconInterval                Unsigned32,
        cLApProfileFastHbTimerTimeout                   Unsigned32,
        cLApProfileFastHbTimerEnabled                   TruthValue,
        cLApProfilePrimaryDiscoveryTimeout              Unsigned32,
        cLApProfileBackupPrimaryControllerAddressType   InetAddressType,
        cLApProfileBackupPrimaryControllerAddress       InetAddress,
        cLApProfileBackupPrimaryControllerName          SnmpAdminString,
        cLApProfileBackupSecondaryControllerAddressType InetAddressType,
        cLApProfileBackupSecondaryControllerAddress     InetAddress,
        cLApProfileBackupSecondaryControllerName        SnmpAdminString,
        cLApProfileBackupTertiaryControllerAddressType  InetAddressType,
        cLApProfileBackupTertiaryControllerAddress      InetAddress,
        cLApProfileBackupTertiaryControllerName         SnmpAdminString,
        cLApProfileTcpMss                               Unsigned32,
        cLApProfileRetransmitCount                      Unsigned32,
        cLApProfileRetransmitTimeout                    Unsigned32,
        cLApProfileOeapDisableLocalAccess               TruthValue,
        cLApProfileLedState                             TruthValue,
        cLApProfileRadioInterfaceShutdownEnabled        TruthValue,
        cLApProfileEthernetInterfaceDowntime            Unsigned32,
        cLApProfileMulticastGroupAddressType            InetAddressType,
        cLApProfileMulticastGroupAddress                InetAddress,
        cLApProfileMulticastMode                        INTEGER,
        cLApProfilePrimedJoinTimeout                    Unsigned32,
        cLApProfilePreferMode                           INTEGER,
        cLApProfileApLagEnabled                         TruthValue,
        cLApProfile802dot1xAuthenticationEnabled        TruthValue,
        cLApProfile802dot1xSupplicantUsername           SnmpAdminString,
        cLApProfile802dot1xSupplicantPassword           SnmpAdminString,
        cLApProfileEncryptionEnable                     TruthValue,
        cLApProfileTelnetEnable                         TruthValue,
        cLApProfileSshEnable                            TruthValue,
        cLApProfileHyperlocationEnable                  TruthValue,
        cLApProfileHyperlocationDetectionThreshold      Integer32,
        cLApProfileHyperlocationResetThreshold          Unsigned32,
        cLApProfileHyperlocationTriggerThreshold        Unsigned32,
        cLApProfileHyperlocationNtpIpAddressType        InetAddressType,
        cLApProfileHyperlocationNtpIpAddress            InetAddress,
        cLApProfileAdjustMss                            TruthValue,
        cLApProfileDiscoveryTimeout                     Unsigned32,
        cLApProfileHeartBeatTimeout                     Unsigned32,
        cLApProfileCdpEnable                            TruthValue,
        cLApProfileApPacketCaptureProfile               SnmpAdminString,
        cLApProfileRogueReportInterval                  Unsigned32,
        cLApProfileRogueMinimumRssi                     Integer32,
        cLApProfileRogueTransientInterval               Unsigned32,
        cLApProfileRogueContainFlexconnect              TruthValue,
        cLApProfileRogueContainAutoRateEnable           TruthValue,
        cLApProfileRogueDetectionEnable                 TruthValue,
        cLApProfileReportInterval24ghz                  Integer32,
        cLApProfileReportInterval5ghz                   Integer32,
        cLApProfileDot1xApSwitchEapAuth                 INTEGER,
        cLApProfileDot1xApSwtichLscAuth                 INTEGER,
        cLApProfileMeshProfileName                      SnmpAdminString,
        cLApProfileUsbStatus                            TruthValue,
        cLApProfileVlanTagging                          TruthValue,
        cLApProfileApCountryCode                        SnmpAdminString,
        cLApProfileExtModuleEnable                      TruthValue,
        cLApProfileStatsTimer                           Unsigned32,
        cLApProfilePoePreStandardSwitchFlag             TruthValue,
        cLApProfilePoePowerInjectorSelection            INTEGER,
        cLApProfilePoeInjectorSwitchMac                 MacAddress,
        cLApProfileHaloBleBeaconAdvertisedPwr           Unsigned32,
        cLApProfileTftpDownGradeAddressType             InetAddressType,
        cLApProfileTftpDownGradeAddress                 InetAddress,
        cLApProfileTftpDownGradeFileName                SnmpAdminString,
        cLApProfileCoreDumpType                         INTEGER,
        cLApProfileCoreDumpTftpAddressType              InetAddressType,
        cLApProfileCoreDumpTftpAddress                  InetAddress,
        cLApProfileCoreDumpCoreFileName                 SnmpAdminString,
        cLApProfileBackupFallbackEnabled                TruthValue,
        cLApProfileClientRssiStatsEnabled               TruthValue,
        cLApProfileClientRssiStatsReportInterval        Unsigned32,
        cLApProfileGasRateLimitEnable                   TruthValue,
        cLApProfileGasRateLimitNumReqPerInterval        INTEGER,
        cLApProfileGasRateLimitIntervalMsec             INTEGER,
        cLApProfileQoSMapApTrustsUpstreamDSCP           TruthValue,
        cLApProfileUdpliteState                         INTEGER,
        cLApProfileMethodListName                       SnmpAdminString,
        cLApProfileWindowSize                           INTEGER,
        cLApProfileCredentialGlobalSecretType           INTEGER,
        cLApProfileCredentialGlobalPasswordType         INTEGER,
        cLApProfile802dot1xSupplicantPasswordType       INTEGER,
        cLApProfileBssidEnableStats                     TruthValue,
        cLApProfileBssidStatsFrequency                  INTEGER,
        cLApProfilePersistentSsidBroadcastEnable        TruthValue,
        cLApProfileDhcpFallback                         TruthValue,
        cLApProfileOeapRogueDetectionEnable             TruthValue,
        cLApProfileOeapEncryptionEnable                 TruthValue,
        cLApProfileOeapLocalAccessEnable                TruthValue,
        cLApProfileOeapProvSsidEnable                   TruthValue,
        cLApProfileCountryCode                          INTEGER
}

cLApProfileName OBJECT-TYPE
    SYNTAX          SnmpAdminString (SIZE  (0..32))
    MAX-ACCESS      not-accessible
    STATUS          current
    DESCRIPTION
        "This object specifies one instance of an AP Profile on the 
        controller."
    ::= { cLApProfileEntry 1 }

cLApProfileRowStatus OBJECT-TYPE
    SYNTAX          RowStatus
    MAX-ACCESS      read-create
    STATUS          current
    DESCRIPTION
        "This object specifies the row to be added or
        deleted in this table."
    ::= { cLApProfileEntry 2 }

cLApProfileCredentialGlobalUserName OBJECT-TYPE
    SYNTAX          SnmpAdminString (SIZE  (0..32))
    MAX-ACCESS      read-write
    STATUS          current
    DESCRIPTION
        "This object specifies the global username for the APs 
        associated to a particular AP Profile.
        This user name is used to access the console on the AP." 
    ::= { cLApProfileEntry 3 }

cLApProfileCredentialGlobalPassword OBJECT-TYPE
    SYNTAX          SnmpAdminString (SIZE  (0..32))
    MAX-ACCESS      read-write
    STATUS          current
    DESCRIPTION
        "This object specifies the password corresponding to
        the user name represented by cLApProfileCredentialGlobalUserName
        object."
    ::= { cLApProfileEntry 4 }

cLApProfileCredentialGlobalSecret OBJECT-TYPE
    SYNTAX          SnmpAdminString (SIZE  (0..32))
    MAX-ACCESS      read-write
    STATUS          current
    DESCRIPTION
        "This object specifies the secret key for the APs associated
        to particular AP profile. This provides read-write access 
        to the console on the AP." 
    ::= { cLApProfileEntry 5 }

cLApProfileCredentialEnableGlobalCredentials OBJECT-TYPE
    SYNTAX          TruthValue
    MAX-ACCESS      read-create
    STATUS          deprecated
    DESCRIPTION
        "This object specifies whether the global credentials for the
        APs associated to a particular AP Profile is enabled or 
        disabled.

        A value of 'true' enables the global username/password
        to be used for the APs associated to a particular AP Profile.
        A value of 'false' disables the global credentials and
        uses the credentials specific for the APs." 
    ::= { cLApProfileEntry 6 }

cLApProfileLinkLatencyEnable OBJECT-TYPE
    SYNTAX          INTEGER {
                        disable(1),
                        enable(2),
                        data(3),
                        reset(4)
                    }
    MAX-ACCESS      read-write
    STATUS          current
    DESCRIPTION
        "This object specifies to the configuration of the Link
        Latency on the APs associated to a particular AP profile.
        disable - disables the link latency on the APs associated to
                  a particular AP profile.
        enable - enables the link latency on the APs associated to
                 a particular AP profile.
        data - enables data link latency on the APs associated to
               a particular AP profile.
        reset - reset the link latency on the APs associated to
                a particular AP profile."
    ::= { cLApProfileEntry 7 }

cLApProfileHaloBleBeaconInterval OBJECT-TYPE
    SYNTAX          Unsigned32 (1..10)
    UNITS           "Hz"
    MAX-ACCESS      read-write
    STATUS          current
    DESCRIPTION
        "This object specifies the time interval between HALO BLE
        beacon transmissions.
        This value is common to HALO enabled APs that have joined the
        controller under the same AP profile."
    DEFVAL          { 1 }
    ::= { cLApProfileEntry 8 }

cLApProfileFastHbTimerTimeout OBJECT-TYPE
    SYNTAX          Unsigned32 (1..10)
    UNITS           "seconds"
    MAX-ACCESS      read-write
    STATUS          current
    DESCRIPTION
        "This object specifies the timeout value for the Fast Heart Beat
        timer of all the APs associated to the current AP Profile." 
    ::= { cLApProfileEntry 12 }

cLApProfileFastHbTimerEnabled OBJECT-TYPE
    SYNTAX          TruthValue
    MAX-ACCESS      read-write
    STATUS          deprecated
    DESCRIPTION
        "This object specifies if Fast Heart Beat Timer is enabled or 
        not.
        A value of 'true' indicates that this timer is enabled.
        A value of 'false' indicates that this timer is disabled."
    ::= { cLApProfileEntry 13 }

cLApProfilePrimaryDiscoveryTimeout OBJECT-TYPE
    SYNTAX          Unsigned32 (30..3000)
    UNITS           "seconds"
    MAX-ACCESS      read-write
    STATUS          current
    DESCRIPTION
        "This object specifies the timeout value for the primary AP
        discovery for a given Ap profile."
    DEFVAL          { 120 }
    ::= { cLApProfileEntry 14 }

cLApProfileBackupPrimaryControllerAddressType OBJECT-TYPE
    SYNTAX          InetAddressType
    MAX-ACCESS      read-write
    STATUS          current
    DESCRIPTION
        "This object specifies the type of the primary controller's
        address made available through 
        cLApProfileBackupPrimaryControllerAddress."
    ::= { cLApProfileEntry 15 }

cLApProfileBackupPrimaryControllerAddress OBJECT-TYPE
    SYNTAX          InetAddress
    MAX-ACCESS      read-write
    STATUS          current
    DESCRIPTION
        "This object specifies the address of the primary controller
        that the APs in the profile should associate with. The name and
        address should be provided in the same set request. An address
        of all zeros will unset the primary controller."
    ::= { cLApProfileEntry 16 }

cLApProfileBackupPrimaryControllerName OBJECT-TYPE
    SYNTAX          SnmpAdminString (SIZE  (0..32))
    MAX-ACCESS      read-write
    STATUS          current
    DESCRIPTION
        "This object specifies the name of the primary controller
        that the APs in the profile should associate with."
    ::= { cLApProfileEntry 17 }

cLApProfileBackupSecondaryControllerAddressType OBJECT-TYPE
    SYNTAX          InetAddressType
    MAX-ACCESS      read-write
    STATUS          current
    DESCRIPTION
        "This object specifies the type of the secondary
        controller's address made available through 
        cLApProfileBackupSecondaryControllerAddress." 
    ::= { cLApProfileEntry 18 }

cLApProfileBackupSecondaryControllerAddress OBJECT-TYPE
    SYNTAX          InetAddress
    MAX-ACCESS      read-write
    STATUS          current
    DESCRIPTION
        "This object specifies the address of the secondary
        controller that the APs in the profile should associate with.
        The name and address should be provided in the same 
        set request. An address of all zeros will unset the secondary 
        controller." 
    ::= { cLApProfileEntry 19 }

cLApProfileBackupSecondaryControllerName OBJECT-TYPE
    SYNTAX          SnmpAdminString (SIZE  (0..32))
    MAX-ACCESS      read-write
    STATUS          current
    DESCRIPTION
        "This object specifies the name of the secondary controller
        that the APs in the profile should associate."
    ::= { cLApProfileEntry 20 }

cLApProfileBackupTertiaryControllerAddressType OBJECT-TYPE
    SYNTAX          InetAddressType
    MAX-ACCESS      read-write
    STATUS          current
    DESCRIPTION
        "This object specifies the type of the tertiary
        controller's address made available through 
        cLApProfileBackupTertiaryControllerAddress." 
    ::= { cLApProfileEntry 21 }

cLApProfileBackupTertiaryControllerAddress OBJECT-TYPE
    SYNTAX          InetAddress
    MAX-ACCESS      read-write
    STATUS          current
    DESCRIPTION
        "This object specifies the address of the tertiary
        controller that the APs in the profile should associate with.
        The name and address should be provided in the same
        set request. An address of all zeros will unset the tertiary
        controller."
    ::= { cLApProfileEntry 22 }

cLApProfileBackupTertiaryControllerName OBJECT-TYPE
    SYNTAX          SnmpAdminString (SIZE  (0..32))
    MAX-ACCESS      read-write
    STATUS          current
    DESCRIPTION
        "This object specifies the name of the tertiary controller
        that the APs in the profile should associate with"
    ::= { cLApProfileEntry 23 }

cLApProfileTcpMss OBJECT-TYPE
    SYNTAX          Unsigned32 (536..1363)
    MAX-ACCESS      read-write
    STATUS          current
    DESCRIPTION
        "This object specifies the  AP TCP MSS value per AP profile.
        The permissible value are between 536 and 1363. This will
        also enable the global TCP MSS flag.
        Any change of value for this object will be reflected
        to cLApTcpMss"
    ::= { cLApProfileEntry 25 }

cLApProfileRetransmitCount OBJECT-TYPE
    SYNTAX          Unsigned32 (3..8)
    UNITS           "retries"
    MAX-ACCESS      read-write
    STATUS          current
    DESCRIPTION
        "This object specifies the retransmission count for the
        control packet for all APs associated to this particular AP
        profile. This value represents the number of packets 
        retransmitted after which the Access Point falls back to 
        another controller in case of failover."
    ::= { cLApProfileEntry 26 }

cLApProfileRetransmitTimeout OBJECT-TYPE
    SYNTAX          Unsigned32 (2..5)
    UNITS           "seconds"
    MAX-ACCESS      read-write
    STATUS          current
    DESCRIPTION
        "This object specifies the retransmission timeout for the
        control packet for all APs associated to this particular AP
        profile. This value represents the timeout for each 
        control Packet of all the Access Points, joined to this 
        retransmission, during the fallback of Access Point to 
        another controller in case of failover."
    ::= { cLApProfileEntry 27 }

cLApProfileOeapDisableLocalAccess OBJECT-TYPE
    SYNTAX          TruthValue
    MAX-ACCESS      read-write
    STATUS          deprecated
    DESCRIPTION
        "This object specifies whether the local access is supported for
        all the Office Extended Access Points associated to current AP
        Profile. If set to true, the local SSID and and LAN ports on
        the OEAP will be disabled." 
    ::= { cLApProfileEntry 28 }

cLApProfileLedState OBJECT-TYPE
    SYNTAX          TruthValue
    MAX-ACCESS      read-write
    STATUS          current
    DESCRIPTION
        "This object specifies whether the LED state of all the
        access points associated to a profile should be enabled or
        disabled."
    ::= { cLApProfileEntry 29 }

cLApProfileRadioInterfaceShutdownEnabled OBJECT-TYPE
    SYNTAX          TruthValue
    MAX-ACCESS      read-write
    STATUS          deprecated
    DESCRIPTION
        "This object allows the user to enable or disable radio
        interface of all the APs associated to current AP Profile.
        When enabled, AP radio's will be shut down when ethernet link 
        goes down for a duration of time set for
        cLApProfileEthernetInterfaceDowntime. 
        A value of 'true' indicates the AP radio interface shutdown is
        enabled.
        A value of 'false' indicates the AP radio interface shutdown is
        disabled." 
    ::= { cLApProfileEntry 30 }

cLApProfileEthernetInterfaceDowntime OBJECT-TYPE
    SYNTAX          Unsigned32
    UNITS           "Seconds"
    MAX-ACCESS      read-write
    STATUS          deprecated
    DESCRIPTION
        "This object specifies the ethernet interface down time after
        which the AP radio interface will be shut down for Aps in a
        profile." 
    ::= { cLApProfileEntry 31 }

cLApProfileMulticastGroupAddressType OBJECT-TYPE
    SYNTAX          InetAddressType
    MAX-ACCESS      read-write
    STATUS          current
    DESCRIPTION
        "This object specifies the AP multicast group address type."
    ::= { cLApProfileEntry 32 }

cLApProfileMulticastGroupAddress OBJECT-TYPE
    SYNTAX          InetAddress
    MAX-ACCESS      read-write
    STATUS          current
    DESCRIPTION
        "This object specifies the IPv6 multicast group address of all
        the APs associated to current AP Profile."
    ::= { cLApProfileEntry 33 }

cLApProfileMulticastMode OBJECT-TYPE
    SYNTAX          INTEGER {
                        unicast(1),
                        multicast(2)
                    }
    MAX-ACCESS      read-write
    STATUS          current
    DESCRIPTION
        "This object specifies the ethernet multicast support of all 
        the APs associated to current AP Profile.
        unicast - Controller will convert multicast to
                   unicast packet.
        multicast - Multicast mode is enabled."
    ::= { cLApProfileEntry 34 }

cLApProfilePrimedJoinTimeout OBJECT-TYPE
    SYNTAX          Unsigned32 (0..43200)
    UNITS           "seconds"
    MAX-ACCESS      read-write
    STATUS          current
    DESCRIPTION
        "This object specifies the primed timeout for the AP
        discovery for a given profile."
    ::= { cLApProfileEntry 35 }

cLApProfilePreferMode OBJECT-TYPE
    SYNTAX          INTEGER {
                        unconfig(1),
                        ipv4(2),
                        ipv6(3)
                    }
    MAX-ACCESS      read-write
    STATUS          current
    DESCRIPTION
        "This object specifies the capwap tunnel prefer-mode for all APs
        associated to this particular AP Profile.
        unconfig - capwap tunnel is not established.
        ipv4 - capwap tunnel established with ipv4 address.
        ipv6 - capwap tunnel established with ipv6 address." 
    ::= { cLApProfileEntry 36 }

cLApProfileApLagEnabled OBJECT-TYPE
    SYNTAX          TruthValue
    MAX-ACCESS      read-write
    STATUS          current
    DESCRIPTION
        "This object specifies the ap-lag capability state of all the 
        APs associated to current AP profile.
        A value of 'true' indicates the ap-lag capability state is
        enabled.
        A value of 'false' indicates the ap-lag capability state is
        disabled."
    ::= { cLApProfileEntry 37 }

cLApProfile802dot1xAuthenticationEnabled OBJECT-TYPE
    SYNTAX          TruthValue
    MAX-ACCESS      read-write
    STATUS          deprecated
    DESCRIPTION
        "This object represents the 802.1x supplicant authentication
        feature of APs associated to current AP Profile.
        If configured as True, user can configure 8021.1x 
        authentication between lightweight access points and the 
        switch. The access point acts as an 802.1x supplicant and is 
        authenticated by the switch using EAP-FAST with anonymous 
        PAC provisioning.User can set global authentication settings 
        that all access points inherit as they join the controller. 
        This includes all access points that are currently joined to 
        the controller and any that join in the future. If desired, 
        user can override the global authentication settings and 
        assign unique authentication settings for a specific 
        access point."
    DEFVAL          { false } 
    ::= { cLApProfileEntry 38 }

cLApProfile802dot1xSupplicantUsername OBJECT-TYPE
    SYNTAX          SnmpAdminString (SIZE  (0..32))
    MAX-ACCESS      read-write
    STATUS          current
    DESCRIPTION
        "This object represents the 802.1x supplicant username that
        is to be inherited by all the APs associated to current AP
        Profile." 
    ::= { cLApProfileEntry 39 }

cLApProfile802dot1xSupplicantPassword OBJECT-TYPE
    SYNTAX          SnmpAdminString (SIZE  (0..32))
    MAX-ACCESS      read-write
    STATUS          current
    DESCRIPTION
        "This object represents the 802.1x supplicant Password that
        is to be inherited by all the APs associated to current AP
        Profile. 
        A query on this OID will always return '****'." 
    ::= { cLApProfileEntry 40 }

cLApProfileEncryptionEnable OBJECT-TYPE
    SYNTAX          TruthValue
    MAX-ACCESS      read-write
    STATUS          current
    DESCRIPTION
        "This object specifies whether encyrption between
        controller and AP is enabled or not in a profile. Encryption
        can only be enabled if ESM card in controller is 
        pluged in.

        A value of 'true' enables encryption between 
        controller and AP.

        A value of 'false' disables encryption between 
        controller and AP."
    DEFVAL          { false }
    ::= { cLApProfileEntry 41 }

cLApProfileTelnetEnable OBJECT-TYPE
    SYNTAX          TruthValue
    MAX-ACCESS      read-write
    STATUS          current
    DESCRIPTION
        "This object specifies whether Telnet session
        can be established to the APs in a given AP profile. 

        A value of 'true' indicates an Telnet session
        can be established to the APs in a given AP profile. 

        A value of 'false' indicates an Telnet session
        cannot be established to the APs in a given AP profile."
    DEFVAL          { false }
    ::= { cLApProfileEntry 42 }

cLApProfileSshEnable OBJECT-TYPE
    SYNTAX          TruthValue
    MAX-ACCESS      read-write
    STATUS          current
    DESCRIPTION
        "This object specifies whether SSH session
        can be established to the APs asscoaited to an AP Profile.

        A value of 'true' indicates an SSH session
        can be established to the APs asscoaited to AP an Profile.

        A value of 'false' indicates an SSH session
        cannot be established to the APs asscoaited to an AP Profile."
    DEFVAL          { false }
    ::= { cLApProfileEntry 43 }

cLApProfileHyperlocationEnable OBJECT-TYPE
    SYNTAX          TruthValue
    MAX-ACCESS      read-write
    STATUS          current
    DESCRIPTION
        "This object represents the admin status of Hyperlocation.
        A value of 'true' indicates that Hyperlocation is enabled.
        A value of 'false' indicates that Hyperlocation is disabled."
    DEFVAL          { false }
    ::= { cLApProfileEntry 44 }

cLApProfileHyperlocationDetectionThreshold OBJECT-TYPE
    SYNTAX          Integer32 (-100..-50)
    UNITS           "dBm"
    MAX-ACCESS      read-write
    STATUS          current
    DESCRIPTION
        "This object represents the value of the Hyperlocation
        detection threshold expressed in dBm. Valid range is
        -100 dbm to -50 dbm."
    DEFVAL          { -100 }
    ::= { cLApProfileEntry 45 }

cLApProfileHyperlocationResetThreshold OBJECT-TYPE
    SYNTAX          Unsigned32 (0..99)
    MAX-ACCESS      read-write
    STATUS          current
    DESCRIPTION
        "This object represents the value of the Hyperlocation
        reset threshold expressed in scan cycles. Valid range is
        0 to 99 scan cycles. Its value must always be smaller
        than the trigger threshold."
    DEFVAL          { 8 }
    ::= { cLApProfileEntry 46 }

cLApProfileHyperlocationTriggerThreshold OBJECT-TYPE
    SYNTAX          Unsigned32 (1..100)
    MAX-ACCESS      read-write
    STATUS          current
    DESCRIPTION
        "This object represents the value of the Hyperlocation
        trigger threshold expressed in scan cycles. Valid range
        is 1 to 100 scan cycles."
    DEFVAL          { 10 }
    ::= { cLApProfileEntry 47 }

cLApProfileHyperlocationNtpIpAddressType OBJECT-TYPE
    SYNTAX          InetAddressType
    MAX-ACCESS      read-write
    STATUS          current
    DESCRIPTION
        "This object represents the NTP server IP address type
        configured for Hyperlocation feature."
    ::= { cLApProfileEntry 48 }

cLApProfileHyperlocationNtpIpAddress OBJECT-TYPE
    SYNTAX          InetAddress
    MAX-ACCESS      read-write
    STATUS          current
    DESCRIPTION
        "This object represents the NTP server IP address
        configured for Hyperlocation feature."
    ::= { cLApProfileEntry 49 }

cLApProfileAdjustMss OBJECT-TYPE
    SYNTAX          TruthValue
    MAX-ACCESS      read-write
    STATUS          current
    DESCRIPTION
        "To enable the TCP MSS flag"
    DEFVAL          { false }
    ::= { cLApProfileEntry 50 }

cLApProfileDiscoveryTimeout OBJECT-TYPE
    SYNTAX          Unsigned32 (1..10)
    UNITS           "seconds"
    MAX-ACCESS      read-write
    STATUS          current
    DESCRIPTION
        "This object represents the timeout for the AP
        discovery for a particular AP profile."
    DEFVAL          { 10 }
    ::= { cLApProfileEntry 51 }

cLApProfileHeartBeatTimeout OBJECT-TYPE
    SYNTAX          Unsigned32 (1..30)
    UNITS           "seconds"
    MAX-ACCESS      read-write
    STATUS          current
    DESCRIPTION
        "This object represents the Heart beat timeout for the APs in 
        a particular AP profile."
    DEFVAL          { 30 }
    ::= { cLApProfileEntry 52 }

cLApProfileCdpEnable OBJECT-TYPE
    SYNTAX          TruthValue
    MAX-ACCESS      read-write
    STATUS          current
    DESCRIPTION
        "This object specifies to  enable the CDP for all APs 
        associated to particular AP Profile"
    DEFVAL          { false }
    ::= { cLApProfileEntry 53 }

cLApProfileApPacketCaptureProfile OBJECT-TYPE
    SYNTAX          SnmpAdminString (SIZE  (0..32))
    MAX-ACCESS      read-write
    STATUS          current
    DESCRIPTION
        "This object represents the AP packet capture profile
        name mapped to this AP join profile. Access Points in this
        AP join profile will use the parameters of packet capture 
        profile"
    ::= { cLApProfileEntry 54 }

cLApProfileRogueReportInterval OBJECT-TYPE
    SYNTAX          Unsigned32 (10..300)
    UNITS           "seconds"
    MAX-ACCESS      read-write
    STATUS          current
    DESCRIPTION
        "This object specifies the rogue report interval,
        which is the interval that monitor mode APs send
        rogue detection details to the controller.
        This value is valid only for the current AP Profile."
    ::= { cLApProfileEntry 55 }

cLApProfileRogueMinimumRssi OBJECT-TYPE
    SYNTAX          Integer32 (-128..-70)
    UNITS           "dBm"
    MAX-ACCESS      read-write
    STATUS          current
    DESCRIPTION
        "This object specifies the minimum value of RSSI
        considered for detection of rogues.
        This value is valid only for the current AP Profile."
    ::= { cLApProfileEntry 56 }

cLApProfileRogueTransientInterval OBJECT-TYPE
    SYNTAX          Unsigned32 (0 | 120..1800)
    MAX-ACCESS      read-write
    STATUS          current
    DESCRIPTION
        "This object specifies the rogue transient
        interval for this AP Profile.

        A value of '0' specifies that an AP sends
        rogue detection details to the controller
        as soon as it detects a rogue.

        A non-zero value specifies that an AP sends
        rogue detection details to the controller if
        it hears the rogue more than once in the specified
        interval."
    DEFVAL          { 0 }
    ::= { cLApProfileEntry 57 }

cLApProfileRogueContainFlexconnect OBJECT-TYPE
    SYNTAX          TruthValue
    MAX-ACCESS      read-write
    STATUS          current
    DESCRIPTION
        "This object specifies whether Rogue containment of
        standalone flexconnect APs is enabled in this AP Profile.
        A value of 'true' enables rogue containment.
        A value of 'false' disables rogue containment."
    DEFVAL          { false }
    ::= { cLApProfileEntry 58 }

cLApProfileRogueContainAutoRateEnable OBJECT-TYPE
    SYNTAX          TruthValue
    MAX-ACCESS      read-write
    STATUS          current
    DESCRIPTION
        "This object specifies whether Rogue containment auto-rate
        is enabled in this AP Profile.
        A value of 'true' enables auto-rate.
        A value of 'false' disables auto-rate."
    DEFVAL          { false }
    ::= { cLApProfileEntry 59 }

cLApProfileRogueDetectionEnable OBJECT-TYPE
    SYNTAX          TruthValue
    MAX-ACCESS      read-write
    STATUS          current
    DESCRIPTION
        "This object specifies whether Rogue Detection
        is enabled in this AP Profile.
        A value of 'true' enables Rogue Detection.
        A value of 'false' disables Rogue Detection.
        Rogue detection is not supported on sniffer
        and rogue detector mode APs."
    DEFVAL          { true }
    ::= { cLApProfileEntry 60 }

cLApProfileReportInterval24ghz OBJECT-TYPE
    SYNTAX          Integer32 (5..90)
    UNITS           "seconds"
    MAX-ACCESS      read-write
    STATUS          current
    DESCRIPTION
        "This object specifies the interval at which APs
        connected will send client statitics for 802.11b radio for a
        particular AP profile."
    DEFVAL          { 90 }
    ::= { cLApProfileEntry 61 }

cLApProfileReportInterval5ghz OBJECT-TYPE
    SYNTAX          Integer32 (5..90)
    UNITS           "seconds"
    MAX-ACCESS      read-write
    STATUS          current
    DESCRIPTION
        "This object specifies the interval at which APs
        connected will send client statitics for 802.11a radio for a
        particular AP profile"
    DEFVAL          { 90 }
    ::= { cLApProfileEntry 62 }

cLApProfileDot1xApSwitchEapAuth OBJECT-TYPE
    SYNTAX          INTEGER {
                        eapNone(1),
                        eapFast(2),
                        eapTls(3),
                        peap(4)
                    }
    MAX-ACCESS      read-write
    STATUS          current
    DESCRIPTION
        "This object specifies Dot1x EAP type
        in this AP Profile."
    ::= { cLApProfileEntry 63 }

cLApProfileDot1xApSwtichLscAuth OBJECT-TYPE
    SYNTAX          INTEGER {
                        authNone(1),
                        authCapwapDtls(2),
                        authDot1xPort(3),
                        authBoth(4)
                    }
    MAX-ACCESS      read-write
    STATUS          current
    DESCRIPTION
        "This object specifies Dot1x LSC AP Auth
        type in this AP Profile."
    ::= { cLApProfileEntry 64 }

cLApProfileMeshProfileName OBJECT-TYPE
    SYNTAX          SnmpAdminString (SIZE  (1..32))
    MAX-ACCESS      read-write
    STATUS          current
    DESCRIPTION
        "This object uniquely identifies a mesh profile in a
        particular AP profile."
    ::= { cLApProfileEntry 65 }

cLApProfileUsbStatus OBJECT-TYPE
    SYNTAX          TruthValue
    MAX-ACCESS      read-write
    STATUS          current
    DESCRIPTION
        "This object specifies USB status(enable/disable) to be applied
        to all APs belonging to this AP join profile."
    DEFVAL          { true }
    ::= { cLApProfileEntry 66 }

cLApProfileVlanTagging OBJECT-TYPE
    SYNTAX          TruthValue
    MAX-ACCESS      read-write
    STATUS          deprecated
    DESCRIPTION
        "This object specifies whether the Vlan tagging of all the APs
        associated to current AP Profile should be enabled or disabled."
    DEFVAL          { false } 
    ::= { cLApProfileEntry 67 }

cLApProfileApCountryCode OBJECT-TYPE
    SYNTAX          SnmpAdminString (SIZE  (0..32))
    MAX-ACCESS      read-write
    STATUS          deprecated
    DESCRIPTION
        "This object represents the AP country code mapped to this
        AP join profile." 
    ::= { cLApProfileEntry 68 }


cLApProfileExtModuleEnable OBJECT-TYPE
    SYNTAX          TruthValue
    MAX-ACCESS      read-write
    STATUS          current
    DESCRIPTION
        "This object specifies whether extended module
        is enabled in this AP Profile.
        A value of 'true' enables extended module.
        A value of 'false' disables extended module."
    ::= { cLApProfileEntry 69 }

cLApProfileStatsTimer OBJECT-TYPE
    SYNTAX          Unsigned32 (0..65535)
    UNITS           "seconds"
    MAX-ACCESS      read-write
    STATUS          current
    DESCRIPTION
        "This object specifies the duration of the
        stats timer value in seconds."
    DEFVAL          { 180 }
    ::= { cLApProfileEntry 70 }

cLApProfilePoePreStandardSwitchFlag OBJECT-TYPE
    SYNTAX          TruthValue
    MAX-ACCESS      read-write
    STATUS          current
    DESCRIPTION
        "This object specifies whether the Pre-standard
        switch state as PoE option.
        A value of 'true' enables Pre-standard switch.
        A value of 'false' disables Pre-standard switch."
    ::= { cLApProfileEntry 71 }

cLApProfilePoePowerInjectorSelection OBJECT-TYPE
    SYNTAX          INTEGER {
                        unknown(1),
                        installed(2),
                        override(3)
                    }
    MAX-ACCESS      read-write
    STATUS          current
    DESCRIPTION
        "This object specifies the Power over Ethernet (PoE) injector
        state for all the APs associated to current AP profile.
        A value of '1' represents the state of PoE injector is unknown.
        A value of '2' represents the state of PoE injector is 
        installed.
        A value of '3' represents the state of PoE injector is 
        override."
    ::= { cLApProfileEntry 72 }

cLApProfilePoeInjectorSwitchMac OBJECT-TYPE
    SYNTAX          MacAddress
    MAX-ACCESS      read-write
    STATUS          current
    DESCRIPTION
        "This object represents the MAC address of the
        switch port that has a Power injector."
    ::= { cLApProfileEntry 73 }

cLApProfileHaloBleBeaconAdvertisedPwr OBJECT-TYPE
    SYNTAX          Unsigned32 (40..100)
    UNITS           "dBm"
    MAX-ACCESS      read-write
    STATUS          current
    DESCRIPTION
        "This object specifies the Power for HALO BLE beacon
        advertisement."
    DEFVAL          { 59 }
    ::= { cLApProfileEntry 74 }

cLApProfileTftpDownGradeAddressType OBJECT-TYPE
    SYNTAX          InetAddressType
    MAX-ACCESS      read-write
    STATUS          current
    DESCRIPTION
        "This object represents the TFTP servers
        address type in use."
    ::= { cLApProfileEntry 75 }

cLApProfileTftpDownGradeAddress OBJECT-TYPE
    SYNTAX          InetAddress
    MAX-ACCESS      read-write
    STATUS          current
    DESCRIPTION
        "This object represents the TFTP servers
        IP address."
    ::= { cLApProfileEntry 76 }

cLApProfileTftpDownGradeFileName OBJECT-TYPE
    SYNTAX          SnmpAdminString (SIZE  (0..32))
    MAX-ACCESS      read-write
    STATUS          current
    DESCRIPTION
        "This object represents the AP image downgrade
        file name on the TFTP server."
    ::= { cLApProfileEntry 77 }

cLApProfileCoreDumpType OBJECT-TYPE
    SYNTAX          INTEGER {
                        uncompress(1),
                        compress(2),
                        disable(3)
                    }
    MAX-ACCESS      read-write
    STATUS          current
    DESCRIPTION
        "This object specifies whether coredump is enabled and
        whether it is in compress or uncompress.
        A value of '1' represents uncompressed form of core dump file.
        A value of '2' represents compressed form of core dump file.
        A value of '3' disables the coredump."
    ::= { cLApProfileEntry 78 }

cLApProfileCoreDumpTftpAddressType OBJECT-TYPE
    SYNTAX          InetAddressType
    MAX-ACCESS      read-write
    STATUS          current
    DESCRIPTION
        "This object represents the TFTP server address type used
        for AP core dump transfer."
    ::= { cLApProfileEntry 79 }

cLApProfileCoreDumpTftpAddress OBJECT-TYPE
    SYNTAX          InetAddress
    MAX-ACCESS      read-write
    STATUS          current
    DESCRIPTION
        "This object represents the TFTP server address used for AP
        core dump transfer."
    ::= { cLApProfileEntry 80 }

cLApProfileCoreDumpCoreFileName OBJECT-TYPE
    SYNTAX          SnmpAdminString (SIZE  (0..32))
    MAX-ACCESS      read-write
    STATUS          current
    DESCRIPTION
        "This object represents core dump file name
        on the TFTP server."
    ::= { cLApProfileEntry 81 }

cLApProfileBackupFallbackEnabled OBJECT-TYPE
    SYNTAX          TruthValue
    MAX-ACCESS      read-write
    STATUS          current
    DESCRIPTION
        "This object represents fallback status of APs asscoaited 
        to an AP Profile.
        A value of 'true' represents AP fallback enabled.
        A value of 'false' represents AP fallback disabled."
    ::= { cLApProfileEntry 82 }

cLApProfileClientRssiStatsEnabled OBJECT-TYPE
    SYNTAX          TruthValue
    MAX-ACCESS      read-write
    STATUS          current
    DESCRIPTION
        "This object represents the status of Client RSSI 
        statistics from Access Point.
        A value of 'true' represents Client RSSI statistics reporting from 
        AP is enabled.
        A value of 'false' represents Client RSSI statistics reporting from 
        AP is disabled."
    DEFVAL          { true }
    ::= { cLApProfileEntry 83 }

cLApProfileClientRssiStatsReportInterval OBJECT-TYPE
    SYNTAX          Unsigned32 (30..300)
    UNITS           "seconds"
    MAX-ACCESS      read-write
    STATUS          current
    DESCRIPTION
        "This object represents Client RSSI statistics reporting interval
         value in seconds."
    DEFVAL          { 30 }
    ::= { cLApProfileEntry 84 }

cLApProfileGasRateLimitEnable OBJECT-TYPE
    SYNTAX          TruthValue
    MAX-ACCESS      read-write
    STATUS          current
    DESCRIPTION
        "This object represents the GAS limit status of APs associated
        to an AP Profile.
        A value of 'true' represents AP GAS limit enabled.
        A value of 'false' represents AP GAS disabled."
    ::= { cLApProfileEntry 85 }

cLApProfileGasRateLimitNumReqPerInterval OBJECT-TYPE
    SYNTAX          INTEGER (1..100)
    UNITS           "packets"
    MAX-ACCESS      read-write
    STATUS          current
    DESCRIPTION
        "This object specifies the maximum number of GAS messages
        per interval."
    ::= { cLApProfileEntry 86 }

cLApProfileGasRateLimitIntervalMsec OBJECT-TYPE
    SYNTAX          INTEGER (100..10000)
    UNITS           "milliseconds"
    MAX-ACCESS      read-write
    STATUS          current
    DESCRIPTION
        "This object specifies the interval for GAS message limit."
    ::= { cLApProfileEntry 87 }

cLApProfileQoSMapApTrustsUpstreamDSCP OBJECT-TYPE
    SYNTAX          TruthValue
    MAX-ACCESS      read-write
    STATUS          current
    DESCRIPTION
        "This object specifies whether the APs associated
        with an AP Profile use the upstream/received DSCP
        for outer CAPWAP tunnel QoS marking instead of
        802.11 User Priority.
        A value of 'true' represents using the upstream DSCP.
        A value of 'false' represents not using the upstream DSCP."
    ::= { cLApProfileEntry 88 }

cLApProfileUdpliteState OBJECT-TYPE
    SYNTAX          INTEGER {
                        unconfig(1),
                        udpliteenabled(2),
                        udplitedisabled(3)
                    }
    MAX-ACCESS      read-write
    STATUS          current
    DESCRIPTION
        "This object specifies the capwap tunnel ipv6 UDP-Lite checksum type
        for all APs associated to this particular AP Profile.
        unconfig - capwap tunnel is not established.
        udplite_enabled  - capwap tunnel established with ipv6 udplite
                           checksum enabled for data port.
        udplite_disabled - capwap tunnel established with ipv6 checksum." 
    ::= { cLApProfileEntry 89 }

cLApProfileMethodListName OBJECT-TYPE
    SYNTAX          SnmpAdminString
    MAX-ACCESS      read-write
    STATUS          current
    DESCRIPTION
        "This object specifies the method list used for the AP 
        accounting"
    ::= { cLApProfileEntry 90 }

cLApProfileWindowSize OBJECT-TYPE
    SYNTAX          INTEGER (1..50)
    MAX-ACCESS      read-write
    STATUS          current
    DESCRIPTION
        "This object specifies the capwap window size for 
        capwap multiwindow"
    ::= { cLApProfileEntry 91 }

cLApProfileCredentialGlobalSecretType OBJECT-TYPE
    SYNTAX          INTEGER {
                        clear(0),
                        aes(8)
                    }
    MAX-ACCESS      read-write
    STATUS          current
    DESCRIPTION
        "This object specifies the secret password type corresponding to
        the secret password type represented by cLApProfileCredentialGlobalSecret
        object."

    ::= { cLApProfileEntry 92 }


cLApProfileCredentialGlobalPasswordType OBJECT-TYPE
    SYNTAX          INTEGER {
                        clear(0),
                        aes(8)
                    }
    MAX-ACCESS      read-write
    STATUS          current
    DESCRIPTION
         "This object specifies the secret password type corresponding to
         the secret password type represented by cLApProfileCredentialGlobalSecret
         object."

    ::= { cLApProfileEntry 93 }

cLApProfile802dot1xSupplicantPasswordType OBJECT-TYPE
    SYNTAX          INTEGER {
                        clear(0),
                        aes(8)
                    }
    MAX-ACCESS      read-write
    STATUS          current
    DESCRIPTION
        "This object specifies the dot1xSupplicant password type corresponding to
         the dot1xSupplicantPassword represented by 
         cLApProfile802dot1xSupplicantPassword object."

    ::= { cLApProfileEntry 94 }

cLApProfileBssidEnableStats OBJECT-TYPE
    SYNTAX          TruthValue
    MAX-ACCESS      read-write
    STATUS          current
    DESCRIPTION
        "This object specifies whether the BSSID stats feature
         is enabled or disabled per ap config profile
         - A value of 'true' represents the BSSID stats as enabled.
         - A Value of 'false' represents the BSSID stats as disabled."

    ::= { cLApProfileEntry 95 }

cLApProfileBssidStatsFrequency OBJECT-TYPE
    SYNTAX         INTEGER
    MAX-ACCESS      read-write
    STATUS          current
    DESCRIPTION
        "This object specifies the BSSID stats frequency set on the AP for 
         sending the stats in the current AP profile"

    ::= { cLApProfileEntry 96 }

cLApProfilePersistentSsidBroadcastEnable OBJECT-TYPE
    SYNTAX          TruthValue
    MAX-ACCESS      read-write
    STATUS          current
    DESCRIPTION
        "This object specifies whether persistent SSID broadcast 
         is enabled or disabled per ap config profile
         - A value of 'true' represents persistent SSID broadcast is enabled.
         - A Value of 'false' represents persistent SSID broadcast is disabled." 

    ::= { cLApProfileEntry 97 }


cLApProfileDhcpFallback OBJECT-TYPE
    SYNTAX          TruthValue
    MAX-ACCESS      read-write
    STATUS          current
    DESCRIPTION
        "This object specifies whether the AP fallback to DHCP 
         is enabled or disabled per ap config profile
         - A value of 'true' represents that AP moves to DHCP if it fails to join controller via static IP.
         - A Value of 'false' represents that AP will not to DHCP if it fails to join controller via static IP." 

    ::= { cLApProfileEntry 98 }

cLApProfileOeapRogueDetectionEnable OBJECT-TYPE
    SYNTAX          TruthValue
    MAX-ACCESS      read-write
    STATUS          current
    DESCRIPTION

        "This object specifies whether Rogue Detection
        is enabled for OEAP.
        A value of 'true' indicates rogue detection is enabled.
        A value of 'false' indicates rogue detection is disabled."
    DEFVAL          { false } 

    ::= { cLApProfileEntry 99 }


cLApProfileOeapEncryptionEnable OBJECT-TYPE
    SYNTAX          TruthValue
    MAX-ACCESS      read-write
    STATUS          current
    DESCRIPTION

        "This object specifies whether encyrption between
        controller and OEAP is enabled or not in a profile.

        A value of 'true' enables encryption between
        controller and AP.

        A value of 'false' disables encryption between
        controller and AP."

    DEFVAL          { true }
    ::= { cLApProfileEntry 100 }


cLApProfileOeapLocalAccessEnable OBJECT-TYPE
    SYNTAX          TruthValue
    MAX-ACCESS      read-write
    STATUS          current
    DESCRIPTION

        "This object specifies Personal SSID
        broadcast

        A value of 'true' enables local access of
        AP Webui

        A value of 'false' disables local access of
        AP Webui."

    DEFVAL          { true }
    ::= { cLApProfileEntry 101 }


cLApProfileOeapProvSsidEnable OBJECT-TYPE
    SYNTAX          TruthValue
    MAX-ACCESS      read-write
    STATUS          current
    DESCRIPTION

        "This object specifies Provisional SSID
        broadcast

        A value of 'true' enables broadcast of
        Provisional SSID

        A value of 'false' disables broadcast of
        Provisional SSID."

    DEFVAL          { false }
    ::= { cLApProfileEntry 102 }

cLApProfileCountryCode OBJECT-TYPE 
    SYNTAX          INTEGER {                                          
      ae(1),
      al(2),
      ar(3),
      at(4),
      au(5),
      ba(6),
      bb(7),
      bd(8),
      be(9),
      bg(10),
      bh(11),
      bm(12),
      bn(13),
      bo(14),
      br(15),
      belarus(16),
      ca(17),
      ch(18),
      cl(19),
      cm(20),
      cn(21),
      co(22),
      cr(23),
      cu(24),
      cy(25),
      cz(26),
      de(27),
      dk(28),
      do(29),
      dz(30),
      ec(31),
      ee(32),
      eg(33),
      el(34),
      es(35),
      fi(36),
      fj(37),
      fr(38),
      gb(39),
      gh(40),
      gi(41),
      gr(42),
      hk(43),
      hr(44),
      hu(45),
      id(46),
      ie(47),
      il(48),
      in(49),
      io(50),
      iq(51),
      is(52),
      it(53),
      j2(54),
      j4(55),
      jm(56),
      jo(57),
      ke(58),
      kn(59),
      kw(60),
      kz(61),
      lb(62),
      li(63),
      lk(64),
      lt(65),
      lu(66),
      lv(67),
      ly(68),
      ma(69),
      mc(70),
      me(71),
      mk(72),
      mn(73),
      mo(74),
      mt(75),
      mx(76),
      my(77),
      ng(78),
      nl(79),
      no(80),
      nz(81),
      om(82),
      pa(83),
      pe(84),
      ph(85),
      pk(86),
      pl(87),
      pr(88),
      pt(89),
      py(90),
      qa(91),
      ro(92),
      rs(93),
      ru(94),
      sa(95),
      se(96),
      sg(97),
      si(98),
      sk(99),
      th(100),
      ti(101),
      tn(102),
      tr(103),
      tw(104),
      ua(105),
      us(106),
      uy(107),
      ve(108),
      vn(109),
      za(110),
      unconfigured(111)
    }
                                                                         
    MAX-ACCESS      read-write                                          
    STATUS          current                                             
    DESCRIPTION                                                         
        "This object specifies the country code for all APs             
        associated to this particular AP Profile."
    ::= { cLApProfileEntry 103 }

-- *********************************************************************
-- * Halo BLE Configuration
-- *********************************************************************

cLApProfileHaloBleBeaconTable OBJECT-TYPE
    SYNTAX          SEQUENCE OF CLApProfileHaloBleBeaconEntry
    MAX-ACCESS      not-accessible
    STATUS          current
    DESCRIPTION
        "This table represents an instance of HALO BLE configuration per
        AP profile. It lists the HALO BLE beacon parameters which are 
        common for HALO enabled APs that have joined the controller 
        under the same AP profile."
    ::= { ciscoLwappApProfile 2 }

cLApProfileHaloBleBeaconEntry OBJECT-TYPE
    SYNTAX          CLApProfileHaloBleBeaconEntry
    MAX-ACCESS      not-accessible
    STATUS          current
    DESCRIPTION
        "This entry contains an instance of HALO BLE beacon 
        configuration for a specific AP profile. It lists the HALO BLE 
        beacon ID, UUID, transmission power, and status per beacon for
        HALO enabled APs of a particular AP profile that have joined the
        controller"
    INDEX           {
                        cLApProfileName,
                        cLApProfileHaloBleBeaconId
                    }
    ::= { cLApProfileHaloBleBeaconTable 1 }

CLApProfileHaloBleBeaconEntry ::= SEQUENCE {
        cLApProfileHaloBleBeaconId         Unsigned32,
        cLApProfileHaloBleBeaconUuid       SnmpAdminString,
        cLApProfileHaloBleBeaconTxPower    Unsigned32,
        cLApProfileHaloBleBeaconEnabled    TruthValue,
        cLApProfileHaloBleBeaconRowStatus  RowStatus
}

cLApProfileHaloBleBeaconId OBJECT-TYPE
    SYNTAX          Unsigned32 (0..4)
    MAX-ACCESS      not-accessible
    STATUS          current
    DESCRIPTION
        "This object represents HALO BLE beacon ID for which BLE
        configuration to be applied."
    ::= { cLApProfileHaloBleBeaconEntry 1 }

cLApProfileHaloBleBeaconUuid OBJECT-TYPE
    SYNTAX          SnmpAdminString (SIZE  (0..128))
    MAX-ACCESS      read-write
    STATUS          current
    DESCRIPTION
        "This object represents HALO BLE beacon UUID (universally
        unique identifier) which is a 128-bit value."
    ::= { cLApProfileHaloBleBeaconEntry 2 }

cLApProfileHaloBleBeaconTxPower OBJECT-TYPE
    SYNTAX          Unsigned32 (0..52)
    UNITS           "dBm"
    MAX-ACCESS      read-write
    STATUS          current
    DESCRIPTION
        "This object represents HALO BLE beacon transmission power.
        The transmission power is based on the size of the required
        proximity zone."
    ::= { cLApProfileHaloBleBeaconEntry 3 }

cLApProfileHaloBleBeaconEnabled OBJECT-TYPE
    SYNTAX          TruthValue
    MAX-ACCESS      read-write
    STATUS          current
    DESCRIPTION
        "This object specifies the status of HALO BLE beacon.
        true(1) - enable the HALO BLE beacon,
        false(2) - disable the HALO BLE beacon."
    ::= { cLApProfileHaloBleBeaconEntry 4 }

cLApProfileHaloBleBeaconRowStatus OBJECT-TYPE
    SYNTAX          RowStatus
    MAX-ACCESS      read-create
    STATUS          current
    DESCRIPTION
        "This object specifies the row to be added or
        deleted in this table."
    ::= { cLApProfileHaloBleBeaconEntry 5 }

-- *********************************************************************
-- * Hotspot 2.0 QoS Map Configuration
-- *********************************************************************

cLApProfileQosMapRangeTable OBJECT-TYPE
    SYNTAX          SEQUENCE OF CLApProfileQosMapRangeEntry
    MAX-ACCESS      not-accessible
    STATUS          current
    DESCRIPTION
        "This table represents an instance of QoS Map configuration per
        AP profile. It lists the QoS Map DSCP-to-User Priority ranges
        which are common for APs that have joined the controller under
        the same AP profile."
    ::= { ciscoLwappApProfile 3 }

cLApProfileQosMapRangeEntry OBJECT-TYPE
    SYNTAX          CLApProfileQosMapRangeEntry
    MAX-ACCESS      not-accessible
    STATUS          current
    DESCRIPTION
        "This entry contains an instance of QoS Map configuration for
        a specific AP profile. It lists the QoS Map DSCP lower range,
        DSCP upper range, 802.11 User Priority and default DSCP
        for upstream User Priority for APs of a particular AP profile
        that have joined the controller"
    INDEX           {
                        cLApProfileName,
                        cLApProfileQosMapRangeUP
                    }
    ::= { cLApProfileQosMapRangeTable 1 }

CLApProfileQosMapRangeEntry ::= SEQUENCE {
        cLApProfileQosMapRangeUP        INTEGER,
        cLApProfileQosMapRangeDSCPLower INTEGER,
        cLApProfileQosMapRangeDSCPUpper INTEGER,
        cLApProfileQosMapRangeUPToDSCP  INTEGER,
        cLApProfileQosMapRangeRowStatus RowStatus
}

cLApProfileQosMapRangeUP OBJECT-TYPE
    SYNTAX          INTEGER (0..7)
    MAX-ACCESS      not-accessible
    STATUS          current
    DESCRIPTION
        "This object represents the 802.11 User Priority
        for which the DSCP-to-User Priority range
        configuration is applied."
    ::= { cLApProfileQosMapRangeEntry 1 }

cLApProfileQosMapRangeDSCPLower OBJECT-TYPE
    SYNTAX          INTEGER (0..63)
    MAX-ACCESS      read-create
    STATUS          current
    DESCRIPTION
        "This object represents the DSCP lower range
        for which the DSCP-to-User Priority range configuration
        is applied on the AP using an AP profile."
    ::= { cLApProfileQosMapRangeEntry 2 }

cLApProfileQosMapRangeDSCPUpper OBJECT-TYPE
    SYNTAX          INTEGER (0..63)
    MAX-ACCESS      read-create
    STATUS          current
    DESCRIPTION
        "This object represents the DSCP upper range
        for which the DSCP-to-User Priority range configuration
        is applied on the AP using an AP profile."
    ::= { cLApProfileQosMapRangeEntry 3 }

cLApProfileQosMapRangeUPToDSCP OBJECT-TYPE
    SYNTAX          INTEGER (0..63)
    MAX-ACCESS      read-create
    STATUS          current
    DESCRIPTION
        "This object represents the DSCP value which should
        be used for the upstream 802.11 User Priority
        on the AP using an AP profile."
    ::= { cLApProfileQosMapRangeEntry 4 }

cLApProfileQosMapRangeRowStatus OBJECT-TYPE
    SYNTAX          RowStatus
    MAX-ACCESS      read-create
    STATUS          current
    DESCRIPTION
        "This object specifies the row to be added or
        deleted in this table."
    ::= { cLApProfileQosMapRangeEntry 5 }


cLApProfileQosMapExceptionTable OBJECT-TYPE
    SYNTAX          SEQUENCE OF CLApProfileQosMapExceptionEntry
    MAX-ACCESS      not-accessible
    STATUS          current
    DESCRIPTION
        "This table represents an instance of QoS Map configuration per
        AP profile. It lists the QoS Map DSCP-to-User Priority
        exceptions which are common for APs that have joined the
        controller under the same AP profile."
    ::= { ciscoLwappApProfile 4 }

cLApProfileQosMapExceptionEntry OBJECT-TYPE
    SYNTAX          CLApProfileQosMapExceptionEntry
    MAX-ACCESS      not-accessible
    STATUS          current
    DESCRIPTION
        "This table represents an instance of QoS Map configuration per
        AP profile. It lists the QoS Map DSCP-to-User Priority
        exceptions which are common for APs that have joined the
        controller under the same AP profile."
    INDEX           {
                        cLApProfileName,
                        cLApProfileQosMapExceptionDSCP
                    }
    ::= { cLApProfileQosMapExceptionTable 1 }

CLApProfileQosMapExceptionEntry ::= SEQUENCE {
        cLApProfileQosMapExceptionDSCP      INTEGER,
        cLApProfileQosMapExceptionUP        INTEGER,
        cLApProfileQosMapExceptionRowStatus RowStatus
}

cLApProfileQosMapExceptionDSCP OBJECT-TYPE
    SYNTAX          INTEGER (0..63)
    MAX-ACCESS      not-accessible
    STATUS          current
    DESCRIPTION
        "This object represents the DSCP value for the DSCP to 802.11
        User Priority mapping exception for the APs that joined
        the controller under the same AP profile."
    ::= { cLApProfileQosMapExceptionEntry 1 }

cLApProfileQosMapExceptionUP OBJECT-TYPE
    SYNTAX          INTEGER (0..7)
    MAX-ACCESS      read-create
    STATUS          current
    DESCRIPTION
        "This object represents the 802.11 User Priority value for the
        DSCP to 802.11 User Priority mapping exception for the APs that
        joined the controller under the same AP profile."
    ::= { cLApProfileQosMapExceptionEntry 2 }

cLApProfileQosMapExceptionRowStatus OBJECT-TYPE
    SYNTAX          RowStatus
    MAX-ACCESS      read-create
    STATUS          current
    DESCRIPTION
        "This object specifies the row to be added or
        deleted in this table."
    ::= { cLApProfileQosMapExceptionEntry 3 }

-- *********************************************************************
-- * AP Packet Capture Profile Configuration
-- *********************************************************************

cLApPacketCaptureProfileTable OBJECT-TYPE
    SYNTAX          SEQUENCE OF CLApPacketCaptureProfileEntry
    MAX-ACCESS      not-accessible
    STATUS          current
    DESCRIPTION
        "This table provides the information about the packet capture
        parameters for the 802.11 LWAPP Access Points.
        Rows are added to this table whenever, new profiles
        are added to this controller, and rows are deleted
        whenever profiles gets deleted from the controller."
    ::= { ciscoLwappApPacketCapture 1 }

cLApPacketCaptureProfileEntry OBJECT-TYPE
    SYNTAX          CLApPacketCaptureProfileEntry
    MAX-ACCESS      not-accessible
    STATUS          current
    DESCRIPTION
        "Each entry in this table provides information about the packet
        capture profile configured on the controller."
    INDEX           { cLApPacketCaptureProfileName }
    ::= { cLApPacketCaptureProfileTable 1 }

CLApPacketCaptureProfileEntry ::= SEQUENCE {
        cLApPacketCaptureProfileName                 SnmpAdminString,
        cLApPacketCaptureProfileRowStatus            RowStatus,
        cLApPacketCaptureProfileBufferSize           Unsigned32,
        cLApPacketCaptureProfileDuration             Unsigned32,
        cLApPacketCaptureProfileTruncation           Unsigned32,
        cLApPacketCaptureProfileFtpServerAddressType InetAddressType,
        cLApPacketCaptureProfileFtpServerAddress     InetAddress,
        cLApPacketCaptureProfileFtpServerPath        SnmpAdminString,
        cLApPacketCaptureProfileFtpUsername          SnmpAdminString,
        cLApPacketCaptureProfileFtpPassword          SnmpAdminString,
        cLApPacketCaptureProfileClassifierArp        TruthValue,
        cLApPacketCaptureProfileClassifierBroadcast  TruthValue,
        cLApPacketCaptureProfileClassifierControl    TruthValue,
        cLApPacketCaptureProfileClassifierData       TruthValue,
        cLApPacketCaptureProfileClassifierDot1x      TruthValue,
        cLApPacketCaptureProfileClassifierIapp       TruthValue,
        cLApPacketCaptureProfileClassifierIp         TruthValue,
        cLApPacketCaptureProfileClassifierManagement TruthValue,
        cLApPacketCaptureProfileClassifierMulticast  TruthValue,
        cLApPacketCaptureProfileClassifierTcp        TruthValue,
        cLApPacketCaptureProfileClassifierUdp        TruthValue,
        cLApPacketCaptureProfileClassifierTcpPort    InetPortNumber,
        cLApPacketCaptureProfileClassifierUdpPort    InetPortNumber
}

cLApPacketCaptureProfileName OBJECT-TYPE
    SYNTAX          SnmpAdminString (SIZE  (0..32))
    MAX-ACCESS      not-accessible
    STATUS          current
    DESCRIPTION
        "This object represents the profile name for
        ap packet capture profile. The parameters of
        packet capture profile are used while capturing packets
        on the Access Point for the specified wireless client."
    ::= { cLApPacketCaptureProfileEntry 1 }

cLApPacketCaptureProfileRowStatus OBJECT-TYPE
    SYNTAX          RowStatus
    MAX-ACCESS      read-create
    STATUS          current
    DESCRIPTION
        "Used to add or delete an entry in this table."
    ::= { cLApPacketCaptureProfileEntry 2 }

cLApPacketCaptureProfileBufferSize OBJECT-TYPE
    SYNTAX          Unsigned32 (1024..4096)
    UNITS           "kilobytes"
    MAX-ACCESS      read-write
    STATUS          current
    DESCRIPTION
        "This object specifies the size of the buffer Access Point
        should use to copy the captured packets for client and dump
        it to the FTP server."
    DEFVAL          { 2048 }
    ::= { cLApPacketCaptureProfileEntry 3 }

cLApPacketCaptureProfileDuration OBJECT-TYPE
    SYNTAX          Unsigned32 (1..60)
    UNITS           "Minutes"
    MAX-ACCESS      read-write
    STATUS          current
    DESCRIPTION
        "This object specifies the duration for which the Access Point
        should capture packets for specified client."
    DEFVAL          { 10 }
    ::= { cLApPacketCaptureProfileEntry 4 }

cLApPacketCaptureProfileTruncation OBJECT-TYPE
    SYNTAX          Unsigned32 (0..1500)
    UNITS           "bytes"
    MAX-ACCESS      read-write
    STATUS          current
    DESCRIPTION
        "This object specifies the length of the packet after
        truncation while capturing packets on the Access Point.
        Default value is 0 which indictaes captured packet should
        contain the full payload length."
    ::= { cLApPacketCaptureProfileEntry 5 }

cLApPacketCaptureProfileFtpServerAddressType OBJECT-TYPE
    SYNTAX          InetAddressType
    MAX-ACCESS      read-write
    STATUS          current
    DESCRIPTION
        "This object specifies the type of the ftp server
        IP Address made available through
        cLApPacketCaptureProfileEntry."
    ::= { cLApPacketCaptureProfileEntry 6 }

cLApPacketCaptureProfileFtpServerAddress OBJECT-TYPE
    SYNTAX          InetAddress
    MAX-ACCESS      read-write
    STATUS          current
    DESCRIPTION
        "This object specifies the IP Address of the
        FTP server. Access Point will dump the captured packets
        to a file in this ftp server."
    ::= { cLApPacketCaptureProfileEntry 7 }

cLApPacketCaptureProfileFtpServerPath OBJECT-TYPE
    SYNTAX          SnmpAdminString
    MAX-ACCESS      read-write
    STATUS          current
    DESCRIPTION
        "This object specifies the directory path in the
        ftp server for storing the file which contains the 
        captured packets in the Access Point."
    ::= { cLApPacketCaptureProfileEntry 8 }

cLApPacketCaptureProfileFtpUsername OBJECT-TYPE
    SYNTAX          SnmpAdminString
    MAX-ACCESS      read-write
    STATUS          current
    DESCRIPTION
        "This object specifies the username to login into
        the ftp server in order to transfer the captured 
        packets from the Access Point."
    ::= { cLApPacketCaptureProfileEntry 9 }

cLApPacketCaptureProfileFtpPassword OBJECT-TYPE
    SYNTAX          SnmpAdminString
    MAX-ACCESS      read-write
    STATUS          current
    DESCRIPTION
        "This object specifies the password to login into
        the ftp server in order to transfer the captured
        packets from the Access Point."
    ::= { cLApPacketCaptureProfileEntry 10 }

cLApPacketCaptureProfileClassifierArp OBJECT-TYPE
    SYNTAX          TruthValue
    MAX-ACCESS      read-write
    STATUS          current
    DESCRIPTION
        "This object specifies the filters for ARP packets
        while capturing packets on the Access Point.
        A value of 'true' indicates ARP packets should be captured.
        A value of 'false' indicates ARP packets shouldn't be captured."
    DEFVAL          { false }
    ::= { cLApPacketCaptureProfileEntry 11 }

cLApPacketCaptureProfileClassifierBroadcast OBJECT-TYPE
    SYNTAX          TruthValue
    MAX-ACCESS      read-write
    STATUS          current
    DESCRIPTION
        "This object specifies the filters for 802.11 Broadcast
        packets, while capturing packets on the Access Point.
        A value of 'true' indicates Broadcast packets should be
        captured.
        A value of 'false' indicates Broadcast packets should not be
        captured."
    DEFVAL          { false }
    ::= { cLApPacketCaptureProfileEntry 12 }

cLApPacketCaptureProfileClassifierControl OBJECT-TYPE
    SYNTAX          TruthValue
    MAX-ACCESS      read-write
    STATUS          current
    DESCRIPTION
        "This object specifies the filters for 802.11 control packets,
        while capturing packets on the Access Point under AP Profile 
        which is making use of this packet capture profile.

        A value of 'true' indicates 802.11 control packets should be
        captured.
        A value of 'false' indicates 802.11 control packets should not
        be captured."
    DEFVAL          { true }
    ::= { cLApPacketCaptureProfileEntry 13 }

cLApPacketCaptureProfileClassifierData OBJECT-TYPE
    SYNTAX          TruthValue
    MAX-ACCESS      read-write
    STATUS          current
    DESCRIPTION
        "This object specifies the filters for 802.11 Data packets,
        while capturing packets on the Access Point under AP Profile
        which is making use of this packet capture profile. 

        A value of 'true' indicates 802.11 Data packets should be
        captured.
        A value of 'false' indicates 802.11 Data packets should not be
        captured."
    DEFVAL          { false }
    ::= { cLApPacketCaptureProfileEntry 14 }

cLApPacketCaptureProfileClassifierDot1x OBJECT-TYPE
    SYNTAX          TruthValue
    MAX-ACCESS      read-write
    STATUS          current
    DESCRIPTION
        "This object specifies the filters for 802.11 Dot1x packets,
        while capturing packets on the Access Point under AP Profile 
        which is making use of this packet capture profile.
        A value of 'true' indicates 802.11 Dot1x packets should be 
        captured.
        A value of 'false' indicates 802.11 Dot1x packets should
        not be captured."
    DEFVAL          { false }
    ::= { cLApPacketCaptureProfileEntry 15 }

cLApPacketCaptureProfileClassifierIapp OBJECT-TYPE
    SYNTAX          TruthValue
    MAX-ACCESS      read-write
    STATUS          current
    DESCRIPTION
        "This object specifies the filters for 802.11 IAPP packets,
        while capturing packets on the Access Point under AP Profile
        which is making use of this packet capture profile.
        A value of 'true' indicates IAPP packets should be captured.
        A value of 'false' indicates IAPP packets should
        not be captured."
    DEFVAL          { false }
    ::= { cLApPacketCaptureProfileEntry 16 }

cLApPacketCaptureProfileClassifierIp OBJECT-TYPE
    SYNTAX          TruthValue
    MAX-ACCESS      read-write
    STATUS          current
    DESCRIPTION
        "This object specifies the filters for IP packets,
        while capturing packets on the Access Point. 
       A value of 'true' indicates IP packets should be captured. 
       A value of 'false' indicates IP packets should not be captured."
    DEFVAL          { false }
    ::= { cLApPacketCaptureProfileEntry 17 }

cLApPacketCaptureProfileClassifierManagement OBJECT-TYPE
    SYNTAX          TruthValue
    MAX-ACCESS      read-write
    STATUS          current
    DESCRIPTION
        "This object specifies the filters for 802.11 Management
        packets, while capturing packets on the Access Point. A value
        of 'true' indicates 802.11 Management packets should be
        captured.
        A value of 'false' indicates 802.11 Management packets should
        not be captured."
    DEFVAL          { true }
    ::= { cLApPacketCaptureProfileEntry 18 }

cLApPacketCaptureProfileClassifierMulticast OBJECT-TYPE
    SYNTAX          TruthValue
    MAX-ACCESS      read-write
    STATUS          current
    DESCRIPTION
        "This object specifies the filters for 802.11 Multicast
        packets, while capturing packets on the Access Point.
        A value of 'true' indicates Multicast packets should be
        captured.
       A value of 'false' indicates Multicast packets should not be 
       captured."
    DEFVAL          { false }
    ::= { cLApPacketCaptureProfileEntry 19 }

cLApPacketCaptureProfileClassifierTcp OBJECT-TYPE
    SYNTAX          TruthValue
    MAX-ACCESS      read-write
    STATUS          current
    DESCRIPTION
        "This object specifies the filters for TCP packets,
        while capturing packets on the Access Point.
        Value of 'true' indicates IP packets should be captured.
        Value of 'false' indicates IP packets should not be captured."
    DEFVAL          { false }
    ::= { cLApPacketCaptureProfileEntry 20 }

cLApPacketCaptureProfileClassifierUdp OBJECT-TYPE
    SYNTAX          TruthValue
    MAX-ACCESS      read-write
    STATUS          current
    DESCRIPTION
        "This object specifies the filters for TCP packets,
        while capturing packets on the Access Point.
        Value of 'true' indicates IP packets should be captured.
        Value of 'false' indicates IP packets should not be captured."
    DEFVAL          { false }
    ::= { cLApPacketCaptureProfileEntry 21 }

cLApPacketCaptureProfileClassifierTcpPort OBJECT-TYPE
    SYNTAX          InetPortNumber (0..65535)
    MAX-ACCESS      read-write
    STATUS          current
    DESCRIPTION
        "This object specifies the filter value port number for TCP
        packets, while capturing packets on the Access Point.
        Default value is 0 which indicates all TCP packets should
        be captured."
    DEFVAL          { 0 }
    ::= { cLApPacketCaptureProfileEntry 22 }

cLApPacketCaptureProfileClassifierUdpPort OBJECT-TYPE
    SYNTAX          InetPortNumber (0..65535)
    MAX-ACCESS      read-write
    STATUS          current
    DESCRIPTION
        "This object specifies the filter value port number for UDP
        packets, while capturing packets on the Access Point under AP 
        Profile which is making use of this packet capture profile.
        Default value is 0 which indicates all UDP packets should
        be captured."
    DEFVAL          { 0 }
    ::= { cLApPacketCaptureProfileEntry 23 }
 

-- *********************************************************************
-- * AP Packet Capture Client Table
-- *********************************************************************

cLApPacketCaptureClientTable OBJECT-TYPE
    SYNTAX          SEQUENCE OF CLApPacketCaptureClientEntry
    MAX-ACCESS      not-accessible
    STATUS          current
    DESCRIPTION
        "This table provides information about the status of
        packet capture already in progress on per Client basis.
        Rows are added to this table whenever, packet capture is
        started for a new client, and rows are deleted whenever 
        packet capture gets stopped for a particular Client."
    ::= { ciscoLwappApPacketCapture 2 }

cLApPacketCaptureClientEntry OBJECT-TYPE
    SYNTAX          CLApPacketCaptureClientEntry
    MAX-ACCESS      not-accessible
    STATUS          current
    DESCRIPTION
        "Each entry in this table provides information about packet 
        capture session currently going on for a client on  802.11 
        LWAPP Access Point that has joined the controller."
    INDEX           { cLApPacketCaptureClientDeviceMac }
    ::= { cLApPacketCaptureClientTable 1 }

CLApPacketCaptureClientEntry ::= SEQUENCE {
        cLApPacketCaptureClientDeviceMac    MacAddress,
        cLApPacketCaptureClientApMacAddress MacAddress,
        cLApPacketCaptureClientAutoMode     TruthValue,
        cLApPacketCaptureClientStartStop    INTEGER,
        cLApPacketCaptureClientSiteName     SnmpAdminString,
        cLApPacketCaptureClientRowStatus    RowStatus
}

cLApPacketCaptureClientDeviceMac OBJECT-TYPE
    SYNTAX          MacAddress
    MAX-ACCESS      not-accessible
    STATUS          current
    DESCRIPTION
        "This object represents the mac address of the client for
        which packet capture should be started on the Access Point.
        Access Point will check for this mac address
        while capturing packets." 
    ::= { cLApPacketCaptureClientEntry 1 }

cLApPacketCaptureClientApMacAddress OBJECT-TYPE
    SYNTAX          MacAddress
    MAX-ACCESS      read-write
    STATUS          current
    DESCRIPTION
        "This object represents the base radio mac address
        of the Access Point on which packet capture should
        be started. This will be used only in case of static mode
        but, it is mandatory to populate this in static mode as well." 
    ::= { cLApPacketCaptureClientEntry 2 }

cLApPacketCaptureClientAutoMode OBJECT-TYPE
    SYNTAX          TruthValue
    MAX-ACCESS      read-write
    STATUS          current
    DESCRIPTION
        "This object specifies the mode for packet capture.
        A value of 'true' indicates packet capture should be started
        in auto mode, which means capture will be started on the
        Access Point on which device is currently connected and 
        also on the nearby Access Points which appear in the 
        RRM neighbor lists of present Access Point.
        A value of 'false' indicates packet capture should be
        started only on the specified Access Point." 
    ::= { cLApPacketCaptureClientEntry 3 }

cLApPacketCaptureClientStartStop OBJECT-TYPE
    SYNTAX          INTEGER  {
                        idle(1),
                        start(2),
                        stop(3)
                    }
    MAX-ACCESS      read-write
    STATUS          current
    DESCRIPTION
        "This object specifies the trigger to start or stop
        packet capture for the client.  A value of '1' 
        indicates packet capture should be started.  A value
        of '2' indicates packet capture should be stopped." 
    ::= { cLApPacketCaptureClientEntry 4 }

cLApPacketCaptureClientSiteName OBJECT-TYPE
    SYNTAX          SnmpAdminString (SIZE  (0..32))
    MAX-ACCESS      read-only
    STATUS          current
    DESCRIPTION
        "This object represents the name of the site on which the
        specific device or the Access Point is present." 
    ::= { cLApPacketCaptureClientEntry 5 }

cLApPacketCaptureClientRowStatus OBJECT-TYPE
    SYNTAX          RowStatus
    MAX-ACCESS      read-create
    STATUS          current
    DESCRIPTION
        "This oject specifies to the addition or deletion of an
        entry in this table. When an entry is added, packet 
        capture will be started for the specified device.
        When an entry is deleted, packet capture will be stopped
        for the specified device."
    ::= { cLApPacketCaptureClientEntry 6 }
 

-- *********************************************************************
-- * AP Packet Capture AP table
-- *********************************************************************

cLApPacketCaptureApTable OBJECT-TYPE
    SYNTAX          SEQUENCE OF CLApPacketCaptureApEntry 
    MAX-ACCESS      not-accessible
    STATUS          current
    DESCRIPTION
        "This table provides information about the status of
        packet capture already in progress on a per AP, per Client 
        basis. Rows are added to this table whenever, packet capture 
        is started for a client on a new AP, and rows are deleted 
        whenever packet capture gets stopped on a particular AP."
    ::= { ciscoLwappApPacketCapture 3 }

cLApPacketCaptureApEntry OBJECT-TYPE
    SYNTAX          CLApPacketCaptureApEntry
    MAX-ACCESS      not-accessible
    STATUS          current
    DESCRIPTION
        "Each entry in this table provides information about status of
        packet capture already in progress on the specific AP."
    INDEX           { cLApSysMacAddress }
    ::= { cLApPacketCaptureApTable 1 }

CLApPacketCaptureApEntry ::= SEQUENCE {
        cLApPacketCaptureApDeviceMac  MacAddress,
        cLApPacketCaptureApMacAddress MacAddress,
        cLApPacketCaptureApStatus     TruthValue
}

cLApPacketCaptureApDeviceMac OBJECT-TYPE
    SYNTAX          MacAddress
    MAX-ACCESS      read-only
    STATUS          current
    DESCRIPTION
        "This object specifies the mac address of the device for
        which packet capture was started on the Access Point.
        Access Point will check for this mac address
        while capturing packets."
    ::= { cLApPacketCaptureApEntry 1 }

cLApPacketCaptureApMacAddress OBJECT-TYPE
    SYNTAX          MacAddress
    MAX-ACCESS      read-only
    STATUS          current
    DESCRIPTION
        "This object specifies the base radio mac address of
        the Access Point on which packet capture was started for
        the specific device."
    ::= { cLApPacketCaptureApEntry 2 }

cLApPacketCaptureApStatus OBJECT-TYPE
    SYNTAX          TruthValue
    MAX-ACCESS      read-only
    STATUS          current
    DESCRIPTION
        "This object specifies the status of the packet capture.
        A value of 'true' indicates packet capture has been started
        for the specified device on the specific Access Point,
        A value of 'false' indicates packet capture is not started
        for the specified device on the specific Access Point."
    ::= { cLApPacketCaptureApEntry 3 }


--********************************************************************
-- *  Cisco 11ax Access Point Radio configuration Objects
--********************************************************************

cLAp11axRadioConfigTable OBJECT-TYPE
    SYNTAX         SEQUENCE OF CLAp11axRadioConfigEntry
    MAX-ACCESS     not-accessible
    STATUS         current
    DESCRIPTION
        "This table represents the radio configuration
        of 11ax Access Points"
    ::= { ciscoLwappAp11axRadioConfig 1 }

cLAp11axRadioConfigEntry OBJECT-TYPE
    SYNTAX         CLAp11axRadioConfigEntry
    MAX-ACCESS     not-accessible
    STATUS         current
    DESCRIPTION
        "Each entry in cLAp11axRadioConfigTable
        corresponds to an 11ax Access Point radio configuration."
    INDEX           { 
                        cLApSysMacAddress,
                        cLApDot11IfSlotId
                    }
    ::= { cLAp11axRadioConfigTable 1 }

CLAp11axRadioConfigEntry ::=SEQUENCE {
        cLAp11axDualRadioCapable         TruthValue,
        cLAp11axRadioFRACapable          TruthValue,
        cLAp11axDualRadioOperation       INTEGER,
        cLAp11axDualRadioMode            INTEGER,
        cLAp11axRadioRoleOperation       INTEGER,
        cLAp11axRadioRole                INTEGER,
        cLAp11axObssPdCapable            TruthValue,
        cLAp11axObssPdSrgCapable         TruthValue
}

cLAp11axDualRadioCapable OBJECT-TYPE
    SYNTAX          TruthValue 
    MAX-ACCESS      read-only
    STATUS          current
    DESCRIPTION
        "This object represents whether radio is dual radio capable or
        not.
        A value of 'true' indicates the radio is dual mode capable.
        A value of 'false' indicates the radio is not dual mode capable."
    ::= { cLAp11axRadioConfigEntry 1 }

cLAp11axRadioFRACapable OBJECT-TYPE
    SYNTAX          TruthValue
    MAX-ACCESS      read-only
    STATUS          current
    DESCRIPTION
        "This object represents whether radio is FRA capable or not.
        A value of 'true' indicates the radio is FRA Capable.
        A value of 'false' indicates the radio is not FRA capable."
    ::= { cLAp11axRadioConfigEntry 2 }

cLAp11axDualRadioOperation OBJECT-TYPE
    SYNTAX          INTEGER {
                        auto(1),
                        manual(2),
                        none(3)
                    }
    MAX-ACCESS      read-write
    STATUS          current
    DESCRIPTION
        "This object specifies dual radio mode operation of
        the slot.
        auto - Dual radio mode is automatic.
        manual - Dual radio mode is configurable manually.
        none - Radio is not dual radio mode capable."
    ::= { cLAp11axRadioConfigEntry 3 }

cLAp11axDualRadioMode OBJECT-TYPE
    SYNTAX          INTEGER {
                        enabled(1),
                        disabled(2),
                        none(3)
                    }
    MAX-ACCESS      read-write
    STATUS          current
    DESCRIPTION
        "This object specifies dual radio mode status of radio
        enabled - Dual radio mode is enabled.
        disabled- Dual radio mode is disabled.
        none - Radio is not dual radio mode capable."
    ::= { cLAp11axRadioConfigEntry 4 }

cLAp11axRadioRoleOperation OBJECT-TYPE
    SYNTAX          INTEGER {
                        auto(1),
                        manual(2),
                        none(3)
                    }
    MAX-ACCESS      read-write
    STATUS          current
    DESCRIPTION
        "This object specifies the radio role operation
        of the slot.
        auto - Radio role assignment is automatic.
        manual - Radio role assignment is manual.
        none - Radio role assignment is neither manual nor automatic."
    ::= { cLAp11axRadioConfigEntry 5 }

cLAp11axRadioRole OBJECT-TYPE
    SYNTAX          INTEGER {
                        clientserving(1),
                        monitor(2),
                        none(3)
                    }
    MAX-ACCESS      read-write
    STATUS          current
    DESCRIPTION
        "This object specifies the role for the slot.
        local - The means the slot is capable of serving clients.
        monitor - The slot does not serves client, only monitors.
        none - The slot is neither client serving nor monitor."
    ::= { cLAp11axRadioConfigEntry 6 }

cLAp11axObssPdCapable OBJECT-TYPE
    SYNTAX          TruthValue
    MAX-ACCESS      read-only
    STATUS          current
    DESCRIPTION
        "This object represents whether the radio is 802.11ax OBSS PD capable
        or not.
        A value of 'true' indicates the radio is OBSS PD capable.
        A value of 'false' indicates the radio is not OBSS PD capable."
    ::= { cLAp11axRadioConfigEntry 7 }

cLAp11axObssPdSrgCapable OBJECT-TYPE
    SYNTAX          TruthValue
    MAX-ACCESS      read-only
    STATUS          current
    DESCRIPTION
        "This object represents whether the radio is 802.11ax SRG OBSS PD capable
        or not.
        A value of 'true' indicates the radio is SRG OBSS PD capable.
        A value of 'false' indicates the radio is not SRG OBSS PD capable."
    ::= { cLAp11axRadioConfigEntry 8 }

-- ********************************************************************
-- *  Notification Objects
-- ********************************************************************

cLApAssocFailureReason OBJECT-TYPE
    SYNTAX          CLApAssocFailureReason
    MAX-ACCESS      accessible-for-notify
    STATUS          current
    DESCRIPTION
        "This object specifies the failure reasons when
        a AP fails to associate with a controller." 
    ::= { ciscoLwappApMIBNotifObjects 1 }

cLApRogueApMacAddress OBJECT-TYPE
    SYNTAX          MacAddress
    MAX-ACCESS      accessible-for-notify
    STATUS          current
    DESCRIPTION
        "This object represents the radio MAC address
        common to the dot11 interfaces of the rogue AP." 
    ::= { ciscoLwappApMIBNotifObjects 2 }

cLApDot11RadioChannelNumber OBJECT-TYPE
    SYNTAX          CLDot11Channel
    MAX-ACCESS      accessible-for-notify
    STATUS          current
    DESCRIPTION
        "This object represents the channel number of the
        radio interface of the AP, represented by 
        cLApDot11IfType." 
    ::= { ciscoLwappApMIBNotifObjects 3 }

cLApRogueApSsid OBJECT-TYPE
    SYNTAX          SnmpAdminString
    MAX-ACCESS      accessible-for-notify
    STATUS          current
    DESCRIPTION
        "This object represents the SSID used by the
        rogue AP to intrude the network." 
    ::= { ciscoLwappApMIBNotifObjects 4 }

cLApRogueType OBJECT-TYPE
    SYNTAX          INTEGER  {
                        asleap(1),
                        honeypot(2),
                        other(3)
                    }
    MAX-ACCESS      accessible-for-notify
    STATUS          current
    DESCRIPTION
        "This object represents the SSID of the used by the
        rogue AP to intrude the network." 
    ::= { ciscoLwappApMIBNotifObjects 5 }

cLApWipsReason OBJECT-TYPE
    SYNTAX          INTEGER  {
                        noMonitoringDevice(1)
                    }
    MAX-ACCESS      accessible-for-notify
    STATUS          current
    DESCRIPTION
        "This object specifies the failure reasons for an AP
        when cLApWipsEnable is set to 'true'.

        noMonitoringDevice - No monitoring device 
        connected to collect WIPs information." 
    ::= { ciscoLwappApMIBNotifObjects 6 }

cLApWipsClear OBJECT-TYPE
    SYNTAX          TruthValue
    MAX-ACCESS      accessible-for-notify
    STATUS          current
    DESCRIPTION
        "This object specifies whether this event is
        raise or clear.
        A value of 'true' indicates this event is cleared
        A value of 'false' indicates this even is raised." 
    ::= { ciscoLwappApMIBNotifObjects 7 }

cLApIfUpDownFailureType OBJECT-TYPE
    SYNTAX          INTEGER  {
                        detectedFailure(1),
                        configuredReset(2)
                    }
    MAX-ACCESS      accessible-for-notify
    STATUS          current
    DESCRIPTION
        "This object specifies the type of the
        AP interface failure.
        detectedFailure(1) - Failure of radio.
        configuredReset(2) - Reset due to manual 
                              configuration." 
    ::= { ciscoLwappApMIBNotifObjects 8 }

cLApIfUpDownCause OBJECT-TYPE
    SYNTAX          SnmpAdminString
    MAX-ACCESS      accessible-for-notify
    STATUS          current
    DESCRIPTION
        "This object specifies the cause of the
        AP interface failure." 
    ::= { ciscoLwappApMIBNotifObjects 9 }

cLApIfUpDownFailureCode OBJECT-TYPE
    SYNTAX          SnmpAdminString
    MAX-ACCESS      accessible-for-notify
    STATUS          current
    DESCRIPTION
        "This object specifies the code of the
        AP interface failure." 
    ::= { ciscoLwappApMIBNotifObjects 10 }

cLApAlarmSet OBJECT-TYPE
    SYNTAX          TruthValue
    MAX-ACCESS      accessible-for-notify
    STATUS          current
    DESCRIPTION
        "This object specifies whether this event is
        raise or clear.
        A value of 'true' indicates this event is set.
        A value of 'false' indicates this even is cleared." 
    ::= { ciscoLwappApMIBNotifObjects 11 }

cLApRogueClassType OBJECT-TYPE
    SYNTAX          INTEGER  {
                        pending(0),
                        friendly(1),
                        malicious(2),
                        unclassified(3),
                        custom(4)
                    }
    MAX-ACCESS      accessible-for-notify
    STATUS          current
    DESCRIPTION
        "This object specifies the AP class type of the
        Rogue AP detected." 
    ::= { ciscoLwappApMIBNotifObjects 12 }

cLApRogueDetectedChannel OBJECT-TYPE
    SYNTAX          CLDot11Channel
    MAX-ACCESS      accessible-for-notify
    STATUS          current
    DESCRIPTION
        "This object represents the rogue
        detected channel number." 
    ::= { ciscoLwappApMIBNotifObjects 13 }

cLApRSSI OBJECT-TYPE
    SYNTAX          Integer32
    MAX-ACCESS      accessible-for-notify
    STATUS          current
    DESCRIPTION
        "This object specifies the Rogue RSSI as seen by
        AP Interface." 
    ::= { ciscoLwappApMIBNotifObjects 14 }

cLApSNR OBJECT-TYPE
    SYNTAX          Integer32
    MAX-ACCESS      accessible-for-notify
    STATUS          current
    DESCRIPTION
        "This object specifies the SNR seen by AP
        Interface from Rogue" 
    ::= { ciscoLwappApMIBNotifObjects 15 }

cLApDot11RadioCurrentChannel OBJECT-TYPE
    SYNTAX          CLDot11Channel
    MAX-ACCESS      accessible-for-notify
    STATUS          current
    DESCRIPTION
        "This object represents the dot11
        current channel." 
    ::= { ciscoLwappApMIBNotifObjects 16 }

cLApAdhocRogue OBJECT-TYPE
    SYNTAX          TruthValue
    MAX-ACCESS      accessible-for-notify
    STATUS          current
    DESCRIPTION
        "This object represents the flag used to state if
        the rogue found is an Adhoc rogue or it is an AP." 
    ::= { ciscoLwappApMIBNotifObjects 17 }

cLApRogueAPOnWiredNetwork OBJECT-TYPE
    SYNTAX          TruthValue
    MAX-ACCESS      accessible-for-notify
    STATUS          current
    DESCRIPTION
        "This object represents the flag used to state if
        the rogue is found on the wired network.
        A value of '1' indicates Rogue AP is found on wired
        network.
        A value of '0' indicates Rogue AP is not found
        on wired network." 
    ::= { ciscoLwappApMIBNotifObjects 18 }

cLApRogueMode OBJECT-TYPE
    SYNTAX          INTEGER  {
                        initializing(0),
                        pending(1),
                        alert(2),
                        detectedLrad(3),
                        known(4),
                        acknowledge(5),
                        contained(6),
                        threat(7),
                        containedPending(8),
                        knownContained(9),
                        trustedMissing(10)
                    }
    MAX-ACCESS      accessible-for-notify
    STATUS          current
    DESCRIPTION
        "This attribute is use to specify the state in which
        the Rogue AP is user can set the Rogue AP in alert, 
        known or acknowledge state.

        Alert state means Rogue AP can be a potential threat,
        trap will be sent out to trap recipients. 

        Known state means its just internal AP which is not 
        on the same Switch.  

        Acknowledge state means an external AP whose
        existence is acceptable and not a threat (probably 
        some other company's AP).

        Contained means containement is initiated and ongoing.
        Threat is usually the state when the rogue is found 
        on wired network.

        known(4), knownContained(9) and trustedMissing(10) 
        will appear in known rogue list.
        known rogues can be pre provisioned and known rogues 
        state can be changed to alert(2)." 
    ::= { ciscoLwappApMIBNotifObjects 19 }

cLApRogueIsClassifiedByRule OBJECT-TYPE
    SYNTAX          TruthValue
    MAX-ACCESS      accessible-for-notify
    STATUS          current
    DESCRIPTION
        "This object represents the flag used to state if the
        rogue is classified by a rogue rule.
        A value of 'true' indicates its classifed by rogue rule.
        A value of 'false' indicates its not classified by rogue 
        rule." 
    ::= { ciscoLwappApMIBNotifObjects 20 }

cLApRogueClassifiedApMacAddress OBJECT-TYPE
    SYNTAX          MacAddress
    MAX-ACCESS      accessible-for-notify
    STATUS          current
    DESCRIPTION
        "This object represents the radio MAC address
        of the classified rogue AP." 
    ::= { ciscoLwappApMIBNotifObjects 21 }

cLApRogueClassifiedRSSI OBJECT-TYPE
    SYNTAX          Integer32
    MAX-ACCESS      accessible-for-notify
    STATUS          current
    DESCRIPTION
        "This object represents the Rogue classified RSSI as
        seen by Airespace AP Interface." 
    ::= { ciscoLwappApMIBNotifObjects 22 }

cLAPPreviousMonitorMode OBJECT-TYPE
    SYNTAX          CLApMode
    MAX-ACCESS      accessible-for-notify
    STATUS          current
    DESCRIPTION
        "This object represents the previous AP monitor Mode." 
    ::= { ciscoLwappApMIBNotifObjects 23 }

cLAPCurrentMonitorMode OBJECT-TYPE
    SYNTAX          CLApMode
    MAX-ACCESS      accessible-for-notify
    STATUS          current
    DESCRIPTION
        "This object represents the current AP monitor Mode." 
    ::= { ciscoLwappApMIBNotifObjects 24 }

cLApSsidKeyConfSsidA OBJECT-TYPE
    SYNTAX          SnmpAdminString
    MAX-ACCESS      accessible-for-notify
    STATUS          current
    DESCRIPTION
        "This object represents the SSID which has same
        cipher key with another SSID on the same AP.
        The another SSID is represented by cLApSsidKeyConfSsidB." 
    ::= { ciscoLwappApMIBNotifObjects 25 }

cLApSsidKeyConfKeyIdxA OBJECT-TYPE
    SYNTAX          Unsigned32
    MAX-ACCESS      accessible-for-notify
    STATUS          current
    DESCRIPTION
        "This object represents key index of the SSID which has same
        cipher key with another SSID on the same AP.
        It is the key index of cLApSsidKeyConfSsidA.
        The another SSID is represented by cLApSsidKeyConfSsidB." 
    ::= { ciscoLwappApMIBNotifObjects 26 }

cLApSsidKeyConfSsidB OBJECT-TYPE
    SYNTAX          SnmpAdminString
    MAX-ACCESS      accessible-for-notify
    STATUS          current
    DESCRIPTION
        "This object represents the SSID which has same
        cipher key with another SSID on the same AP.
        The another SSID is represented by cLApSsidKeyConfSsidA." 
    ::= { ciscoLwappApMIBNotifObjects 27 }

cLApSsidKeyConfKeyIdxB OBJECT-TYPE
    SYNTAX          Unsigned32
    MAX-ACCESS      accessible-for-notify
    STATUS          current
    DESCRIPTION
        "This object represents key index of the SSID which has same
        cipher key with another SSID on the same AP.
        It is the key index of cLApSsidKeyConfSsidB.
        The another SSID is represented by cLApSsidKeyConfSsidA." 
    ::= { ciscoLwappApMIBNotifObjects 28 }

cLApPreviousChannel OBJECT-TYPE
    SYNTAX          Unsigned32
    MAX-ACCESS      accessible-for-notify
    STATUS          current
    DESCRIPTION
        "This object represents the channel before changed." 
    ::= { ciscoLwappApMIBNotifObjects 29 }

cLApCurrentChannel OBJECT-TYPE
    SYNTAX          Unsigned32
    MAX-ACCESS      accessible-for-notify
    STATUS          current
    DESCRIPTION
        "This object represents the channel after changed." 
    ::= { ciscoLwappApMIBNotifObjects 30 }

cLApChannelCustomize OBJECT-TYPE
    SYNTAX          INTEGER  {
                        automatic(1),
                        customized(2)
                    }
    MAX-ACCESS      accessible-for-notify
    STATUS          current
    DESCRIPTION
        "This object represents the channel's change mode.
        If this value is true, then bsnAPDot11CurrentChannel in
        bsnAPIfDot11PhyDSSSTable is assigned by dynamic
        algorithm and is read-only." 
    ::= { ciscoLwappApMIBNotifObjects 31 }

cLApIfLoadChannelUtilization OBJECT-TYPE
    SYNTAX          Integer32 (0..65535)
    MAX-ACCESS      accessible-for-notify
    STATUS          current
    DESCRIPTION
        "This object specifies the code of the
        AP Interface channel load utilization." 
    ::= { ciscoLwappApMIBNotifObjects 32 }

cLAPGroupVlanName OBJECT-TYPE
    SYNTAX          OCTET STRING (SIZE  (0..255))
    MAX-ACCESS      accessible-for-notify
    STATUS          current
    DESCRIPTION
        "This object specifies the code of the
        AP Group Interface Name." 
    ::= { ciscoLwappApMIBNotifObjects 33 }

cLApRuleName OBJECT-TYPE
    SYNTAX          SnmpAdminString (SIZE  (1..32))
    MAX-ACCESS      accessible-for-notify
    STATUS          current
    DESCRIPTION
        "This object represents the rule name to identify
        applied on the Ap." 
    ::= { ciscoLwappApMIBNotifObjects 34 }

cLApSeverityScore OBJECT-TYPE
    SYNTAX          Unsigned32
    MAX-ACCESS      accessible-for-notify
    STATUS          current
    DESCRIPTION
        "This object is used to define the custom classification
        severity score of the rules.
        This object is applicable when cLRuleRogueType is configured
        as 'custom'." 
    ::= { ciscoLwappApMIBNotifObjects 35 }

cLApDot11XorRadioRoleChangeReason OBJECT-TYPE
    SYNTAX          INTEGER  {
                        none(1),
                        auto(2),
                        manual(3)
                    }
    MAX-ACCESS      accessible-for-notify
    STATUS          current
    DESCRIPTION
        "This object is used to identify the reason code for
        radio role change of XOR radio." 
    ::= { ciscoLwappApMIBNotifObjects 36 }

cLApDot11XorRadioBandChangeReason OBJECT-TYPE
    SYNTAX          INTEGER  {
                        none(1),
                        coverageHole(2),
                        hyperlocation(3),
                        revert(4),
                        fra(5),
                        manual(6)
                    }
    MAX-ACCESS      accessible-for-notify
    STATUS          current
    DESCRIPTION
        "This object is used to identify the reason code for
        radio band change of XOR radio." 
    ::= { ciscoLwappApMIBNotifObjects 37 }

cLApBrokenAntApName OBJECT-TYPE
         SYNTAX OCTET STRING (SIZE(0..32))
         MAX-ACCESS accessible-for-notify
         STATUS     current
         DESCRIPTION
             "This object represents the AP name of
              the trap with broken antenna info."
         ::= {  ciscoLwappApMIBNotifObjects 38 }

cLApBrokenAntInfo OBJECT-TYPE
         SYNTAX OCTET STRING (SIZE(0..32))
         MAX-ACCESS accessible-for-notify
         STATUS     current
         DESCRIPTION
             "This object represents the condition of
              antenna for a given AP. It denotes if
              AP antenna are broken or not; if broken, then which
              particular antenna (like ALL/A/B/C/D/AB/BC...) broken
              will be mentioned."
         ::= {  ciscoLwappApMIBNotifObjects 39 }

cLApRogueDot11RadioBand OBJECT-TYPE
    SYNTAX          CLDot11Band
    MAX-ACCESS      accessible-for-notify
    STATUS          current
    DESCRIPTION
        "This object represents the radio band of the Rouge AP."
    ::= { ciscoLwappApMIBNotifObjects 40 }
-- ********************************************************************
-- *  Notifications
-- ********************************************************************

ciscoLwappApIfRegulatoryDomainMismatchNotif NOTIFICATION-TYPE
    OBJECTS         {
                        cLApName,
                        cLApDot11IfType,
                        cLApDot11IfRegDomain,
                        cldRegulatoryDomain
                    }
    STATUS          current
    DESCRIPTION
        "This notification  is generated if an AP radio's regulatory
        domain doesn't match the country the controller is configured
        for.  Due to the mismatch, the AP will fail to associate with
        the controller."
   ::= { ciscoLwappApMIBNotifs 1 }

ciscoLwappApCrash NOTIFICATION-TYPE
    OBJECTS         { cLApName }
    STATUS          obsolete
    DESCRIPTION
        "This notification is generated after an AP rejoins the
        controller after  a crash. Once the AP joins, the controller
        will get the crash file from the AP and sends this 
        notification."
   ::= { ciscoLwappApMIBNotifs 2 }

ciscoLwappApUnsupported NOTIFICATION-TYPE
    OBJECTS         {
                        cLApName,
                        cLApAssocFailureReason
                    }
    STATUS          current
    DESCRIPTION
        "This notification is generated after an unsupported AP tries
        to join the controller."
   ::= { ciscoLwappApMIBNotifs 3 }

ciscoLwappApAssociated NOTIFICATION-TYPE
    OBJECTS         {
                        cLApName,
                        cLApLastRebootReason,
                        cLApDataEncryptionStatus
                    }
    STATUS          current
    DESCRIPTION
        "This notification is generated whenever an AP joins the
        controller successfully. This notification contains 
        information about the last reboot reason and Data 
        Encryption status of the AP."
   ::= { ciscoLwappApMIBNotifs 4 }

ciscoLwappApPower NOTIFICATION-TYPE
    OBJECTS         {
                        cLApName,
                        cLApPowerStatus
                    }
    STATUS          current
    DESCRIPTION
        "This notification is generated whenever an AP detects low
        power from Ethernet."
   ::= { ciscoLwappApMIBNotifs 5 }

ciscoLwappApRogueApDetected NOTIFICATION-TYPE
    OBJECTS         {
                        cLApSysMacAddress,
                        cLApName,
                        cLApRogueApMacAddress,
                        cLApEthernetIfSlotId,
                        cLApDot11IfType,
                        cLApDot11RadioChannelNumber,
                        cLApRogueApSsid,
                        cLApRogueType,
                        cLApRogueDot11RadioBand
                    }
    STATUS          current
    DESCRIPTION
        "This notification is generated whenever a rogue AP is
        detected."
   ::= { ciscoLwappApMIBNotifs 6 }

ciscoLwappApRogueApCleared NOTIFICATION-TYPE
    OBJECTS         {
                        cLApSysMacAddress,
                        cLApName,
                        cLApRogueApMacAddress,
                        cLApEthernetIfSlotId,
                        cLApDot11IfType,
                        cLApDot11RadioChannelNumber,
                        cLApRogueApSsid,
                        cLApRogueType,
                        cLApRogueDot11RadioBand
                    }
    STATUS          current
    DESCRIPTION
        "This notification is generated whenever a rogue AP was
        detected and then subsequently if its been removed from 
        the network."
   ::= { ciscoLwappApMIBNotifs 7 }

ciscoLwappApWipsNotification NOTIFICATION-TYPE
    OBJECTS         {
                        cLApName,
                        cLApWipsReason,
                        cLApWipsClear
                    }
    STATUS          current
    DESCRIPTION
        "This notification is generated whenever a controller
        detects a WIPS event."
   ::= { ciscoLwappApMIBNotifs 8 }

ciscoLwappApNoDownlinkChannelNotify NOTIFICATION-TYPE
    OBJECTS         { cLApName }
    STATUS          current
    DESCRIPTION
        "This notification is generated when ever AP fails to find
        new downlink channel."
   ::= { ciscoLwappApMIBNotifs 9 }

ciscoLwappApIfUpNotify NOTIFICATION-TYPE
    OBJECTS         {
                        cLApSysMacAddress,
                        cLApDot11IfSlotId,
                        cLApPortNumber,
                        cLApIfUpDownFailureType,
                        cLApIfUpDownCause,
                        cLApIfUpDownFailureCode,
                        cLApName
                    }
    STATUS          current
    DESCRIPTION
        "This notification is generated when AP's Interface
        operational status goes up."
   ::= { ciscoLwappApMIBNotifs 10 }

ciscoLwappApIfDownNotify NOTIFICATION-TYPE
    OBJECTS         {
                        cLApSysMacAddress,
                        cLApDot11IfSlotId,
                        cLApAdminStatus,
                        cLApDot11IfAdminStatus,
                        cLApIfUpDownFailureType,
                        cLApIfUpDownCause,
                        cLApIfUpDownFailureCode,
                        cLApName
                    }
    STATUS          current
    DESCRIPTION
        "This notification is generated when AP's Interface
        operational status goes down."
   ::= { ciscoLwappApMIBNotifs 11 }

ciscoLwappApClientThresholdNotify NOTIFICATION-TYPE
    OBJECTS         {
                        cLApSysMacAddress,
                        cLApName,
                        cLApDot11IfSlotId,
                        cLApDot11IfType,
                        cLRFProfileHighDensityMaxRadioClients,
                        cLRFProfileHDClientTrapThreshold
                    }
    STATUS          current
    DESCRIPTION
        "This notification is generated when the number of
        clients on the AP's Radio Interface exceeds
        the limit defined in cLRFProfileHDClientTrapThreshold."
   ::= { ciscoLwappApMIBNotifs 12 }

ciscoLwappApUpgradeFailureNotify NOTIFICATION-TYPE
    OBJECTS         {
                        cLApSysMacAddress,
                        cLApName,
                        cLApUpgradeFromVersion,
                        cLApUpgradeToVersion,
                        cLApUpgradeFailureCause
                    }
    STATUS          current
    DESCRIPTION
        "This notification is generated when AP image upgrade failed."
   ::= { ciscoLwappApMIBNotifs 13 }

ciscoLwappApCpuUsageHigh NOTIFICATION-TYPE
    OBJECTS         {
                        cLApSysMacAddress,
                        cLApName,
                        cLApCpuCurrentUsage,
                        cLApAlarmSet
                    }
    STATUS          current
    DESCRIPTION
        "This notification generates when an AP detects its
        CPU usage is higher than the threshold configured in 
        clsSysApCpuUsageThreshold, with cLApAlarmSet
        set to true. When this AP's CPU usage falls below
        the threshold lately, this notification is
        generated with cLApAlarmSet set to false."
   ::= { ciscoLwappApMIBNotifs 14 }

ciscoLwappApMemoryUsageHigh NOTIFICATION-TYPE
    OBJECTS         {
                        cLApSysMacAddress,
                        cLApName,
                        cLApMemoryCurrentUsage,
                        cLApAlarmSet
                    }
    STATUS          current
    DESCRIPTION
        "This notification generates when an AP detects its memory
        usage is higher than the threshold configured in 
        clsSysApMemoryUsageThreshold, with cLApAlarmSet
        set to true. When this AP's memory usage falls below
        the threshold lately, this notification is
        generated with cLApAlarmSet set to false."
   ::= { ciscoLwappApMIBNotifs 15 }

ciscoLwappApMaxClientLimitNotify NOTIFICATION-TYPE
    OBJECTS         {
                        cLApSysMacAddress,
                        cLApName,
                        cLApDot11IfSlotId,
                        cLApMaxClientLimitNumberTrap,
                        cLApMaxClientLimitCause,
                        cLApMaxClientLimitSet
                    }
    STATUS          current
    DESCRIPTION
        "This notification is generated when the event that
        max client limit reached is raised or cleared."
   ::= { ciscoLwappApMIBNotifs 16 }

ciscoLwappApAdjChannelRogueDetected NOTIFICATION-TYPE
    OBJECTS         {
                        cLApSysMacAddress,
                        cLApName,
                        cLApRogueApMacAddress,
                        cLApEthernetIfSlotId,
                        cLApDot11IfType,
                        cLApRogueDetectedChannel,
                        cLApRSSI,
                        cLApSNR,
                        cLApDot11RadioCurrentChannel,
                        cLApAdhocRogue,
                        cLApRogueApSsid,
                        cLApRogueClassType
                    }
    STATUS          current
    DESCRIPTION
        "This notification is generated whenever a rogue AP is
        detected at the Adjacent channels"
   ::= { ciscoLwappApMIBNotifs 17 }

ciscoLwappApAdjChannelRogueCleared NOTIFICATION-TYPE
    OBJECTS         {
                        cLApSysMacAddress,
                        cLApName,
                        cLApRogueApMacAddress,
                        cLApEthernetIfSlotId,
                        cLApDot11IfType,
                        cLApRogueDetectedChannel,
                        cLApDot11RadioCurrentChannel
                    }
    STATUS          current
    DESCRIPTION
        "This notification is generated whenever a rogue AP is
        detected at the Adjacent channels and then
        subsequently if its been removed from the network."
   ::= { ciscoLwappApMIBNotifs 18 }

ciscoLwappApRogueDetected NOTIFICATION-TYPE
    OBJECTS         {
                        cLApSysMacAddress,
                        cLApName,
                        cLApRogueApMacAddress,
                        cLApEthernetIfSlotId,
                        cLApDot11IfType,
                        cLApRogueDetectedChannel,
                        cLApRSSI,
                        cLApSNR,
                        cLApRogueAPOnWiredNetwork,
                        cLApAdhocRogue,
                        cLApRogueApSsid,
                        cLApRogueClassType,
                        cLApRogueMode,
                        cLApRogueIsClassifiedByRule,
                        cLApSeverityScore,
                        cLApRuleName,
                        cLApRogueClassifiedApMacAddress,
                        cLApRogueClassifiedRSSI,
                        cLApRogueDot11RadioBand
                    }
    STATUS          current
    DESCRIPTION
        "This notification is generated whenever a rogue AP is
        detected at the same channel."
   ::= { ciscoLwappApMIBNotifs 19 }

ciscoLwappApCurrentChannelRogueDetected NOTIFICATION-TYPE
    OBJECTS         {
                        cLApSysMacAddress,
                        cLApName,
                        cLApRogueApMacAddress,
                        cLApEthernetIfSlotId,
                        cLApDot11IfType,
                        cLApRogueDetectedChannel,
                        cLApRSSI,
                        cLApSNR,
                        cLApDot11RadioCurrentChannel,
                        cLApAdhocRogue,
                        cLApRogueApSsid,
                        cLApRogueClassType
                    }
    STATUS          current
    DESCRIPTION
        "This notification is generated whenever a rogue AP is
        detected at the Current channel."
   ::= { ciscoLwappApMIBNotifs 20 }

ciscoLwappApCurrentChannelRogueCleared NOTIFICATION-TYPE
    OBJECTS         {
                        cLApSysMacAddress,
                        cLApName,
                        cLApRogueApMacAddress,
                        cLApEthernetIfSlotId,
                        cLApDot11IfType,
                        cLApRogueDetectedChannel,
                        cLApDot11RadioCurrentChannel
                    }
    STATUS          current
    DESCRIPTION
        "This notification is generated whenever a rogue AP is
        detected at the Current channels and then
        subsequently if its been removed from the network."
   ::= { ciscoLwappApMIBNotifs 21 }

ciscoLwappApMonitorModeChangeNotify NOTIFICATION-TYPE
    OBJECTS         {
                        cLApSysMacAddress,
                        cLApName,
                        cLAPPreviousMonitorMode,
                        cLAPCurrentMonitorMode
                    }
    STATUS          current
    DESCRIPTION
        "This notification is generated when the event that
        AP monitor mode changed."
   ::= { ciscoLwappApMIBNotifs 22 }

ciscoLwappApAcTimeSyncFailureTrap NOTIFICATION-TYPE
    OBJECTS         {
                        cLApSysMacAddress,
                        cLApName
                    }
    STATUS          current
    DESCRIPTION
        "This notification is generated when the heartbeat between
        AP and Controller is lost or connection broken."
   ::= { ciscoLwappApMIBNotifs 23 }

ciscoLwappApSsidKeyConflict NOTIFICATION-TYPE
    OBJECTS         {
                        cLApSysMacAddress,
                        cLApIfMacAddress,
                        cLApSsidKeyConfSsidA,
                        cLApSsidKeyConfKeyIdxA,
                        cLApSsidKeyConfSsidB,
                        cLApSsidKeyConfKeyIdxB
                    }
    STATUS          current
    DESCRIPTION
        "This notification is generated whenever 2 SSIDs
        on same AP have same cipher key."
   ::= { ciscoLwappApMIBNotifs 24 }

ciscoLwappApCurrChannelChanged NOTIFICATION-TYPE
    OBJECTS         {
                        cLApSysMacAddress,
                        cLApName,
                        cLApDot11IfSlotId,
                        cLApPreviousChannel,
                        cLApCurrentChannel,
                        cLApChannelCustomize
                    }
    STATUS          current
    DESCRIPTION
        "This notification is generated when the channel is changed
        by automatic or customized."
   ::= { ciscoLwappApMIBNotifs 25 }

ciscoLwappApCapwapRetransmissionQueueFullEvent NOTIFICATION-TYPE
    OBJECTS         { cLApSysMacAddress }
    STATUS          current
    DESCRIPTION
        "This notification is generated whenever capwap retransmission
        queue for an AP is filled."
   ::= { ciscoLwappApMIBNotifs 26 }

ciscoLwappApSystemBootupEvent NOTIFICATION-TYPE
    OBJECTS         { cLApSysMacAddress }
    STATUS          current
    DESCRIPTION
        "This notification is generated whenever AP boots up."
   ::= { ciscoLwappApMIBNotifs 27 }

ciscoLwappXmFilterCheckWarning NOTIFICATION-TYPE
    OBJECTS         { cLApName }
    STATUS          current
    DESCRIPTION
        "This notification is generated whenever
        co-existence filter is not present"
   ::= { ciscoLwappApMIBNotifs 28 }

ciscoLwappApModeUnsupportedOnFlexExpressEvent NOTIFICATION-TYPE
    OBJECTS         { cLApSysMacAddress }
    STATUS          current
    DESCRIPTION
        "This notification is generated whenever ap with unsupported
        mode joins flexexpress wlc or virtual wlc"
   ::= { ciscoLwappApMIBNotifs 29 }

ciscoLwappApXorRadioRoleChangeNotify NOTIFICATION-TYPE
    OBJECTS         {
                        cLApSysMacAddress,
                        cLApName,
                        cLApDot11IfSlotId,
                        cLApDot11XorRadioBand,
                        cLApDot11XorRadioRoleChangeReason
                    }
    STATUS          current
    DESCRIPTION
        "This notification is generated whenever XOR radio of AP has
        changed its Radio role"
   ::= { ciscoLwappApMIBNotifs 30 }

ciscoLwappRadioBandChangeNotify NOTIFICATION-TYPE
    OBJECTS         {
                        cLApSysMacAddress,
                        cLApName,
                        cLApDot11IfSlotId,
                        cLApDot11XorRadioBand,
                        cLApDot11XorRadioBandChangeReason
                    }
    STATUS          current
    DESCRIPTION
        "This notification is generated whenever XOR radio of AP has
        changed its Band"
   ::= { ciscoLwappApMIBNotifs 31 }

ciscoLwappBrokenAntennaDetails NOTIFICATION-TYPE
     OBJECTS {
                 cLApBrokenAntApName,
                 cLApBrokenAntInfo
             }
     STATUS     current
     DESCRIPTION
             "This notification is generated whenever this AP sends the
              antenna details, if any got broken or not"
     ::= { ciscoLwappApMIBNotifs 33 }

ciscoLwappApRadioStuck NOTIFICATION-TYPE
     OBJECTS {
                 cLApSysMacAddress,
                 cLApName,
                 bsnStationAPIfSlotId,
             }
     STATUS     current
     DESCRIPTION
        "This notification generates when an AP detects that its
         radio is stuck"
     ::= { ciscoLwappApMIBNotifs 34 }

--**********************************************************************************
-- cLAPNtpInfoTable - NTP status for AP
--**********************************************************************************

cLAPNtpInfoTable  OBJECT-TYPE
    SYNTAX        SEQUENCE OF CLAPNtpInfoEntry
    MAX-ACCESS    not-accessible
    STATUS        current
    DESCRIPTION
        "This table represents collection of
         NTP-Server information received from AP."

    ::= { ciscoLwappApNtpInfo 1 }

cLAPNtpInfoEntry  OBJECT-TYPE
    SYNTAX        CLAPNtpInfoEntry
    MAX-ACCESS    not-accessible
    STATUS        current
    DESCRIPTION
        "Each entry in cLAPNtpInfoTable corresponds
         NTP-server information for a particular AP."

    INDEX    { cLApSysMacAddress }
    ::= { cLAPNtpInfoTable 1 }

CLAPNtpInfoEntry ::= SEQUENCE {
        cLAPNtpInfoState          TruthValue,
        cLApNtpInfoStatus         CLApNtpStatus,
        cLAPNtpInfoStratum        Unsigned32,
        cLAPNtpInfoLastSync       Unsigned32,
        cLAPNtpInfoOffset         Integer32,
        cLAPNtpInfoIPAddressType  InetAddressType,
        cLAPNtpInfoIPAddress      InetAddress
    }

cLAPNtpInfoState          OBJECT-TYPE
    SYNTAX                TruthValue
    MAX-ACCESS            read-only
    STATUS                current
    DESCRIPTION
        "This object specifies whether
         NTP service is enabled or disabled at AP.
         A value 'true' means NTP server is running at AP.
         A value 'false' means NTP server is not running at AP"
    ::= { cLAPNtpInfoEntry 1 }

cLApNtpInfoStatus         OBJECT-TYPE
    SYNTAX                CLApNtpStatus
    MAX-ACCESS            read-only
    STATUS                current
    DESCRIPTION
        "This object specifies the NTP server
         status for AP"
    ::= { cLAPNtpInfoEntry 2 }

cLAPNtpInfoStratum        OBJECT-TYPE
    SYNTAX                Unsigned32
    MAX-ACCESS            read-only
    STATUS                current
    DESCRIPTION
        "This object specifies NTP server stratum
         for AP.
         The object value is only applicable when
         cLAPNtpInfoState is 'true' and cLApNtpInfoStatus
         is other than none."
    DEFVAL { 0 }
    ::= { cLAPNtpInfoEntry 3 }

cLAPNtpInfoLastSync       OBJECT-TYPE
    SYNTAX                Unsigned32
    MAX-ACCESS            read-only
    STATUS                current
    DESCRIPTION
        "This object specifies AP last synced time with
         NTP server in seconds.
         The object value is only applicable when cLAPNtpInfoState
         is 'true'  and cLApNtpInfoStatus is other than none."
    DEFVAL { 0 }
    ::= { cLAPNtpInfoEntry 4 }

cLAPNtpInfoOffset         OBJECT-TYPE
    SYNTAX                Integer32
    MAX-ACCESS            read-only
    STATUS                current
    DESCRIPTION
        "This object specifies NTP server offset
         in micro-seconds for AP.
         The object value is only applicable when
         cLAPNtpInfoState is 'true'  and cLApNtpInfoStatus
         is other than none."
    DEFVAL { 0 }
    ::= { cLAPNtpInfoEntry 5 }

cLAPNtpInfoIPAddressType  OBJECT-TYPE
    SYNTAX                InetAddressType
    MAX-ACCESS            read-only
    STATUS                current
    DESCRIPTION
        "This object specifies the NTP server
        IP address type (ipv4 or ipv6) currently configured at AP.
        The object value is only applicable when
        cLAPNtpInfoState is 'true' and
        cLApNtpInfoStatus is other than none."
    DEFVAL { 0 }
    ::= { cLAPNtpInfoEntry 6 }

cLAPNtpInfoIPAddress      OBJECT-TYPE
    SYNTAX                InetAddress
    MAX-ACCESS            read-only
    STATUS                current
    DESCRIPTION
        "This object specifies the NTP server
        IP address currently configured at AP.
        The object value is only applicable when
        cLAPNtpInfoState is 'true'  and
        cLApNtpInfoStatus is other than none."
    DEFVAL { 0 }
    ::= { cLAPNtpInfoEntry 7 }

--**********************************************************************************
-- cLAPNtpInfoTable - NTP status for AP ends here
--**********************************************************************************
--

-- ********************************************************************
-- *    Compliance statements
-- ********************************************************************

ciscoLwappApMIBCompliances  OBJECT IDENTIFIER
    ::= { ciscoLwappApMIBConform 1 }

ciscoLwappApMIBGroups  OBJECT IDENTIFIER
    ::= { ciscoLwappApMIBConform 2 }


-- STATUS deprecated by ciscoLwappApMIBCompliance

ciscoLwappApMIBCompliance MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup
                    }
    ::= { ciscoLwappApMIBCompliances 1 }

-- STATUS deprecated by ciscoLwappApMIBComplianceRev2

ciscoLwappApMIBComplianceRev1 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1
                    }
    ::= { ciscoLwappApMIBCompliances 2 }

-- STATUS deprecated by ciscoLwappApMIBComplianceRev3

ciscoLwappApMIBComplianceRev2 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2
                    }
    ::= { ciscoLwappApMIBCompliances 3 }

-- Added since last MIB approval

ciscoLwappApMIBComplianceRev3 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApGroupSup4,
                        ciscoLwappApNotifObjsGroup,
                        ciscoLwappApNotifsGroup,
                        ciscoLwappApGroupSup4,
                        ciscoLwappApEthernetIfGroup,
                        ciscoLwappApRadioGroup
                    }
    ::= { ciscoLwappApMIBCompliances 4 }

-- Added for Franciscan release

ciscoLwappApMIBComplianceRev4 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroup,
                        ciscoLwappApGroupSup4,
                        ciscoLwappApEthernetIfGroup,
                        ciscoLwappApRadioGroup,
                        ciscoLwappApGroupSup5
                    }
    ::= { ciscoLwappApMIBCompliances 5 }

ciscoLwappApMIBComplianceRev5 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroup,
                        ciscoLwappApGroupSup4,
                        ciscoLwappApEthernetIfGroup,
                        ciscoLwappApRadioGroup,
                        ciscoLwappApGroupSup5,
                        ciscoLwappSeClientSup
                    }
    ::= { ciscoLwappApMIBCompliances 6 }

ciscoLwappApMIBComplianceRev6 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroup,
                        ciscoLwappApGroupSup4,
                        ciscoLwappApEthernetIfGroup,
                        ciscoLwappApRadioGroup,
                        ciscoLwappApGroupSup5,
                        ciscoLwappSeClientSup
                    }
    ::= { ciscoLwappApMIBCompliances 7 }

ciscoLwappApMIBComplianceRev7 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup10,
                        ciscoLwappApXorRadioGroup,
                        ciscoLwappApNotifsXorGroup
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."
    ::= { ciscoLwappApMIBCompliances 8 }

ciscoLwappApMIBComplianceRev8 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup10,
                        ciscoLwappApXorRadioGroup,
                        ciscoLwappApNotifsXorGroup,
                        ciscoLwappApProfileHaloBleGroup,
                        ciscoLwappApProfileGroup,
                        ciscoLwappApPacketCaptureProfileGroup,
                        ciscoLwappApPacketCaptureClientProfileGroup
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 9 }

ciscoLwappApMIBComplianceRev9 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup10,
                        ciscoLwappApXorRadioGroup,
                        ciscoLwappApNotifsXorGroup,
                        ciscoLwappApProfileHaloBleGroup,
                        ciscoLwappApProfileGroupSup1,
                        ciscoLwappApPacketCaptureProfileGroup,
                        ciscoLwappApPacketCaptureClientProfileGroup
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 10 }

ciscoLwappApMIBComplianceRev10 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup12,
                        ciscoLwappApXorRadioGroup,
                        ciscoLwappApNotifsXorGroup,
                        ciscoLwappApProfileHaloBleGroup,
                        ciscoLwappApProfileGroupSup2,
                        ciscoLwappApPacketCaptureProfileGroup,
                        ciscoLwappApPacketCaptureClientProfileGroup,
                        ciscoLwappApProfileQosMapGroup
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 11 }

ciscoLwappApMIBComplianceRev11 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup11,
                        ciscoLwappApGroupSup12,
                        ciscoLwappApXorRadioGroup,
                        ciscoLwappApNotifsXorGroup,
                        ciscoLwappApProfileHaloBleGroup,
                        ciscoLwappApProfileGroupSup2,
                        ciscoLwappApPacketCaptureProfileGroup,
                        ciscoLwappApPacketCaptureClientProfileGroup,
                        ciscoLwappApProfileQosMapGroup,
                        ciscoLwappApGroupSup13,
                        ciscoLwappAp11axGroup,
                        ciscoLwappApProfileHaloBleGroupSup1,
                        ciscoLwappApProfileGroupSup3,
                        ciscoLwappApLanStatsGroupSup1
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 12 }

ciscoLwappApMIBComplianceRev12 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup11,
                        ciscoLwappApGroupSup12,
                        ciscoLwappApXorRadioGroup,
                        ciscoLwappApNotifsXorGroup,
                        ciscoLwappApProfileHaloBleGroup,
                        ciscoLwappApProfileGroupSup2,
                        ciscoLwappApPacketCaptureProfileGroup,
                        ciscoLwappApPacketCaptureClientProfileGroup,
                        ciscoLwappApProfileQosMapGroup,
                        ciscoLwappApGroupSup13,
                        ciscoLwappAp11axGroup,
                        ciscoLwappApProfileHaloBleGroupSup1,
                        ciscoLwappApProfileGroupSup3,
                        ciscoLwappApLanStatsGroupSup1,
                        ciscoLwappApXorRadioGroupSup1,
                        ciscoLwappApProfileGroupSup4
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 13 }

ciscoLwappApMIBComplianceRev13 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup11,
                        ciscoLwappApGroupSup14,
                        ciscoLwappApXorRadioGroup,
                        ciscoLwappApNotifsXorGroup,
                        ciscoLwappApProfileHaloBleGroup,
                        ciscoLwappApProfileGroupSup2,
                        ciscoLwappApPacketCaptureProfileGroup,
                        ciscoLwappApPacketCaptureClientProfileGroup,
                        ciscoLwappApProfileQosMapGroup,
                        ciscoLwappApGroupSup13,
                        ciscoLwappAp11axGroup,
                        ciscoLwappApProfileHaloBleGroupSup1,
                        ciscoLwappApProfileGroupSup3,
                        ciscoLwappApLanStatsGroupSup1,
                        ciscoLwappApXorRadioGroupSup1,
                        ciscoLwappApProfileGroupSup4
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 14 }

ciscoLwappApMIBComplianceRev14 MODULE-COMPLIANCE
    STATUS          current
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup,
                        ciscoLwappApNotifsGroupVer2,
                        ciscoLwappApGroupSup8,
                        ciscoLwappApGroupSup9,
                        ciscoLwappApRadioGroupSup1,
                        ciscoLwappHaloBleGroup,
                        ciscoLwappApBleBeaconGroup,
                        ciscoLwappApLanStatsGroup,
                        ciscoLwappApGroupSup11,
                        ciscoLwappApGroupSup14,
                        ciscoLwappApNotifsXorGroup,
                        ciscoLwappApProfileHaloBleGroup,
                        ciscoLwappApProfileGroupSup2,
                        ciscoLwappApPacketCaptureProfileGroup,
                        ciscoLwappApPacketCaptureClientProfileGroup,
                        ciscoLwappApProfileQosMapGroup,
                        ciscoLwappApGroupSup13,
                        ciscoLwappAp11axGroup,
                        ciscoLwappApProfileHaloBleGroupSup1,
                        ciscoLwappApLanStatsGroupSup1,
                        ciscoLwappApXorRadioGroupSup2,
                        ciscoLwappApProfileGroupSup4
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAp11ChannelBandwidth
    MIN-ACCESS      read-only
    DESCRIPTION
        "Write access is not required."

    OBJECT          cLApSecureCipher
    MIN-ACCESS      read-only
    DESCRIPTION
        "Write access is not required."

    OBJECT          cLApAntennaBandMode
    MIN-ACCESS      read-only
    DESCRIPTION
        "Write access is not required."

    OBJECT          cLApBleBeaconMajorField
    MIN-ACCESS      read-only
    DESCRIPTION
        "Write access is not required."

    OBJECT          cLApBleBeaconMinorField
    MIN-ACCESS      read-only
    DESCRIPTION
        "Write access is not required."

    OBJECT          cLApBleBeaconTxPower
    MIN-ACCESS      read-only
    DESCRIPTION
        "Write access is not required."

    OBJECT          cLApBleBeaconStatus
    MIN-ACCESS      read-only
    DESCRIPTION
        "Write access is not required."

    OBJECT          cLApBleBeaconUuid
    MIN-ACCESS      read-only
    DESCRIPTION
        "Write access is not required."

    OBJECT          cLApBleBeaconInterval
    MIN-ACCESS      read-only
    DESCRIPTION
        "Write access is not required."

    OBJECT          cLApBleBeaconApplyGlobal
    MIN-ACCESS      read-only
    DESCRIPTION
        "Write access is not required."

    OBJECT          cLApBleBeaconAdvTxPower
    MIN-ACCESS      read-only
    DESCRIPTION
        "Write access is not required."
    ::= { ciscoLwappApMIBCompliances 15 }

-- ********************************************************************
-- *    Units of conformance
-- ********************************************************************

ciscoLwappApGroup OBJECT-GROUP
    OBJECTS         {
                        cLApIfMacAddress,
                        cLApMaxNumberOfDot11Slots,
                        cLApIfSmtDot11Bssid
                    }
    STATUS          current
    DESCRIPTION
        "This collection of objects represents the information
        about the general attributes and functional 
        parameters of those APs that have joined the
        controller."
    ::= { ciscoLwappApMIBGroups 1 }

ciscoLwappApIfGroup OBJECT-GROUP
    OBJECTS         { cLApDot11IfType }
    STATUS          current
    DESCRIPTION
        "This collection of objects represents the information
        about the dot11 interfaces of those APs that have 
        joined the controller."
    ::= { ciscoLwappApMIBGroups 2 }

ciscoLwappApGroupSup1 OBJECT-GROUP
    OBJECTS         { cLApEntPhysicalIndex }
    STATUS          current
    DESCRIPTION
        "This supplemental collection of objects represents the
        information about the general attributes and functional 
        parameters of those APs that have joined the
        controller."
    ::= { ciscoLwappApMIBGroups 3 }

ciscoLwappApGroupSup2 OBJECT-GROUP
    OBJECTS         { cLApName }
    STATUS          current
    DESCRIPTION
        "This supplemental collection of objects represents the
        name associated with those APs that have joined the
        controller."
    ::= { ciscoLwappApMIBGroups 4 }

ciscoLwappApGroupSup3 OBJECT-GROUP
    OBJECTS         {
                        cLApDot11IfRegDomain,
                        cLApDot11nSupport,
                        cLAp11nChannelBandwidth,
                        cLApCountryCode,
                        cLApCountryAllowed
                    }
    STATUS          current
    DESCRIPTION
        "This supplemental collection of objects represents the
        country and 802.11n related information for those APs 
        that have joined the controller."
    ::= { ciscoLwappApMIBGroups 5 }

ciscoLwappApNotifObjsGroup OBJECT-GROUP
    OBJECTS         { cLApAssocFailureReason }
    STATUS          current
    DESCRIPTION
        "This supplemental collection of objects represents the
        information carried by the AP related notifications 
        sent by the agent to a network management station."
    ::= { ciscoLwappApMIBGroups 6 }

ciscoLwappApNotifsGroup NOTIFICATION-GROUP
   NOTIFICATIONS    {
                        ciscoLwappApIfRegulatoryDomainMismatchNotif,
                        ciscoLwappApUnsupported,
                        ciscoLwappApCrash,
                        ciscoLwappApAssociated
                    }
    STATUS          deprecated
    DESCRIPTION
        "This supplemental collection of objects represents the
        AP related notifications sent by the agent to a network
        management station.
        ciscoLwappApNotifsGroup object is superseded by 
        ciscoLwappApNotifsGroupVer1."
    ::= { ciscoLwappApMIBGroups 7 }

ciscoLwappApGroupSup4 OBJECT-GROUP
    OBJECTS         {
                        cLApUpTime,
                        cLLwappUpTime,
                        cLLwappJoinTakenTime,
                        cLApMaxNumberOfEthernetSlots,
                        cLApPrimaryControllerAddressType,
                        cLApPrimaryControllerAddress,
                        cLApSecondaryControllerAddressType,
                        cLApSecondaryControllerAddress,
                        cLApTertiaryControllerAddressType,
                        cLApTertiaryControllerAddress,
                        cLApLomEnabled,
                        cLApLomFirstChannel,
                        cLApLomSecondChannel,
                        cLApLomThirdChannel,
                        cLApLomFourthChannel,
                        cLApCredentialGlobalUserName,
                        cLApCredentialGlobalPassword,
                        cLApCredentialGlobalSecret,
                        cLApCredentialUserName,
                        cLApCredentialPassword,
                        cLApCredentialSecret,
                        cLApCredentialEnableGlobalCredentials,
                        cLApFastHbTimerTimeout,
                        cLApFastHbTimerEnabled,
                        cLApPrimaryDiscoveryTimeout,
                        cLApGlobalPrimaryControllerAddressType,
                        cLApGlobalPrimaryControllerAddress,
                        cLApGlobalPrimaryControllerName,
                        cLApGlobalSecondaryControllerAddressType,
                        cLApGlobalSecondaryControllerAddress,
                        cLApGlobalSecondaryControllerName,
                        ciscoLwappApIfRegulatoryDomainMismatchNotifEnabled,
                        ciscoLwappApCrashEnabled,
                        ciscoLwappApUnsupportedEnabled,
                        ciscoLwappApAssociatedEnabled,
                        cLApLastRebootReason,
                        cLApPrimedDiscoveryTimeout,
                        cLApExtensionChannel,
                        cLAdjChannelRogueEnabled,
                        cLApWipsEnable,
                        cLApNwLegacyBeamForming,
                        cLApProfileFastHbTimerEnabled
                    }
    STATUS          deprecated
    DESCRIPTION
        "This supplemental collection of objects represents the
        information for those APs that have joined the controller.
        ciscoLwappApGroupSup4 object is superseded by 
        ciscoLwappApGroupSup6."
    ::= { ciscoLwappApMIBGroups 8 }

ciscoLwappApEthernetIfGroup OBJECT-GROUP
    OBJECTS         {
                        cLApEthernetIfName,
                        cLApEthernetIfMacAddress,
                        cLApEthernetIfAdminStatus,
                        cLApEthernetIfOperStatus,
                        cLApEthernetIfRxUcastPkts,
                        cLApEthernetIfRxNUcastPkts,
                        cLApEthernetIfTxUcastPkts,
                        cLApEthernetIfTxNUcastPkts
                    }
    STATUS          current
    DESCRIPTION
        "This collection of objects represents the information
        about the Ethernet interfaces of those APs that have
        joined the controller."
    ::= { ciscoLwappApMIBGroups 9 }

ciscoLwappApRadioGroup OBJECT-GROUP
    OBJECTS         {
                        cLApDot11RadioMACAddress,
                        cLApDot11RadioSubBand,
                        cLApDot11RadioVersion,
                        cLApDot11IsBackhaul,
                        cLApDot11RadioRole,
                        cLApDot11RadioMode,
                        cLApDot11RadioSubType
                    }
    STATUS          current
    DESCRIPTION
        "This collection of objects represents the information
        about the Radios of those APs that have
        joined the controller."
    ::= { ciscoLwappApMIBGroups 10 }

ciscoLwappApGroupSup5 OBJECT-GROUP
    OBJECTS         {
                        cLApGlobalFailoverPriority,
                        cLApFailoverPriority,
                        cLApEncryptionEnable,
                        cLApLinkLatencyEnable,
                        cLApLinkLatencyReset,
                        cLApLinkLatencyStatsCurrent,
                        cLApLinkLatencyStatsMin,
                        cLApLinkLatencyStatsMax,
                        cLApLinkLatencyTimeStamp
                    }
    STATUS          current
    DESCRIPTION
        "This supplemental collection of objects represents
        objects related to encryption and link latency of 
        AP."
    ::= { ciscoLwappApMIBGroups 11 }

ciscoLwappSeClientSup OBJECT-GROUP
    OBJECTS         {
                        cLApSeClientUserName,
                        cLApSeClientIPAddrType,
                        cLApSeClientIPAddr,
                        cLApSeClientDuration,
                        cLApSeClientPort
                    }
    STATUS          current
    DESCRIPTION
        "This supplemental collection of objects represents the
        Spectrum Expert client details connected to the APs."
    ::= { ciscoLwappApMIBGroups 12 }

ciscoLwappDot11IfAntennaGroup OBJECT-GROUP
    OBJECTS         { cLApDot11IfAntennaEnable }
    STATUS          current
    DESCRIPTION
        "This supplemental collection of objects represents the
        antenna details corresponding to the dot11 interface of the
        Access Points."
    ::= { ciscoLwappApMIBGroups 13 }

ciscoLwappRetransmitGroup OBJECT-GROUP
    OBJECTS         {
                        cLApRetransmitCount,
                        cLApRetransmitTimeout,
                        cLApGlobalRetransmitCount,
                        cLApGlobalRetransmitTimeout
                    }
    STATUS          current
    DESCRIPTION
        "This supplemental collection of objects represents the
        retransmit parameters corresponding to the fallback of an
        AccessPoint to another controller during failover."
    ::= { ciscoLwappApMIBGroups 14 }

ciscoLwappApGroupSup6 OBJECT-GROUP
    OBJECTS         {
                        cLApUpTime,
                        cLLwappUpTime,
                        cLLwappJoinTakenTime,
                        cLApMaxNumberOfEthernetSlots,
                        cLApPrimaryControllerAddressType,
                        cLApPrimaryControllerAddress,
                        cLApSecondaryControllerAddressType,
                        cLApSecondaryControllerAddress,
                        cLApTertiaryControllerAddressType,
                        cLApTertiaryControllerAddress,
                        cLApLomFirstChannel,
                        cLApLomSecondChannel,
                        cLApLomThirdChannel,
                        cLApLomFourthChannel,
                        cLApCredentialGlobalUserName,
                        cLApCredentialGlobalPassword,
                        cLApCredentialGlobalSecret,
                        cLApCredentialUserName,
                        cLApCredentialPassword,
                        cLApCredentialSecret,
                        cLApCredentialEnableGlobalCredentials,
                        cLApFastHbTimerTimeout,
                        cLApFastHbTimerEnabled,
                        cLApPrimaryDiscoveryTimeout,
                        cLApGlobalPrimaryControllerAddressType,
                        cLApGlobalPrimaryControllerAddress,
                        cLApGlobalPrimaryControllerName,
                        cLApGlobalSecondaryControllerAddressType,
                        cLApGlobalSecondaryControllerAddress,
                        cLApGlobalSecondaryControllerName,
                        ciscoLwappApIfRegulatoryDomainMismatchNotifEnabled,
                        ciscoLwappApCrashEnabled,
                        ciscoLwappApUnsupportedEnabled,
                        ciscoLwappApAssociatedEnabled,
                        cLApLastRebootReason,
                        cLApPrimedDiscoveryTimeout,
                        cLApGlobalPreferMode
                    }
    STATUS          current
    DESCRIPTION
        "This supplemental collection of objects represents the
        global and credential information for those APs 
        that have joined the controller."
    ::= { ciscoLwappApMIBGroups 15 }

ciscoLwappApNotifsGroupVer1 NOTIFICATION-GROUP
   NOTIFICATIONS    {
                        ciscoLwappApIfRegulatoryDomainMismatchNotif,
                        ciscoLwappApUnsupported,
                        ciscoLwappApAssociated
                    }
    STATUS          current
    DESCRIPTION
        "This supplemental collection of objects represents the
        AP related notifications sent by the agent to a network
        management station."
    ::= { ciscoLwappApMIBGroups 16 }

ciscoLwappApGroupSup7 OBJECT-GROUP
    OBJECTS         {
                        cLApTelnetEnable,
                        cLApSshEnable,
                        cLApPreStdStateEnabled,
                        cLApPwrInjectorStateEnabled,
                        cLApPwrInjectorSelection,
                        cLApPwrInjectorSwMacAddr,
                        cLApMonitorModeOptimization,
                        cLApDomainName,
                        cLApNameServerAddress,
                        cLApAMSDUEnable,
                        cLApEncryptionSupported,
                        cLApRogueDetectionEnabled,
                        cLApTcpMss,
                        cLApAdminStatus,
                        cLApCdpOverAirEnabled,
                        cLApDot11IfAdminStatus,
                        cLApEthernetIfCdpEnabled,
                        cLApGlobalTcpMss,
                        cLApGlobalDot11IfCdpEnabled,
                        cLApGlobalEthernetIfCdpEnabled,
                        cLApVlanIfMode,
                        cLApVlanIfEnable,
                        cLApVlanIfNativeVlanId,
                        cLApGlobal802dot1xAuthenticationEnabled,
                        cLApGlobal802dot1xSupplicantPassword,
                        cLApGlobal802dot1xSupplicantUsername,
                        cLApGlobal802dot1xSupplicantEapType,
                        cLAp802dot1xSupplicantOverrideEnabled,
                        cLAp802dot1xSupplicantOverrideUsername,
                        cLAp802dot1xSupplicantOverridePassword,
                        cLAp802dot1xSupplicantOverrideEapType,
                        cLApNwTxPowerThreshold,
                        cLApVlanListRowStatus
                    }
    STATUS          current
    DESCRIPTION
        "This supplemental collection of objects represents the
        information about the general attributes and functional 
        parameters of those APs that have joined the
        controller."
    ::= { ciscoLwappApMIBGroups 17 }

ciscoLwappApGroupSup8 OBJECT-GROUP
    OBJECTS         {
                        cLApDot11acSupport,
                        cLAp11ChannelBandwidth,
                        cLApExtensionChannels,
                        cLApGlobalMaxApsSupported,
                        cLApAuthorizeApMacAuth,
                        cLApAuthorizeApSerialNumAuth,
                        cLApAuthorizeApMethodList,
                        cLApGlobalAPAuditReport,
                        cLApGlobalAPAuditReportInterval,
                        cLApGlobalAPConnectCount,
                        cLApAuthorizeApMacMethodList,
                        cLApAuthorizeApSerialNumMethodList,
                        clApImageUpgradeHttpsEnable
                    }
    STATUS          current
    DESCRIPTION
        "This supplemental collection of objects represents the
        information about the general attributes and functional 
        parameters of those APs that have joined the
        controller."
    ::= { ciscoLwappApMIBGroups 18 }

ciscoLwappApNotifsGroupVer2 NOTIFICATION-GROUP
   NOTIFICATIONS    {
                        ciscoLwappApPower,
                        ciscoLwappApRogueApDetected,
                        ciscoLwappApRogueApCleared,
                        ciscoLwappApWipsNotification,
                        ciscoLwappApNoDownlinkChannelNotify,
                        ciscoLwappApIfUpNotify,
                        ciscoLwappApIfDownNotify,
                        ciscoLwappRadioBandChangeNotify,
                        ciscoLwappApModeUnsupportedOnFlexExpressEvent,
                        ciscoLwappXmFilterCheckWarning,
                        ciscoLwappApSystemBootupEvent,
                        ciscoLwappApCapwapRetransmissionQueueFullEvent,
                        ciscoLwappApCurrChannelChanged,
                        ciscoLwappApSsidKeyConflict,
                        ciscoLwappApAcTimeSyncFailureTrap,
                        ciscoLwappApMonitorModeChangeNotify,
                        ciscoLwappApCurrentChannelRogueCleared,
                        ciscoLwappApCurrentChannelRogueDetected,
                        ciscoLwappApRogueDetected,
                        ciscoLwappApAdjChannelRogueCleared,
                        ciscoLwappApAdjChannelRogueDetected,
                        ciscoLwappApMaxClientLimitNotify,
                        ciscoLwappApMemoryUsageHigh,
                        ciscoLwappApCpuUsageHigh,
                        ciscoLwappApUpgradeFailureNotify,
                        ciscoLwappApClientThresholdNotify,
                        ciscoLwappBrokenAntennaDetails,
                        ciscoLwappApRadioStuck
                    }
    STATUS          current
    DESCRIPTION
        "This supplemental collection of objects represents the
        AP related notifications sent by the agent to a network
        management station."
    ::= { ciscoLwappApMIBGroups 19 }

ciscoLwappApGroupSup9 OBJECT-GROUP
    OBJECTS         {
                        cLApSecureCipher,
                        cLApAntennaBandMode,
                        cLAPNtpInfoState,
                        cLApNtpInfoStatus,
                        cLAPNtpInfoStratum,
                        cLAPNtpInfoLastSync,
                        cLAPNtpInfoOffset,
                        cLAPNtpInfoIPAddressType,
                        cLAPNtpInfoIPAddress
                    }
    STATUS          current
    DESCRIPTION
        "This supplemental collection of objects represents the
        information about the general attributes and functional 
        parameters of those APs that have joined the
        controller."
    ::= { ciscoLwappApMIBGroups 20 }

ciscoLwappApRadioGroupSup1 OBJECT-GROUP
    OBJECTS         {
                        cLApDot11RadioMode,
                        cLApDot11RadioSubType
                    }
    STATUS          current
    DESCRIPTION
        "This collection of objects represents the information
        about the Radios of those APs that have
        joined the controller."
    ::= { ciscoLwappApMIBGroups 21 }

ciscoLwappHaloBleGroup OBJECT-GROUP
    OBJECTS         {
                        cLHaloGlobalBleBeaconInterval,
                        cLHaloGlobalBleBeaconUuid,
                        cLHaloGlobalBleBeaconTxPower,
                        cLHaloGlobalBleBeaconEnable
                    }
    STATUS          current
    DESCRIPTION
        "This collection contains BLE global configuration which lists
        the BLE beacon's identification number and attenuation value
        of HALO APs that have joined the controller."
    ::= { ciscoLwappApMIBGroups 22 }

ciscoLwappApBleBeaconGroup OBJECT-GROUP
    OBJECTS         {
                        cLApBleBeaconMajorField,
                        cLApBleBeaconMinorField,
                        cLApBleBeaconTxPower,
                        cLApBleBeaconStatus,
                        cLApBleBeaconUuid,
                        cLApBleBeaconInterval,
                        cLApBleBeaconApplyGlobal,
                        cLApBleBeaconAdvTxPower
                    }
    STATUS          current
    DESCRIPTION
        "This collection represents BLE beacon's AP specific
        configuration for HALO APs that have joined the controller."
    ::= { ciscoLwappApMIBGroups 23 }

ciscoLwappApLanStatsGroup OBJECT-GROUP
    OBJECTS         {
                        cLApLanPortState,
                        cLApLanPortVlanId,
                        cLApLanPortVlanIdValid,
                        cLApLanPoeState,
                        cLApLanOverride
                    }
    STATUS          current
    DESCRIPTION
        "This collection represents Sardinia AP LAN stats
        information that have joined the controller."
    ::= { ciscoLwappApMIBGroups 24 }

ciscoLwappApGroupSup10 OBJECT-GROUP
    OBJECTS         {
                        cLApPowerStatus,
                        cLApNameServerAddressType,
                        cLApDataEncryptionStatus,
                        cLApNsiKey,
                        cLApPortNumber,
                        cLApVenueConfigVenueGroup,
                        cLApVenueConfigVenueType,
                        cLApVenueConfigVenueName,
                        cLApVenueConfigLanguage,
                        cLApLEDState,
                        cLApRealTimeStatsModeEnabled,
                        cLApTrunkVlan,
                        cLApTrunkVlanStatus,
                        cLApLocation,
                        cLApSubMode,
                        cLApAssocCount,
                        cLApAssocFailResourceCount,
                        cLApAssociatedClientCount,
                        cLApMemoryCurrentUsage,
                        cLApMemoryAverageUsage,
                        cLApCpuCurrentUsage,
                        cLApCpuAverageUsage,
                        cLApUpgradeFromVersion,
                        cLApUpgradeToVersion,
                        cLApUpgradeFailureCause,
                        cLApMaxClientLimitNumberTrap,
                        cLApMaxClientLimitCause,
                        cLApMaxClientLimitSet,
                        cLApFloorLabel,
                        cLApConnectCount,
                        cLApReassocSuccCount,
                        cLApReassocFailCount,
                        cLApAssocFailCountByRate,
                        cLApAbnormalOfflineCount,
                        cLApActiveClientCount,
                        cLApAssocFailCountForRssiLow,
                        cLApSysNetId,
                        cLApAssocFailTimes,
                        cLApHeartBeatRspAvgTime,
                        cLApEchoRequestCount,
                        cLApEchoResponseLossCount,
                        cLApModuleInserted,
                        cLApEnableModule,
                        cLApIsUniversal,
                        cLApUniversalPrimeStatus,
                        cLApIsMaster,
                        cLApBleFWDownloadStatus,
                        cLApDot11XorDartConnectorStatus,
                        cLApDot11IfAntennaTxEnable,
                        cLApDot11IfAntennaRxEnable,
                        cLApEthernetIfDuplex,
                        cLApEthernetIfLinkSpeed,
                        cLApEthernetIfPOEPower,
                        cLApEthernetIfRxTotalBytes,
                        cLApEthernetIfTxTotalBytes,
                        cLApEthernetIfInputCrc,
                        cLApEthernetIfInputAborts,
                        cLApEthernetIfInputErrors,
                        cLApEthernetIfInputFrames,
                        cLApEthernetIfInputOverrun,
                        cLApEthernetIfInputDrops,
                        cLApEthernetIfInputResource,
                        cLApEthernetIfUnknownProtocol,
                        cLApEthernetIfRunts,
                        cLApEthernetIfGiants,
                        cLApEthernetIfThrottle,
                        cLApEthernetIfResets,
                        cLApEthernetIfOutputCollision,
                        cLApEthernetIfOutputNoBuffer,
                        cLApEthernetIfOutputResource,
                        cLApEthernetIfOutputUnderrun,
                        cLApEthernetIfOutputErrors,
                        cLApEthernetIfOutputTotalDrops,
                        cLApDataLinkLatencyStatsCurrent,
                        cLApDataLinkLatencyStatsMin,
                        cLApDataLinkLatencyStatsMax,
                        cLApDataLinkLatencyTimeStamp,
                        cLApCtsSxpDefaultPassword,
                        cLApCtsSxpState,
                        cLApCtsSxpMode,
                        cLApCtsSxpListenerMinHoldtime,
                        cLApCtsSxpListenerMaxHoldtime,
                        cLApCtsSxpReconcilePeriod,
                        cLApCtsSxpRetryPeriod,
                        cLApCtsSxpSpeakerHoldTime,
                        cLApCtsSxpSpeakerKeepAlive,
                        cLApCtsInlineTagStatus,
                        cLApCtsSgaclStatus,
                        cLApCtsOverrideStatus,
                        cLApModeClear,
                        cLApSiteTagName,
                        cLApRfTagName,
                        cLApPolicyTagName,
                        cLApTagSource,
                        cLApUsbModuleName,
                        cLApUsbModuleState,
                        cLApUsbModuleProductId,
                        cLApUsbDescription,
                        cLApUsbStateInfo,
                        cLApUsbOverride,
                        cLApUsbSerialNumber,
                        cLApUsbMaxPower,
                        cLApLagConfigStatus,
                        cLApMonitorModeOptStatus,
                        cLApLegacyBeamForming,
                        cLApDot11IfLinkChangeCount,
                        cLApDot11MaxClients,
                        cLApPromiscuousModeDwelling,
                        cLApDot11IfStaKeepingTime,
                        cLApDot11IfLinkSpeed,
                        cLApDot11IfMtu,
                        cLApDot11IfDesc,
                        cLAPDot11IfMinTxPowerStep,
                        cLApDot11IfMaxDataRate,
                        cLApEthernetIfMtu,
                        cLApEthernetIfType,
                        cLApEthernetIfLinkChangeCount,
                        cLApWlanStatsTxPktNum,
                        cLApWlanStatsTxOctetNum,
                        cLApWlanStatsRxPktNum,
                        cLApWlanStatsRxOctetNum,
                        cLApWlanStatsRetransmitNum,
                        cLApWlanStatsAssocClientNum,
                        cLApWlanStatsOnlineUserNum,
                        cLApHyperlocationAdminState,
                        cLApHyperlocationUnsetFlag,
                        cLApOeapDisableLocalAccess,
                        cLApGlobalLEDState,
                        cLApRadioInterfaceShutdownEnabled,
                        cLApEthernetInterfaceDowntime,
                        cLAPMulticastGroupAddressType,
                        cLAPMulticastGroupAddress,
                        cLAPMulticastMode,
                        cLApGlobalAPLagCapability,
                        cLApGlobalAPDtlsVersion,
                        cLApGlobalAPDtlsCipherSuite,
                        cLApWlanInfoMaxClients,
                        cLApRadioWlanSsid,
                        cLApRadioWlanBssid,
                        cLApNwTxPowerThresholdVer2,
                        cLApDot11RadioStatsRxErrorFrameCount,
                        cLApDot11RadioStatsMacMicErrFrameCount,
                        cLApDot11RadioStatsMacDecryptErrFrameCount,
                        cLApDot11RadioStatsRxMgmtFrameCount,
                        cLApDot11RadioStatsRxCtrlFrameCount,
                        cLApDot11RadioStatsRxDataFrameCount,
                        cLApDot11RadioStatsTxMgmtFrameCount,
                        cLApDot11RadioStatsTxCtrlFrameCount,
                        cLApDot11RadioStatsTxDataFrameCount,
                        cLApDot11RadioStatsRxDataPacketCount,
                        cLApDot11RadioStatsTxDataPacketCount,
                        cLApDot11RadioStatsTxDataPacketCount,
                        cLApDot11RadioStatsRetryFrameCount,
                        cLApDot11RadioStatsRetryPacketCount,
                        cLApDot11RadioRssiHighest,
                        cLApDot11RadioRssiLowest,
                        cLApDot11RadioRssiAverage,
                        cLApCrashFileName,
                        cLApCrashFileSize,
                        cLApCrashFileTimeStamp,
                        cLApLEDFlashStatus,
                        cLApLEDFlashDuration,
                        cLApInetAddressType,
                        cLApInetAddress,
                        cLApStaticIpv6AddressEnabled,
                        cLApStaticIpv6InetAddressType,
                        cLApStaticIpv6InetAddress,
                        cLApStaticIpv6PrefixLength,
                        cLApStaticIpv6GatewayInetAddressType,
                        cLApStaticIpv6GatewayInetAddress,
                        cLApStaticIpNetmaskType,
                        cLApStaticIpNetmask,
                        cLApPreferMode,
                        cLApPreferModeApplied,
                        cLApSysMemType,
                        cLApSysMemSize,
                        cLApSysFlashSize,
                        cLApSysCpuType,
                        cLApSysFlashType,
                        cLApDot11RadioRateStatsRxPackets,
                        cLApDot11RadioRateStatsRxBytes,
                        cLApDot11RadioRateStatsTxPackets,
                        cLApDot11RadioRateStatsTxBytes,
                        cLApDot11RadioRateString,
                        cLApPacketDumpFtpServerAddressType,
                        cLApPacketDumpFtpServerAddress,
                        cLApPacketDumpFtpServerPath,
                        cLApPacketDumpFtpUsername,
                        cLApPacketDumpFtpPassword,
                        cLApPacketDumpClassifier,
                        cLApPacketDumpBufferSize,
                        cLApPacketDumpCaptureTime,
                        cLApPacketDumpTruncation,
                        cLApPacketDumpApName,
                        cLApPacketDumpDeviceMacAddress,
                        cLApPacketDumpStartStop,
                        cLApDot11RadioSsidName,
                        cLApCmMacAddress,
                        cLApCmApMacAddress,
                        cLApCmSwVersion,
                        cLApEthernetSpeed,
                        cLApEthernetStatus,
                        cLApCmStatus,
                        cLApCmSerialNumber,
                        cLApCmUsChannelStatus,
                        cLApCmDsChannelStatus,
                        cLApCmMaskBit,
                        cLApEnvTemperatureDegree,
                        cLApEnvTemperatureState,
                        cLApEnvOrientation,
                        cLApEnvPoeOutStatus,
                        cLApGpsLocationPresent,
                        cLApGpsLocationValid,
                        cLApGpsLatitude,
                        cLApGpsLongitude,
                        cLApGpsAltitude,
                        cLApGpsCollectionTime,
                        cLApRogueApMacAddress,
                        cLApDot11RadioChannelNumber,
                        cLApRogueApSsid,
                        cLApRogueType,
                        cLApWipsReason,
                        cLApWipsClear,
                        cLApIfUpDownFailureType,
                        cLApIfUpDownCause,
                        cLApIfUpDownFailureCode,
                        cLApAlarmSet,
                        cLApRogueClassType,
                        cLApRogueDetectedChannel,
                        cLApRSSI,
                        cLApSNR,
                        cLApDot11RadioCurrentChannel,
                        cLApAdhocRogue,
                        cLApRogueAPOnWiredNetwork,
                        cLApRogueMode,
                        cLApRogueIsClassifiedByRule,
                        cLApRogueClassifiedApMacAddress,
                        cLApRogueClassifiedRSSI,
                        cLAPPreviousMonitorMode,
                        cLAPCurrentMonitorMode,
                        cLApSsidKeyConfSsidA,
                        cLApSsidKeyConfKeyIdxA,
                        cLApSsidKeyConfSsidB,
                        cLApSsidKeyConfKeyIdxB,
                        cLApPreviousChannel,
                        cLApCurrentChannel,
                        cLApChannelCustomize,
                        cLApIfLoadChannelUtilization,
                        cLAPGroupVlanName,
                        cLApRuleName,
                        cLApSeverityScore,
                        cLApDot11XorRadioRoleChangeReason,
                        cLApDot11XorRadioBandChangeReason
                    }
    STATUS          deprecated
    DESCRIPTION
        "This supplemental collection of objects represents the
        information about the general attributes and functional 
        parameters of those APs that have joined the
        controller."
    ::= { ciscoLwappApMIBGroups 25 }

ciscoLwappApXorRadioGroup OBJECT-GROUP
    OBJECTS         {
                        cLApDot11XorRadioMode,
                        cLApDot11XorRadioBand,
                        cLApDot11XorRadioRoleAssignment,
                        ciscoLwappXorRadioRoleChangeEnabled,
                        cLApDot11IfSensorReachability,
                        cLApFraCoverageOverlapFactor,
                        cLApFraSuggestedMode
                    }
    STATUS          deprecated
    DESCRIPTION
        "This collection of objects represents the information
        about the Xor Radios of those APs that have
        joined the controller."
    ::= { ciscoLwappApMIBGroups 26 }

ciscoLwappApNotifsXorGroup NOTIFICATION-GROUP
   NOTIFICATIONS    { ciscoLwappApXorRadioRoleChangeNotify }
    STATUS          current
    DESCRIPTION
        "This collection of objects represents the XOR radio
        related notifications sent by the agent to a network
        management station."
    ::= { ciscoLwappApMIBGroups 27 }

ciscoLwappApGroupSup11 OBJECT-GROUP
    OBJECTS         { cLApDot11axSupport }
    STATUS          current
    DESCRIPTION
        "This supplemental collection of objects represents the
        information about the general attributes and functional
        parameters of those APs that have joined the
        controller."
    ::= { ciscoLwappApMIBGroups 28 }

ciscoLwappApProfileHaloBleGroup OBJECT-GROUP
    OBJECTS         {
                        cLApProfileHaloBleBeaconInterval,
                        cLApProfileHaloBleBeaconTxPower,
                        cLApProfileHaloBleBeaconEnabled,
                        cLApProfileHaloBleBeaconUuid,
                        cLApProfileHaloBleBeaconTxPower,
                        cLApProfileHaloBleBeaconEnabled,
                        cLApProfileHaloBleBeaconAdvertisedPwr
                    }
    STATUS          current
    DESCRIPTION
        "This collection contains HALO BLE beacon configuration for a
        specific AP profile. It lists the HALO BLE beacon ID, UUID,
        transmission power, and status per beacon for HALO enabled APs
        that have joined the controller."
    ::= { ciscoLwappApMIBGroups 29 }

ciscoLwappApProfileGroup OBJECT-GROUP
    OBJECTS         {
                        cLApProfileRowStatus,
                        cLApProfileCredentialGlobalUserName,
                        cLApProfileCredentialGlobalPassword,
                        cLApProfileCredentialGlobalSecret,
                        cLApProfileCredentialEnableGlobalCredentials,
                        cLApProfileLinkLatencyEnable,
                        cLApProfileHaloBleBeaconInterval,
                        cLApProfileFastHbTimerTimeout,
                        cLApProfilePrimaryDiscoveryTimeout,
                        cLApProfileBackupPrimaryControllerAddressType,
                        cLApProfileBackupPrimaryControllerAddress,
                        cLApProfileBackupPrimaryControllerName,
                        cLApProfileBackupSecondaryControllerAddressType,
                        cLApProfileBackupSecondaryControllerAddress,
                        cLApProfileBackupSecondaryControllerName,
                        cLApProfileBackupTertiaryControllerAddressType,
                        cLApProfileBackupTertiaryControllerAddress,
                        cLApProfileBackupTertiaryControllerName,
                        cLApProfileTcpMss,
                        cLApProfileRetransmitCount,
                        cLApProfileRetransmitTimeout,
                        cLApProfileOeapDisableLocalAccess,
                        cLApProfileLedState,
                        cLApProfileRadioInterfaceShutdownEnabled,
                        cLApProfileEthernetInterfaceDowntime,
                        cLApProfileMulticastGroupAddressType,
                        cLApProfileMulticastGroupAddress,
                        cLApProfileMulticastMode,
                        cLApProfilePrimedJoinTimeout,
                        cLApProfilePreferMode,
                        cLApProfileApLagEnabled,
                        cLApProfile802dot1xAuthenticationEnabled,
                        cLApProfile802dot1xSupplicantUsername,
                        cLApProfile802dot1xSupplicantPassword,
                        cLApProfileEncryptionEnable,
                        cLApProfileTelnetEnable,
                        cLApProfileSshEnable,
                        cLApProfileHyperlocationEnable,
                        cLApProfileHyperlocationDetectionThreshold,
                        cLApProfileHyperlocationResetThreshold,
                        cLApProfileHyperlocationTriggerThreshold,
                        cLApProfileHyperlocationNtpIpAddressType,
                        cLApProfileHyperlocationNtpIpAddress,
                        cLApProfileAdjustMss,
                        cLApProfileDiscoveryTimeout,
                        cLApProfileHeartBeatTimeout,
                        cLApProfileCdpEnable,
                        cLApProfileApPacketCaptureProfile,
                        cLApProfileRogueReportInterval,
                        cLApProfileRogueMinimumRssi,
                        cLApProfileRogueTransientInterval,
                        cLApProfileRogueContainFlexconnect,
                        cLApProfileRogueContainAutoRateEnable,
                        cLApProfileRogueDetectionEnable,
                        cLApProfileReportInterval24ghz,
                        cLApProfileReportInterval5ghz,
                        cLApProfileDot1xApSwitchEapAuth,
                        cLApProfileDot1xApSwtichLscAuth,
                        cLApProfileMeshProfileName,
                        cLApProfileUsbStatus,
                        cLApProfileVlanTagging,
                        cLApProfileApCountryCode,
                        cLApProfileExtModuleEnable,
                        cLApProfileStatsTimer,
                        cLApProfilePoePreStandardSwitchFlag,
                        cLApProfilePoePowerInjectorSelection,
                        cLApProfilePoeInjectorSwitchMac,
                        cLApProfileHaloBleBeaconAdvertisedPwr,
                        cLApProfileTftpDownGradeAddressType,
                        cLApProfileTftpDownGradeAddress,
                        cLApProfileTftpDownGradeFileName,
                        cLApProfileCoreDumpType,
                        cLApProfileCoreDumpTftpAddressType,
                        cLApProfileCoreDumpTftpAddress,
                        cLApProfileCoreDumpCoreFileName,
                        cLApProfileBackupFallbackEnabled
                    }
    STATUS          deprecated
    DESCRIPTION
        "This collection contains the information about the credentials
        of the 802.11 LWAPP Access Point that have joined the 
        Controller"
    ::= { ciscoLwappApMIBGroups 30 }

ciscoLwappApPacketCaptureProfileGroup OBJECT-GROUP
    OBJECTS         {
                        cLApPacketCaptureProfileRowStatus,
                        cLApPacketCaptureProfileBufferSize,
                        cLApPacketCaptureProfileDuration,
                        cLApPacketCaptureProfileTruncation,
                        cLApPacketCaptureProfileFtpServerAddressType,
                        cLApPacketCaptureProfileFtpServerAddress,
                        cLApPacketCaptureProfileFtpServerPath,
                        cLApPacketCaptureProfileFtpUsername,
                        cLApPacketCaptureProfileFtpPassword,
                        cLApPacketCaptureProfileClassifierArp,
                        cLApPacketCaptureProfileClassifierBroadcast,
                        cLApPacketCaptureProfileClassifierControl,
                        cLApPacketCaptureProfileClassifierData,
                        cLApPacketCaptureProfileClassifierDot1x,
                        cLApPacketCaptureProfileClassifierIapp,
                        cLApPacketCaptureProfileClassifierIp,
                        cLApPacketCaptureProfileClassifierManagement,
                        cLApPacketCaptureProfileClassifierMulticast,
                        cLApPacketCaptureProfileClassifierTcp,
                        cLApPacketCaptureProfileClassifierUdp,
                        cLApPacketCaptureProfileClassifierTcpPort,
                        cLApPacketCaptureProfileClassifierUdpPort,
                        cLApPacketCaptureApDeviceMac,
                        cLApPacketCaptureApMacAddress,
                        cLApPacketCaptureApStatus
                    }
    STATUS          current
    DESCRIPTION
        "This collection contains the information about the packet
        capture parameters of the 802.11 LWAPP Access Point that have
        joined the Controller"
    ::= { ciscoLwappApMIBGroups 31 }

ciscoLwappApPacketCaptureClientProfileGroup OBJECT-GROUP
    OBJECTS         {
                        cLApPacketCaptureClientApMacAddress,
                        cLApPacketCaptureClientAutoMode,
                        cLApPacketCaptureClientStartStop,
                        cLApPacketCaptureClientSiteName,
                        cLApPacketCaptureClientRowStatus
                    }
    STATUS          current
    DESCRIPTION
        "This collection contains the information about the packet
        capture parameters for per client basis for LWAPP Access Point 
        that have joined the Controller"
    ::= { ciscoLwappApMIBGroups 32 }

ciscoLwappApProfileGroupSup1 OBJECT-GROUP
    OBJECTS         {
                        cLApProfileRowStatus,
                        cLApProfileCredentialGlobalUserName,
                        cLApProfileCredentialGlobalPassword,
                        cLApProfileCredentialGlobalSecret,
                        cLApProfileLinkLatencyEnable,
                        cLApProfileHaloBleBeaconInterval,
                        cLApProfileFastHbTimerTimeout,
                        cLApProfilePrimaryDiscoveryTimeout,
                        cLApProfileBackupPrimaryControllerAddressType,
                        cLApProfileBackupPrimaryControllerAddress,
                        cLApProfileBackupPrimaryControllerName,
                        cLApProfileBackupSecondaryControllerAddressType,
                        cLApProfileBackupSecondaryControllerAddress,
                        cLApProfileBackupSecondaryControllerName,
                        cLApProfileBackupTertiaryControllerAddressType,
                        cLApProfileBackupTertiaryControllerAddress,
                        cLApProfileBackupTertiaryControllerName,
                        cLApProfileTcpMss,
                        cLApProfileRetransmitCount,
                        cLApProfileRetransmitTimeout,
                        cLApProfileLedState,
                        cLApProfileMulticastGroupAddressType,
                        cLApProfileMulticastGroupAddress,
                        cLApProfileMulticastMode,
                        cLApProfilePrimedJoinTimeout,
                        cLApProfilePreferMode,
                        cLApProfileApLagEnabled,
                        cLApProfile802dot1xSupplicantUsername,
                        cLApProfile802dot1xSupplicantPassword,
                        cLApProfileEncryptionEnable,
                        cLApProfileTelnetEnable,
                        cLApProfileSshEnable,
                        cLApProfileHyperlocationEnable,
                        cLApProfileHyperlocationDetectionThreshold,
                        cLApProfileHyperlocationResetThreshold,
                        cLApProfileHyperlocationTriggerThreshold,
                        cLApProfileHyperlocationNtpIpAddressType,
                        cLApProfileHyperlocationNtpIpAddress,
                        cLApProfileAdjustMss,
                        cLApProfileDiscoveryTimeout,
                        cLApProfileHeartBeatTimeout,
                        cLApProfileCdpEnable,
                        cLApProfileApPacketCaptureProfile,
                        cLApProfileRogueReportInterval,
                        cLApProfileRogueMinimumRssi,
                        cLApProfileRogueTransientInterval,
                        cLApProfileRogueContainFlexconnect,
                        cLApProfileRogueContainAutoRateEnable,
                        cLApProfileRogueDetectionEnable,
                        cLApProfileReportInterval24ghz,
                        cLApProfileReportInterval5ghz,
                        cLApProfileDot1xApSwitchEapAuth,
                        cLApProfileDot1xApSwtichLscAuth,
                        cLApProfileMeshProfileName,
                        cLApProfileUsbStatus,
                        cLApProfileExtModuleEnable,
                        cLApProfileStatsTimer,
                        cLApProfilePoePreStandardSwitchFlag,
                        cLApProfilePoePowerInjectorSelection,
                        cLApProfilePoeInjectorSwitchMac,
                        cLApProfileHaloBleBeaconAdvertisedPwr,
                        cLApProfileTftpDownGradeAddressType,
                        cLApProfileTftpDownGradeAddress,
                        cLApProfileTftpDownGradeFileName,
                        cLApProfileCoreDumpType,
                        cLApProfileCoreDumpTftpAddressType,
                        cLApProfileCoreDumpTftpAddress,
                        cLApProfileCoreDumpCoreFileName,
                        cLApProfileBackupFallbackEnabled
                    }
    STATUS          deprecated
    DESCRIPTION
        "This collection contains the information about the credentials
        of the 802.11 LWAPP Access Point that have joined the 
        Controller"
    ::= { ciscoLwappApMIBGroups 33 }

ciscoLwappApProfileQosMapGroup OBJECT-GROUP
    OBJECTS         {
                        cLApProfileQosMapRangeUP,
                        cLApProfileQosMapRangeDSCPLower,
                        cLApProfileQosMapRangeDSCPUpper,
                        cLApProfileQosMapRangeUPToDSCP,
                        cLApProfileQosMapRangeRowStatus,
                        cLApProfileQosMapExceptionDSCP,
                        cLApProfileQosMapExceptionUP,
                        cLApProfileQosMapExceptionRowStatus
                    }
    STATUS          current
    DESCRIPTION
        "This collection contains Hotspot QoS Map configuration for a
        specific AP profile. It lists the QoS Map DSCP to UP                    
        mappings and mappings exceptions for Aps                                
        that have joined the controller."
    ::= { ciscoLwappApMIBGroups 34 }

ciscoLwappApProfileGroupSup2 OBJECT-GROUP
    OBJECTS         {
                        cLApProfileRowStatus,
                        cLApProfileCredentialGlobalUserName,
                        cLApProfileCredentialGlobalPassword,
                        cLApProfileCredentialGlobalSecret,
                        cLApProfileLinkLatencyEnable,
                        cLApProfileHaloBleBeaconInterval,
                        cLApProfileFastHbTimerTimeout,
                        cLApProfilePrimaryDiscoveryTimeout,
                        cLApProfileBackupPrimaryControllerAddressType,
                        cLApProfileBackupPrimaryControllerAddress,
                        cLApProfileBackupPrimaryControllerName,
                        cLApProfileBackupSecondaryControllerAddressType,
                        cLApProfileBackupSecondaryControllerAddress,
                        cLApProfileBackupSecondaryControllerName,
                        cLApProfileBackupTertiaryControllerAddressType,
                        cLApProfileBackupTertiaryControllerAddress,
                        cLApProfileBackupTertiaryControllerName,
                        cLApProfileTcpMss,
                        cLApProfileRetransmitCount,
                        cLApProfileRetransmitTimeout,
                        cLApProfileLedState,
                        cLApProfileMulticastGroupAddressType,
                        cLApProfileMulticastGroupAddress,
                        cLApProfileMulticastMode,
                        cLApProfilePrimedJoinTimeout,
                        cLApProfilePreferMode,
                        cLApProfileApLagEnabled,
                        cLApProfile802dot1xSupplicantUsername,
                        cLApProfile802dot1xSupplicantPassword,
                        cLApProfileEncryptionEnable,
                        cLApProfileTelnetEnable,
                        cLApProfileSshEnable,
                        cLApProfileHyperlocationEnable,
                        cLApProfileHyperlocationDetectionThreshold,
                        cLApProfileHyperlocationResetThreshold,
                        cLApProfileHyperlocationTriggerThreshold,
                        cLApProfileHyperlocationNtpIpAddressType,
                        cLApProfileHyperlocationNtpIpAddress,
                        cLApProfileAdjustMss,
                        cLApProfileDiscoveryTimeout,
                        cLApProfileHeartBeatTimeout,
                        cLApProfileCdpEnable,
                        cLApProfileApPacketCaptureProfile,
                        cLApProfileRogueReportInterval,
                        cLApProfileRogueMinimumRssi,
                        cLApProfileRogueTransientInterval,
                        cLApProfileRogueContainFlexconnect,
                        cLApProfileRogueContainAutoRateEnable,
                        cLApProfileRogueDetectionEnable,
                        cLApProfileReportInterval24ghz,
                        cLApProfileReportInterval5ghz,
                        cLApProfileDot1xApSwitchEapAuth,
                        cLApProfileDot1xApSwtichLscAuth,
                        cLApProfileMeshProfileName,
                        cLApProfileUsbStatus,
                        cLApProfileExtModuleEnable,
                        cLApProfileStatsTimer,
                        cLApProfilePoePreStandardSwitchFlag,
                        cLApProfilePoePowerInjectorSelection,
                        cLApProfilePoeInjectorSwitchMac,
                        cLApProfileHaloBleBeaconAdvertisedPwr,
                        cLApProfileTftpDownGradeAddressType,
                        cLApProfileTftpDownGradeAddress,
                        cLApProfileTftpDownGradeFileName,
                        cLApProfileCoreDumpType,
                        cLApProfileCoreDumpTftpAddressType,
                        cLApProfileCoreDumpTftpAddress,
                        cLApProfileCoreDumpCoreFileName,
                        cLApProfileBackupFallbackEnabled,
                        cLApProfileClientRssiStatsEnabled,
                        cLApProfileClientRssiStatsReportInterval,
                        cLApProfileGasRateLimitEnable,
                        cLApProfileGasRateLimitNumReqPerInterval,
                        cLApProfileGasRateLimitIntervalMsec,
                        cLApProfileQoSMapApTrustsUpstreamDSCP
                    }
    STATUS          current
    DESCRIPTION
        "This collection contains the information about the credentials
        of the 802.11 LWAPP Access Point that have joined the 
        Controller"
    ::= { ciscoLwappApMIBGroups 35 }

ciscoLwappApGroupSup12 OBJECT-GROUP
    OBJECTS         {
                        cLApPowerStatus,
                        cLApNameServerAddressType,
                        cLApDataEncryptionStatus,
                        cLApNsiKey,
                        cLApPortNumber,
                        cLApVenueConfigVenueGroup,
                        cLApVenueConfigVenueType,
                        cLApVenueConfigVenueName,
                        cLApVenueConfigLanguage,
                        cLApLEDState,
                        cLApRealTimeStatsModeEnabled,
                        cLApTrunkVlan,
                        cLApTrunkVlanStatus,
                        cLApLocation,
                        cLApSubMode,
                        cLApAssocCount,
                        cLApAssocFailResourceCount,
                        cLApAssociatedClientCount,
                        cLApMemoryCurrentUsage,
                        cLApMemoryAverageUsage,
                        cLApCpuCurrentUsage,
                        cLApCpuAverageUsage,
                        cLApUpgradeFromVersion,
                        cLApUpgradeToVersion,
                        cLApUpgradeFailureCause,
                        cLApMaxClientLimitNumberTrap,
                        cLApMaxClientLimitCause,
                        cLApMaxClientLimitSet,
                        cLApFloorLabel,
                        cLApConnectCount,
                        cLApReassocSuccCount,
                        cLApReassocFailCount,
                        cLApAssocFailCountByRate,
                        cLApAbnormalOfflineCount,
                        cLApActiveClientCount,
                        cLApAssocFailCountForRssiLow,
                        cLApSysNetId,
                        cLApAssocFailTimes,
                        cLApHeartBeatRspAvgTime,
                        cLApEchoRequestCount,
                        cLApEchoResponseLossCount,
                        cLApModuleInserted,
                        cLApEnableModule,
                        cLApIsUniversal,
                        cLApUniversalPrimeStatus,
                        cLApIsMaster,
                        cLApBleFWDownloadStatus,
                        cLApDot11XorDartConnectorStatus,
                        cLApDot11IfAntennaTxEnable,
                        cLApDot11IfAntennaRxEnable,
                        cLApEthernetIfDuplex,
                        cLApEthernetIfLinkSpeed,
                        cLApEthernetIfPOEPower,
                        cLApEthernetIfRxTotalBytes,
                        cLApEthernetIfTxTotalBytes,
                        cLApEthernetIfInputCrc,
                        cLApEthernetIfInputAborts,
                        cLApEthernetIfInputErrors,
                        cLApEthernetIfInputFrames,
                        cLApEthernetIfInputOverrun,
                        cLApEthernetIfInputDrops,
                        cLApEthernetIfInputResource,
                        cLApEthernetIfUnknownProtocol,
                        cLApEthernetIfRunts,
                        cLApEthernetIfGiants,
                        cLApEthernetIfThrottle,
                        cLApEthernetIfResets,
                        cLApEthernetIfOutputCollision,
                        cLApEthernetIfOutputNoBuffer,
                        cLApEthernetIfOutputResource,
                        cLApEthernetIfOutputUnderrun,
                        cLApEthernetIfOutputErrors,
                        cLApEthernetIfOutputTotalDrops,
                        cLApDataLinkLatencyStatsCurrent,
                        cLApDataLinkLatencyStatsMin,
                        cLApDataLinkLatencyStatsMax,
                        cLApDataLinkLatencyTimeStamp,
                        cLApCtsSxpDefaultPassword,
                        cLApCtsSxpState,
                        cLApCtsSxpMode,
                        cLApCtsSxpListenerMinHoldtime,
                        cLApCtsSxpListenerMaxHoldtime,
                        cLApCtsSxpReconcilePeriod,
                        cLApCtsSxpRetryPeriod,
                        cLApCtsSxpSpeakerHoldTime,
                        cLApCtsSxpSpeakerKeepAlive,
                        cLApCtsInlineTagStatus,
                        cLApCtsSgaclStatus,
                        cLApCtsOverrideStatus,
                        cLApModeClear,
                        cLApSiteTagName,
                        cLApRfTagName,
                        cLApPolicyTagName,
                        cLApTagSource,
                        cLApUsbModuleName,
                        cLApUsbModuleState,
                        cLApUsbModuleProductId,
                        cLApUsbDescription,
                        cLApUsbStateInfo,
                        cLApUsbOverride,
                        cLApUsbSerialNumber,
                        cLApUsbMaxPower,
                        cLApLagConfigStatus,
                        cLApMonitorModeOptStatus,
                        cLApLegacyBeamForming,
                        cLApDot11IfLinkChangeCount,
                        cLApDot11MaxClients,
                        cLApPromiscuousModeDwelling,
                        cLApDot11IfStaKeepingTime,
                        cLApDot11IfLinkSpeed,
                        cLApDot11IfMtu,
                        cLApDot11IfDesc,
                        cLAPDot11IfMinTxPowerStep,
                        cLApDot11IfMaxDataRate,
                        cLApEthernetIfMtu,
                        cLApEthernetIfType,
                        cLApEthernetIfLinkChangeCount,
                        cLApWlanStatsTxPktNum,
                        cLApWlanStatsTxOctetNum,
                        cLApWlanStatsRxPktNum,
                        cLApWlanStatsRxOctetNum,
                        cLApWlanStatsRetransmitNum,
                        cLApWlanStatsAssocClientNum,
                        cLApWlanStatsOnlineUserNum,
                        cLApHyperlocationAdminState,
                        cLApHyperlocationUnsetFlag,
                        cLApOeapDisableLocalAccess,
                        cLApGlobalLEDState,
                        cLApRadioInterfaceShutdownEnabled,
                        cLApEthernetInterfaceDowntime,
                        cLAPMulticastGroupAddressType,
                        cLAPMulticastGroupAddress,
                        cLAPMulticastMode,
                        cLApGlobalAPLagCapability,
                        cLApGlobalAPDtlsVersion,
                        cLApGlobalAPDtlsCipherSuite,
                        cLApWlanInfoMaxClients,
                        cLApRadioWlanSsid,
                        cLApRadioWlanBssid,
                        cLApNwTxPowerThresholdVer2,
                        cLApDot11RadioStatsRxErrorFrameCount,
                        cLApDot11RadioStatsMacMicErrFrameCount,
                        cLApDot11RadioStatsMacDecryptErrFrameCount,
                        cLApDot11RadioStatsRxMgmtFrameCount,
                        cLApDot11RadioStatsRxCtrlFrameCount,
                        cLApDot11RadioStatsRxDataFrameCount,
                        cLApDot11RadioStatsTxMgmtFrameCount,
                        cLApDot11RadioStatsTxCtrlFrameCount,
                        cLApDot11RadioStatsTxDataFrameCount,
                        cLApDot11RadioStatsRxDataPacketCount,
                        cLApDot11RadioStatsTxDataPacketCount,
                        cLApDot11RadioStatsTxDataPacketCount,
                        cLApDot11RadioStatsRetryFrameCount,
                        cLApDot11RadioStatsRetryPacketCount,
                        cLApDot11RadioRssiHighest,
                        cLApDot11RadioRssiLowest,
                        cLApDot11RadioRssiAverage,
                        cLApCrashFileName,
                        cLApCrashFileSize,
                        cLApCrashFileTimeStamp,
                        cLApLEDFlashStatus,
                        cLApLEDFlashDuration,
                        cLApInetAddressType,
                        cLApInetAddress,
                        cLApStaticIpv6AddressEnabled,
                        cLApStaticIpv6InetAddressType,
                        cLApStaticIpv6InetAddress,
                        cLApStaticIpv6PrefixLength,
                        cLApStaticIpv6GatewayInetAddressType,
                        cLApStaticIpv6GatewayInetAddress,
                        cLApStaticIpNetmaskType,
                        cLApStaticIpNetmask,
                        cLApPreferMode,
                        cLApPreferModeApplied,
                        cLApSysMemType,
                        cLApSysMemSize,
                        cLApSysFlashSize,
                        cLApSysCpuType,
                        cLApSysFlashType,
                        cLApDot11RadioRateStatsRxPackets,
                        cLApDot11RadioRateStatsRxBytes,
                        cLApDot11RadioRateStatsTxPackets,
                        cLApDot11RadioRateStatsTxBytes,
                        cLApDot11RadioRateString,
                        cLApPacketDumpFtpServerAddressType,
                        cLApPacketDumpFtpServerAddress,
                        cLApPacketDumpFtpServerPath,
                        cLApPacketDumpFtpUsername,
                        cLApPacketDumpFtpPassword,
                        cLApPacketDumpClassifier,
                        cLApPacketDumpBufferSize,
                        cLApPacketDumpCaptureTime,
                        cLApPacketDumpTruncation,
                        cLApPacketDumpApName,
                        cLApPacketDumpDeviceMacAddress,
                        cLApPacketDumpStartStop,
                        cLApDot11RadioSsidName,
                        cLApCmMacAddress,
                        cLApCmApMacAddress,
                        cLApCmSwVersion,
                        cLApEthernetSpeed,
                        cLApEthernetStatus,
                        cLApCmStatus,
                        cLApCmSerialNumber,
                        cLApCmUsChannelStatus,
                        cLApCmDsChannelStatus,
                        cLApCmMaskBit,
                        cLApEnvTemperatureDegree,
                        cLApEnvTemperatureState,
                        cLApEnvOrientation,
                        cLApEnvPoeOutStatus,
                        cLApGpsLocationPresent,
                        cLApGpsLocationValid,
                        cLApGpsLatitude,
                        cLApGpsLongitude,
                        cLApGpsAltitude,
                        cLApGpsCollectionTime,
                        cLApRogueApMacAddress,
                        cLApDot11RadioChannelNumber,
                        cLApRogueApSsid,
                        cLApRogueType,
                        cLApWipsReason,
                        cLApWipsClear,
                        cLApIfUpDownFailureType,
                        cLApIfUpDownCause,
                        cLApIfUpDownFailureCode,
                        cLApAlarmSet,
                        cLApRogueClassType,
                        cLApRogueDetectedChannel,
                        cLApRSSI,
                        cLApSNR,
                        cLApDot11RadioCurrentChannel,
                        cLApAdhocRogue,
                        cLApRogueAPOnWiredNetwork,
                        cLApRogueMode,
                        cLApRogueIsClassifiedByRule,
                        cLApRogueClassifiedApMacAddress,
                        cLApRogueClassifiedRSSI,
                        cLAPPreviousMonitorMode,
                        cLAPCurrentMonitorMode,
                        cLApSsidKeyConfSsidA,
                        cLApSsidKeyConfKeyIdxA,
                        cLApSsidKeyConfSsidB,
                        cLApSsidKeyConfKeyIdxB,
                        cLApPreviousChannel,
                        cLApCurrentChannel,
                        cLApChannelCustomize,
                        cLApIfLoadChannelUtilization,
                        cLAPGroupVlanName,
                        cLApRuleName,
                        cLApSeverityScore,
                        cLApDot11XorRadioRoleChangeReason,
                        cLApDot11XorRadioBandChangeReason
                    }
    STATUS          deprecated
    DESCRIPTION
        "This supplemental collection of objects represents the
        information about the general attributes and functional
        parameters of those APs that have joined the
        controller."
    ::= { ciscoLwappApMIBGroups 36 }

ciscoLwappApGroupSup13 OBJECT-GROUP
    OBJECTS         {
                        cLApDot11IfPhyS80EightyChannelNumber,
                        cLApDot11IfRptncPresent,
                        cLApDot11IfDartPresent,
                        cLApFilterName
                    }
    STATUS          current
    DESCRIPTION
        "This collection of objects represents the information
        about radio information of APs that have joined the controller."
    ::= { ciscoLwappApMIBGroups 37 }

ciscoLwappApLanStatsGroupSup1 OBJECT-GROUP
    OBJECTS         { cLApLanPowerLevelId }
    STATUS          current
    DESCRIPTION
        "This collection represents Sardinia AP LAN stats
        information that have joined the controller."
    ::= { ciscoLwappApMIBGroups 38 }

ciscoLwappApProfileGroupSup3 OBJECT-GROUP
    OBJECTS         {
                        cLApProfileUdpliteState,
                        cLApProfileMethodListName
                    }
    STATUS          deprecated
    DESCRIPTION
        "This collection contains the information about the credentials
        of the 802.11 LWAPP Access Point that have joined the 
        Controller"
    ::= { ciscoLwappApMIBGroups 39 }

ciscoLwappApProfileHaloBleGroupSup1 OBJECT-GROUP
    OBJECTS         { cLApProfileHaloBleBeaconRowStatus }
    STATUS          current
    DESCRIPTION
        "This collection contains HALO BLE beacon configuration for a
        specific AP profile. It lists the HALO BLE beacon ID, UUID,
        transmission power, and status per beacon for HALO enabled APs
        that have joined the controller."
    ::= { ciscoLwappApMIBGroups 40 }

ciscoLwappAp11axGroup OBJECT-GROUP
    OBJECTS         {
                        cLAp11axDualRadioCapable,
                        cLAp11axRadioFRACapable,
                        cLAp11axDualRadioOperation,
                        cLAp11axDualRadioMode,
                        cLAp11axRadioRoleOperation,
                        cLAp11axRadioRole,
                        cLAp11axObssPdCapable,
			cLAp11axObssPdSrgCapable
                    }
    STATUS          current
    DESCRIPTION
        "This collection contains HALO BLE beacon configuration for a
        specific AP profile. It lists the HALO BLE beacon ID, UUID,
        transmission power, and status per beacon for HALO enabled APs
        that have joined the controller."
    ::= { ciscoLwappApMIBGroups 41 }

ciscoLwappApXorRadioGroupSup1 OBJECT-GROUP
    OBJECTS         {
                        cLApDot11XorRadioMode,
                        cLApDot11XorRadioBand,
                        cLApDot11XorRadioRoleAssignment,
                        ciscoLwappXorRadioRoleChangeEnabled,
                        cLApDot11IfSensorReachability,
                        cLApFraCoverageOverlapFactor,
                        cLApFraSuggestedMode,
                        cLApDot11IfDualRadioMode,
                        cLApDot11IfDualRadioCapable,
                        cLApDot11IfRadioFRACapable,
                        cLApDot11IfDualRadioOperation,
                        cLApDot11IfRadioRoleOperation,
                        cLApDot11IfRadioRole
                    }
    STATUS          deprecated
    DESCRIPTION
        "This collection of objects represents the information
        about the Xor Radios of those APs that have
        joined the controller."
    ::= { ciscoLwappApMIBGroups 42 }

ciscoLwappApProfileGroupSup4 OBJECT-GROUP
    OBJECTS         {
                        cLApProfileUdpliteState,
                        cLApProfileMethodListName,
                        cLApProfileWindowSize,
                        cLApProfileCredentialGlobalSecretType,
                        cLApProfileCredentialGlobalPasswordType,
                        cLApProfile802dot1xSupplicantPasswordType,
                        cLApProfileBssidEnableStats,
                        cLApProfileBssidStatsFrequency,
                        cLApProfilePersistentSsidBroadcastEnable,
                        cLApProfileDhcpFallback,
                        cLApProfileOeapRogueDetectionEnable,
                        cLApProfileOeapEncryptionEnable,
                        cLApProfileOeapLocalAccessEnable,
                        cLApProfileOeapProvSsidEnable,
                        cLApProfileCountryCode
                    }
    STATUS          current
    DESCRIPTION
        "This collection contains the information about the credentials
        of the 802.11 LWAPP Access Point that have joined the 
        Controller"
    ::= { ciscoLwappApMIBGroups 43 }

ciscoLwappApGroupSup14 OBJECT-GROUP
    OBJECTS         {
                        cLApPowerStatus,
                        cLApNameServerAddressType,
                        cLApDataEncryptionStatus,
                        cLApNsiKey,
                        cLApPortNumber,
                        cLApVenueConfigVenueGroup,
                        cLApVenueConfigVenueType,
                        cLApVenueConfigVenueName,
                        cLApVenueConfigLanguage,
                        cLApLEDState,
                        cLApRealTimeStatsModeEnabled,
                        cLApTrunkVlan,
                        cLApTrunkVlanStatus,
                        cLApLocation,
                        cLApSubMode,
                        cLApAssocCount,
                        cLApAssocFailResourceCount,
                        cLApAssociatedClientCount,
                        cLApMemoryCurrentUsage,
                        cLApMemoryAverageUsage,
                        cLApCpuCurrentUsage,
                        cLApCpuAverageUsage,
                        cLApUpgradeFromVersion,
                        cLApUpgradeToVersion,
                        cLApUpgradeFailureCause,
                        cLApMaxClientLimitNumberTrap,
                        cLApMaxClientLimitCause,
                        cLApMaxClientLimitSet,
                        cLApFloorLabel,
                        cLApReassocSuccCount,
                        cLApReassocFailCount,
                        cLApAssocFailCountByRate,
                        cLApAbnormalOfflineCount,
                        cLApActiveClientCount,
                        cLApAssocFailCountForRssiLow,
                        cLApSysNetId,
                        cLApAssocFailTimes,
                        cLApHeartBeatRspAvgTime,
                        cLApEchoRequestCount,
                        cLApEchoResponseLossCount,
                        cLApModuleInserted,
                        cLApEnableModule,
                        cLApIsUniversal,
                        cLApUniversalPrimeStatus,
                        cLApIsMaster,
                        cLApBleFWDownloadStatus,
                        cLApDot11XorDartConnectorStatus,
                        cLApDot11IfAntennaTxEnable,
                        cLApDot11IfAntennaRxEnable,
                        cLApEthernetIfDuplex,
                        cLApEthernetIfLinkSpeed,
                        cLApEthernetIfPOEPower,
                        cLApEthernetIfRxTotalBytes,
                        cLApEthernetIfTxTotalBytes,
                        cLApEthernetIfInputCrc,
                        cLApEthernetIfInputAborts,
                        cLApEthernetIfInputErrors,
                        cLApEthernetIfInputFrames,
                        cLApEthernetIfInputOverrun,
                        cLApEthernetIfInputDrops,
                        cLApEthernetIfInputResource,
                        cLApEthernetIfUnknownProtocol,
                        cLApEthernetIfRunts,
                        cLApEthernetIfGiants,
                        cLApEthernetIfThrottle,
                        cLApEthernetIfResets,
                        cLApEthernetIfOutputCollision,
                        cLApEthernetIfOutputNoBuffer,
                        cLApEthernetIfOutputResource,
                        cLApEthernetIfOutputUnderrun,
                        cLApEthernetIfOutputErrors,
                        cLApEthernetIfOutputTotalDrops,
                        cLApDataLinkLatencyStatsCurrent,
                        cLApDataLinkLatencyStatsMin,
                        cLApDataLinkLatencyStatsMax,
                        cLApDataLinkLatencyTimeStamp,
                        cLApCtsSxpDefaultPassword,
                        cLApCtsSxpState,
                        cLApCtsSxpMode,
                        cLApCtsSxpListenerMinHoldtime,
                        cLApCtsSxpListenerMaxHoldtime,
                        cLApCtsSxpReconcilePeriod,
                        cLApCtsSxpRetryPeriod,
                        cLApCtsSxpSpeakerHoldTime,
                        cLApCtsSxpSpeakerKeepAlive,
                        cLApCtsInlineTagStatus,
                        cLApCtsSgaclStatus,
                        cLApCtsOverrideStatus,
                        cLApModeClear,
                        cLApSiteTagName,
                        cLApRfTagName,
                        cLApPolicyTagName,
                        cLApTagSource,
                        cLApUsbModuleName,
                        cLApUsbModuleState,
                        cLApUsbModuleProductId,
                        cLApUsbDescription,
                        cLApUsbStateInfo,
                        cLApUsbOverride,
                        cLApUsbSerialNumber,
                        cLApUsbMaxPower,
                        cLApLagConfigStatus,
                        cLApMonitorModeOptStatus,
                        cLApLegacyBeamForming,
                        cLApDot11IfLinkChangeCount,
                        cLApDot11MaxClients,
                        cLApPromiscuousModeDwelling,
                        cLApDot11IfStaKeepingTime,
                        cLApDot11IfLinkSpeed,
                        cLApDot11IfMtu,
                        cLApDot11IfDesc,
                        cLAPDot11IfMinTxPowerStep,
                        cLApDot11IfMaxDataRate,
                        cLApEthernetIfMtu,
                        cLApEthernetIfType,
                        cLApEthernetIfLinkChangeCount,
                        cLApWlanStatsTxPktNum,
                        cLApWlanStatsTxOctetNum,
                        cLApWlanStatsRxPktNum,
                        cLApWlanStatsRxOctetNum,
                        cLApWlanStatsRetransmitNum,
                        cLApWlanStatsAssocClientNum,
                        cLApWlanStatsOnlineUserNum,
                        cLApHyperlocationAdminState,
                        cLApHyperlocationUnsetFlag,
                        cLApOeapDisableLocalAccess,
                        cLApGlobalLEDState,
                        cLApRadioInterfaceShutdownEnabled,
                        cLApEthernetInterfaceDowntime,
                        cLAPMulticastGroupAddressType,
                        cLAPMulticastGroupAddress,
                        cLAPMulticastMode,
                        cLApGlobalAPLagCapability,
                        cLApGlobalAPDtlsVersion,
                        cLApGlobalAPDtlsCipherSuite,
                        cLApWlanInfoMaxClients,
                        cLApRadioWlanSsid,
                        cLApRadioWlanBssid,
                        cLApNwTxPowerThresholdVer2,
                        cLApDot11RadioStatsRxErrorFrameCount,
                        cLApDot11RadioStatsMacMicErrFrameCount,
                        cLApDot11RadioStatsMacDecryptErrFrameCount,
                        cLApDot11RadioStatsRxMgmtFrameCount,
                        cLApDot11RadioStatsRxCtrlFrameCount,
                        cLApDot11RadioStatsRxDataFrameCount,
                        cLApDot11RadioStatsTxMgmtFrameCount,
                        cLApDot11RadioStatsTxCtrlFrameCount,
                        cLApDot11RadioStatsTxDataFrameCount,
                        cLApDot11RadioStatsRxDataPacketCount,
                        cLApDot11RadioStatsTxDataPacketCount,
                        cLApDot11RadioStatsTxDataPacketCount,
                        cLApDot11RadioStatsRetryFrameCount,
                        cLApDot11RadioStatsRetryPacketCount,
                        cLApDot11RadioRssiHighest,
                        cLApDot11RadioRssiLowest,
                        cLApDot11RadioRssiAverage,
                        cLApCrashFileName,
                        cLApCrashFileSize,
                        cLApCrashFileTimeStamp,
                        cLApLEDFlashStatus,
                        cLApLEDFlashDuration,
                        cLApInetAddressType,
                        cLApInetAddress,
                        cLApStaticIpv6AddressEnabled,
                        cLApStaticIpv6InetAddressType,
                        cLApStaticIpv6InetAddress,
                        cLApStaticIpv6PrefixLength,
                        cLApStaticIpv6GatewayInetAddressType,
                        cLApStaticIpv6GatewayInetAddress,
                        cLApStaticIpNetmaskType,
                        cLApStaticIpNetmask,
                        cLApPreferMode,
                        cLApPreferModeApplied,
                        cLApSysMemType,
                        cLApSysMemSize,
                        cLApSysFlashSize,
                        cLApSysCpuType,
                        cLApSysFlashType,
                        cLApDot11RadioRateStatsRxPackets,
                        cLApDot11RadioRateStatsRxBytes,
                        cLApDot11RadioRateStatsTxPackets,
                        cLApDot11RadioRateStatsTxBytes,
                        cLApDot11RadioRateString,
                        cLApPacketDumpFtpServerAddressType,
                        cLApPacketDumpFtpServerAddress,
                        cLApPacketDumpFtpServerPath,
                        cLApPacketDumpFtpUsername,
                        cLApPacketDumpFtpPassword,
                        cLApPacketDumpClassifier,
                        cLApPacketDumpBufferSize,
                        cLApPacketDumpCaptureTime,
                        cLApPacketDumpTruncation,
                        cLApPacketDumpApName,
                        cLApPacketDumpDeviceMacAddress,
                        cLApPacketDumpStartStop,
                        cLApDot11RadioSsidName,
                        cLApCmMacAddress,
                        cLApCmApMacAddress,
                        cLApCmSwVersion,
                        cLApEthernetSpeed,
                        cLApEthernetStatus,
                        cLApCmStatus,
                        cLApCmSerialNumber,
                        cLApCmUsChannelStatus,
                        cLApCmDsChannelStatus,
                        cLApCmMaskBit,
                        cLApEnvTemperatureDegree,
                        cLApEnvTemperatureState,
                        cLApEnvOrientation,
                        cLApEnvPoeOutStatus,
                        cLApGpsLocationPresent,
                        cLApGpsLocationValid,
                        cLApGpsLatitude,
                        cLApGpsLongitude,
                        cLApGpsAltitude,
                        cLApGpsCollectionTime,
                        cLApRogueApMacAddress,
                        cLApDot11RadioChannelNumber,
                        cLApRogueApSsid,
                        cLApRogueType,
                        cLApRogueDot11RadioBand,
                        cLApWipsReason,
                        cLApWipsClear,
                        cLApIfUpDownFailureType,
                        cLApIfUpDownCause,
                        cLApIfUpDownFailureCode,
                        cLApAlarmSet,
                        cLApRogueClassType,
                        cLApRogueDetectedChannel,
                        cLApRSSI,
                        cLApSNR,
                        cLApDot11RadioCurrentChannel,
                        cLApAdhocRogue,
                        cLApRogueAPOnWiredNetwork,
                        cLApRogueMode,
                        cLApRogueIsClassifiedByRule,
                        cLApRogueClassifiedApMacAddress,
                        cLApRogueClassifiedRSSI,
                        cLAPPreviousMonitorMode,
                        cLAPCurrentMonitorMode,
                        cLApSsidKeyConfSsidA,
                        cLApSsidKeyConfKeyIdxA,
                        cLApSsidKeyConfSsidB,
                        cLApSsidKeyConfKeyIdxB,
                        cLApPreviousChannel,
                        cLApCurrentChannel,
                        cLApChannelCustomize,
                        cLApIfLoadChannelUtilization,
                        cLAPGroupVlanName,
                        cLApRuleName,
                        cLApSeverityScore,
                        cLApDot11XorRadioRoleChangeReason,
                        cLApDot11XorRadioBandChangeReason,
                        cLApBrokenAntApName,
                        cLApBrokenAntInfo,
                        cLApIndoorMode,
                        cLApSlotWlanStatsTxPktNum,
                        cLApSlotWlanStatsTxOctetNum,
                        cLApSlotWlanStatsRxPktNum,
                        cLApSlotWlanStatsRxOctetNum,
                        cLApSlotWlanStatsRetransmitNum,
                        cLApSlotWlanStatsAssocClientNum,
                        cLApSlotWlanStatsOnlineUserNum
                    }
    STATUS          current
    DESCRIPTION
        "This supplemental collection of objects represents the
        information about the general attributes and functional
        parameters of those APs that have joined the
        controller."
    ::= { ciscoLwappApMIBGroups 44 }

ciscoLwappApXorRadioGroupSup2 OBJECT-GROUP
    OBJECTS         {
                        cLApDot11XorRadioMode,
                        cLApDot11XorRadioBand,
                        cLApDot11XorRadioRoleAssignment,
                        ciscoLwappXorRadioRoleChangeEnabled,
                        cLApDot11IfSensorReachability,
                        cLApFraCoverageOverlapFactor,
                        cLApFraSuggestedMode
                    }
    STATUS          current
    DESCRIPTION
        "This collection of objects represents the information
        about the Xor Radios of those APs that have
        joined the controller."
    ::= { ciscoLwappApMIBGroups 45 }

END


--%DNP%  MLC -Submitted MLC

--%DNP%  MTF -TRUE MTF

--%DNP%  NO REPLACEMENT =cLAdjChannelRogueEnabled 

--%DNP%  NO REPLACEMENT =cLApConnectCount 

--%DNP%  NO REPLACEMENT =cLApDot11IfDualRadioCapable 

--%DNP%  NO REPLACEMENT =cLApDot11IfDualRadioMode 

--%DNP%  NO REPLACEMENT =cLApDot11IfDualRadioOperation 

--%DNP%  NO REPLACEMENT =cLApDot11IfRadioFRACapable 

--%DNP%  NO REPLACEMENT =cLApDot11IfRadioRole 

--%DNP%  NO REPLACEMENT =cLApDot11IfRadioRoleOperation 

--%DNP%  NO REPLACEMENT =cLApExtensionChannel 

--%DNP%  NO REPLACEMENT =cLApLomEnabled 

--%DNP%  NO REPLACEMENT =cLApNwLegacyBeamForming 

--%DNP%  NO REPLACEMENT =cLApProfile802dot1xAuthenticationEnabled 

--%DNP%  NO REPLACEMENT =cLApProfileApCountryCode 

--%DNP%  NO REPLACEMENT =cLApProfileCredentialEnableGlobalCredentials 

--%DNP%  NO REPLACEMENT =cLApProfileEthernetInterfaceDowntime 

--%DNP%  NO REPLACEMENT =cLApProfileFastHbTimerEnabled 

--%DNP%  NO REPLACEMENT =cLApProfileOeapDisableLocalAccess 

--%DNP%  NO REPLACEMENT =cLApProfileRadioInterfaceShutdownEnabled 

--%DNP%  NO REPLACEMENT =cLApProfileVlanTagging 

--%DNP%  NO REPLACEMENT =cLApWipsEnable 

--%DNP%  NO REPLACEMENT =ciscoLwappApGroupSup10 

--%DNP%  NO REPLACEMENT =ciscoLwappApGroupSup12 

--%DNP%  NO REPLACEMENT =ciscoLwappApProfileGroup 

--%DNP%  NO REPLACEMENT =ciscoLwappApProfileGroupSup1 

--%DNP%  NO REPLACEMENT =ciscoLwappApProfileGroupSup3 

--%DNP%  NO REPLACEMENT =ciscoLwappApXorRadioGroup 

--%DNP%  NO REPLACEMENT =ciscoLwappApXorRadioGroupSup1
