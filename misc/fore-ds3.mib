------------------------------------------------------------------------
-- ($Id: fore-ds3.mib,v 1.37 1995/10/30 20:31:31 swbuild Exp $)
-- Copyright 1993-1995 by Fore Systems, Inc.

Fore-DS3-MIB DEFINITIONS ::= BEGIN

IMPORTS
	Counter, Gauge, IpAddress, TimeTicks	FROM RFC1155-SMI
	OBJECT-TYPE				FROM RFC1212
	asx					FROM Fore-Switch-MIB;
	

------------------------------------------------------------------------
-- The implementation of the foreDs3 tables is mandatory
-- for all switches that have DS3 port module.

foreDs3			OBJECT IDENTIFIER ::= { asx 3 }
ds3ConfGroup		OBJECT IDENTIFIER ::= { foreDs3 1 }
ds3StatsGroup		OBJECT IDENTIFIER ::= { foreDs3 2 }


------------------------------------------------------------------------
-- The DS3 configuration Group

ds3ConfTable OBJECT-TYPE
	SYNTAX	SEQUENCE OF Ds3ConfEntry
	ACCESS	not-accessible
	STATUS	mandatory
	DESCRIPTION
		"A table of DS3 switch port configuration information."
	::= { ds3ConfGroup 1 }

ds3ConfEntry OBJECT-TYPE
	SYNTAX	Ds3ConfEntry
	ACCESS	not-accessible
	STATUS	mandatory
	DESCRIPTION
		"A table entry containing DS3 configuration information for each port. Not 
		all RFC1407 configuration table variables are included, and some are modified."
	INDEX	{ ds3ConfBoard, ds3ConfModule, ds3ConfPort }
	::= { ds3ConfTable 1 }

Ds3ConfEntry ::=
	SEQUENCE {
		ds3ConfBoard		INTEGER,
		ds3ConfModule		INTEGER,
		ds3ConfPort		INTEGER,
		ds3LineType		INTEGER,		
		ds3LineCoding		INTEGER,
		ds3SendCode		INTEGER,
		ds3ReceiveCode		INTEGER,
		ds3LoopbackConfig	INTEGER,
		ds3TxClockSource	INTEGER,
		ds3RxScrambling		INTEGER,
		ds3TxScrambling		INTEGER,
		ds3LineStatus		INTEGER,
		ds3IdleUnassignedCells  INTEGER,
		ds3LineTypeFraming 	INTEGER,
		ds3LineLength		INTEGER	
}		


ds3ConfBoard OBJECT-TYPE
	SYNTAX	INTEGER
	ACCESS	read-only
	STATUS	mandatory
	DESCRIPTION
		"The index of this port's switch board."
	::= { ds3ConfEntry 1 }

ds3ConfModule OBJECT-TYPE
	SYNTAX	INTEGER
	ACCESS	read-only
	STATUS	mandatory
	DESCRIPTION
		"The network module of this port."
	::= { ds3ConfEntry 2 }

ds3ConfPort OBJECT-TYPE
	SYNTAX	INTEGER
	ACCESS	read-only
	STATUS	mandatory
	DESCRIPTION
		"The number of this port."
	::= { ds3ConfEntry 3 }

ds3LineType OBJECT-TYPE
	SYNTAX	INTEGER {
		ds3Other (1), 
		ds3M23 (2), 
		ds3SYNTRAN (3), 
		ds3CbitParity (4), 
		ds3ClearChannel (5)
		} 
	ACCESS	read-write
	STATUS	mandatory
	DESCRIPTION
		"This variable indicates the variety of DS3 C-bit application 
		implementing this interface. The type of interface affects the 
		interpretation of the usage and error statistics. This variable 
		is defined in the rfc1407 configuration table as dsx3LineType. 
		According to rfc1407, the different values are:
		ds3M23           specification: ANSI T1.107-1988
		ds3SYNTRAN       specification: ANSI T1.107-1988
		ds3CbitParity    specification: ANSI T1.107a-1989
		ds3CleatChannel  specification: ANSI T1.102-1987."
	DEFVAL { 4 }
	::= { ds3ConfEntry 4 }

ds3LineCoding OBJECT-TYPE
	SYNTAX	INTEGER {
		ds3Other (1), 
		ds3B3ZS (2)
		}
	ACCESS	read-only
	STATUS	mandatory
	DESCRIPTION
		"This variable describes the variety of Zero Code suppression used 
		on this interface, which in turn affects a number of its characteristics. 
		ds3B3ZS (2) refers to the use of specified pattern of normal bits and 
		bipolar violations which are used to replaced sequences of zero bits of 
		specified length. This variable is defined in the rfc1407 configuration 
		table as dsx3LineCoding."
	DEFVAL { 2 }
	::= { ds3ConfEntry 5 }

ds3SendCode OBJECT-TYPE
	SYNTAX	INTEGER {
		ds3SendNoCode (1),
		ds3SendLineCode (2),
		ds3SendPayloadCode (3),
		ds3SendResetCode (4),
		ds3SendDS1LoopCode (5),
		ds3SendTestPattern (6)
		}
	ACCESS	read-write
	STATUS	mandatory
	DESCRIPTION
		"This variable indicates what type of code is being sent across the DS3/E3
		interface by the device. 
		The values mean:
		ds3SendNoCode		sending looped or normal data
		ds3SendLineCode		sending request for a line loopback
		ds3SendPayloadCode	sending a request for a payload loopback (i.e. all 
					DS1/E1 in a DS3/E3 frame)
		ds3SendResetCode	sending a loopback deactivation request
		ds3SendDS1LoopCode	requesting to loopback a particular DS1/E1 within a 
					DS3/E3 frame
		ds3SendTestPattern	sending a test pattern."
	DEFVAL { 1 }
	::= { ds3ConfEntry 6 }

ds3ReceiveCode OBJECT-TYPE
	SYNTAX	INTEGER {
		ds3ReceiveNoCode (1),
		ds3ReceiveLineCode (2),
		ds3ReceivePayloadCode (3),
		ds3ReceiveResetCode (4),
		ds3ReceiveDS1LoopCode (5),
		ds3ReceiveTestPattern (6)
		}
	ACCESS	read-only
	STATUS	mandatory
	DESCRIPTION
		"This variable indicates the type of code that was received across the DS3/E3 
		interface. 
		The values mean:
		ds3ReceiveNoCode	receiving looped or normal data
		ds3ReceiveLineCode	receiving request for a line loopback
		ds3ReceivePayloadCode	receiving a request for a payload loopback (i.e. all  
					DS1/E1 in a DS3/E3 frame)
		ds3ReceiveResetCode	receiving a loopback deactivation request
		ds3ReceiveDS1LoopCode	receiving a request to loopback a particular DS1/E1 
					within a DS3/E3 frame
		ds3ReceiveTestPattern	receiving a test pattern."
	DEFVAL { 1 }
	::= { ds3ConfEntry 7 }

ds3LoopbackConfig OBJECT-TYPE
	SYNTAX	INTEGER {
		ds3NoLoop (1), 
		ds3CellLoop (2),
		ds3PayloadLoop (3),
		ds3DiagLoop (4),
                ds3LineLoop (5),
		ds3OtherLoop (6)
		}
	ACCESS	read-write
	STATUS	mandatory
	DESCRIPTION
		"This variable represents the loopback configuration of the DS3 interface. This 
		variable is defined in the rfc1407 configuration table as dsx3LoopbackConfig, 
		with slightly different values.
		ds3NoLoop (1) means that the interface is not in a loopback state.
		ds3CellLoop (2) means that cells that are processed by the receiving component 
		  are not written into the receive FIFO, but into the transmit FIFO for 
		  retransmission.
		ds3PayloadLoop (3) means that the receive signal is looped back for retransmission
		  after it has passed through the port's reframing function.	
		ds3DiagLoop (4) means that the transmit data stream is looped back to the receiver.
                ds3LineLoop (5) is only supported on series B and later netmods.
		ds3OtherLoop (6) means that the interface is in a loopback that is not defined 
		  here."
	DEFVAL { 1 }
	::= { ds3ConfEntry 8 }

ds3TxClockSource OBJECT-TYPE
	SYNTAX	INTEGER {
		rxTiming (1),
		localTiming (2)
		}
	ACCESS	read-write
	STATUS	mandatory
	DESCRIPTION
		"The source of the transmit clock."
	DEFVAL { 2 }
	::= { ds3ConfEntry 9 }

ds3RxScrambling OBJECT-TYPE
	SYNTAX	INTEGER {
		descrambling(1),
		noDescrambling(2)
		}
	ACCESS	read-write
	STATUS	mandatory
	DESCRIPTION
		"This variable indicates whether the information is being descrambled 
		on receiving. It should be set the same as the transmitting side." 
	DEFVAL { 2 }
	::= { ds3ConfEntry 10 }

ds3TxScrambling OBJECT-TYPE
	SYNTAX	INTEGER {
		scrambling(1),
		noScrambling(2)
		}
	ACCESS	read-write
	STATUS	mandatory
	DESCRIPTION
		"This variable indicates whether the information (48 octet payload) is being 
		scrambled before transmitting. It should be set the same as the receiving side."
	DEFVAL { 2 }
	::= { ds3ConfEntry 11 }

ds3LineStatus OBJECT-TYPE
	SYNTAX	INTEGER (1..2046)
	ACCESS	read-only
	STATUS	mandatory
	DESCRIPTION
		"This variable indicates the Line Status of the interface. A similar object is
		defined in the rfc1407 configuration table as dsx3LineStatus (the ds3RxFERF bit 
		is not defined in rfc1407) . The variable contains loopback state information 
		and failure state information. It is a bit map represented as a sum. The 
		ds3NoAlarm should be set if and only if no other flag is set.
		The various bit positions are:
                   1  No Alarm.
                   2  Receiving PLCP Yellow Alarm Indication.
                   4  Transmitting PLCP Yellow alarm indication.
                   8  Receiving PLCP LOF.
                  16  Receiving FERF.
                  32  Transmiting FERF.
                  64  Receiving AIS failure indication.
                 128  Receiving LOF failure indication.
                 256  Receiving LOS failure indication.
                 512  Loopback State.
                1024  Receiving a test pattern.
                2048  Other failures."
	DEFVAL { 1 }
	::= { ds3ConfEntry 12 }

ds3IdleUnassignedCells OBJECT-TYPE
	SYNTAX	INTEGER {
		unassigned(1),
		idle(2)
		}
	ACCESS	read-write
	STATUS	mandatory
	DESCRIPTION
		"This variable indicates the types of cells that  should be sent 
		in case there is no real data to send. According to the ATM Forum, 
		Unassigned cells should be sent (octet 1-3 are 0's, octet 4 is 
		0000xxx0, where x is 'don't care'). According to the CCITT 
		specifications, Idle cells should be sent (everything is '0' except 
		for the CLP bit which is '1'). By default, unassigned cells are 
		transmitted is case there is no data to send."
	DEFVAL { 1 }
	::= { ds3ConfEntry 13 }

ds3LineTypeFraming OBJECT-TYPE
	SYNTAX	INTEGER {
		ds3Hcs (1), 
		ds3Plcp (2)
		} 
	ACCESS	read-write
	STATUS	mandatory
	DESCRIPTION
		"This variable indicates the way ATM cells are constructed 
		from the DS3 stream. ds3Hcs(1) indicates that the ATM cells
		are constructed upon the Header Check Sequence (HCS) inside the
		ATM cell header. ds3Plcp(2) indicates that the ATM cells
		are constructed from the DS3 PLCP (Physical Layer Convergence
		Protocol) bits."
	DEFVAL { 1 }
	::= { ds3ConfEntry 14 }

ds3LineLength OBJECT-TYPE
        SYNTAX  INTEGER {
                ds3LineLt225 (1),
                ds3LineGt225 (2)
        }
        ACCESS  read-write
        STATUS  mandatory
        DESCRIPTION
                "This variable represents the length of the physical cable
                connected to the ds3 port. The user has to set this object to 
		match the physical cable in order to get the netmod to receive 
		the signal on the cable. The different values are:
                ds3LineLt225 (1) means the line is shorter than 225 ft,
                ds1LineGt225 (2) means the line length is greater than
		220 ft."
        DEFVAL { 2 }
        ::= { ds3ConfEntry 15 }

------------------------------------------------------------------------
-- The DS3 Statistics Group

ds3FramingTable OBJECT-TYPE
	SYNTAX	SEQUENCE OF Ds3FramingEntry
	ACCESS	not-accessible
	STATUS	mandatory
	DESCRIPTION
		"A table of DS3 framing statistics information."
	::= { ds3StatsGroup 1 }

ds3FramingEntry OBJECT-TYPE
	SYNTAX	Ds3FramingEntry
	ACCESS	not-accessible
	STATUS	mandatory
	DESCRIPTION
		"A table entry containing DS3 framing statistics information."
	INDEX	{ ds3FramingBoard, ds3FramingModule, ds3FramingPort }
	::= { ds3FramingTable 1 }

Ds3FramingEntry ::=
	SEQUENCE {
		ds3FramingBoard		INTEGER,
		ds3FramingModule	INTEGER,
		ds3FramingPort		INTEGER,

		ds3FramingLOSs		Counter,
		ds3FramingLCVs		Counter,
		ds3FramingSumLCVs	Counter,
		ds3FramingFERRs		Counter,
		ds3FramingOOFs		Counter,
		ds3FramingFERFs		Counter,
		ds3FramingAISs		Counter,
		ds3FramingPbitPERRs	Counter,

		ds3FramingCbitPERRs	Counter,
		ds3FramingFEBEs		Counter
	}

ds3FramingBoard OBJECT-TYPE
	SYNTAX	INTEGER
	ACCESS	read-only
	STATUS	mandatory
	DESCRIPTION
		"The index of this port's switch board."
	::= { ds3FramingEntry 1 }

ds3FramingModule OBJECT-TYPE
	SYNTAX	INTEGER
	ACCESS	read-only
	STATUS	mandatory
	DESCRIPTION
		"The network module of this port."
	::= { ds3FramingEntry 2 }

ds3FramingPort OBJECT-TYPE
	SYNTAX	INTEGER
	ACCESS	read-only
	STATUS	mandatory
	DESCRIPTION
		"The number of this port."
	::= { ds3FramingEntry 3 }

ds3FramingLOSs OBJECT-TYPE
	SYNTAX	Counter
	ACCESS	read-only
	STATUS	mandatory
	DESCRIPTION
		"The number of seconds in which Loss Of Signal (LOS) errors were detected 
		by the DS3 Receive Framer block."
	::= { ds3FramingEntry 4 }

ds3FramingLCVs OBJECT-TYPE
	SYNTAX	Counter
	ACCESS	read-only
	STATUS	mandatory
	DESCRIPTION
		"The number of Line Code Violations (LCV) that were detected by the DS3 
		Receive Framer block."
	::= { ds3FramingEntry 5 }

ds3FramingSumLCVs OBJECT-TYPE
	SYNTAX	Counter
	ACCESS	read-only
	STATUS	mandatory
	DESCRIPTION
		"The number of DS3 information blocks (85 bits) which contain one or more 
		Line Code Violations (LCV)."
	::= { ds3FramingEntry 6 }

ds3FramingFERRs OBJECT-TYPE
	SYNTAX	Counter
	ACCESS	read-only
	STATUS	mandatory
	DESCRIPTION
		"Number of DS3 framing error (FERR) events."
	::= { ds3FramingEntry 7 }

ds3FramingOOFs OBJECT-TYPE
	SYNTAX	Counter
	ACCESS	read-only
	STATUS	mandatory
	DESCRIPTION
		"Number of seconds DS3 Out Of Frame (OOF) error events were experienced."
	::= { ds3FramingEntry 8 }

ds3FramingFERFs OBJECT-TYPE
	SYNTAX	Counter
	ACCESS	read-only
	STATUS	mandatory
	DESCRIPTION
		"The number of seconds in which Far End Receive Failure (FERF) state has  
		been detected by the DS3 Receive Framer block. FERF signal alerts the upstream 
		terminal that a failure has been detected along the downstream line."
	::= { ds3FramingEntry 9 }

ds3FramingAISs OBJECT-TYPE
	SYNTAX	Counter
	ACCESS	read-only
	STATUS	mandatory
	DESCRIPTION
		"The number of seconds in which Alarm Indication Signals (AIS) were 
		detected by the DS3 Receive Framer block. AIS indicates that an upstream 
		failure has been detected by the far end."
	::= { ds3FramingEntry 10 }

ds3FramingPbitPERRs OBJECT-TYPE
	SYNTAX	Counter
	ACCESS	read-only
	STATUS	mandatory
	DESCRIPTION
		"Number of P-bit parity error (PERR) events."
	::= { ds3FramingEntry 11 }

ds3FramingCbitPERRs OBJECT-TYPE
	SYNTAX	Counter
	ACCESS	read-only
	STATUS	mandatory
	DESCRIPTION
		"Number of C-bit parity error (PERR) events."
	::= { ds3FramingEntry 12 }

ds3FramingFEBEs OBJECT-TYPE
	SYNTAX	Counter
	ACCESS	read-only
	STATUS	mandatory
	DESCRIPTION
		"Number of DS3 far end block error (FEBE) events."
	::= { ds3FramingEntry 13 }

------------------------------------------------------------------------

ds3PlcpTable OBJECT-TYPE
	SYNTAX	SEQUENCE OF Ds3PlcpEntry
	ACCESS	not-accessible
	STATUS	mandatory
	DESCRIPTION
		"A table of DS3 Physical Layer Convergence Protocol (Procedure) statistics 
		information."
	::= { ds3StatsGroup 2 }

ds3PlcpEntry OBJECT-TYPE
	SYNTAX	Ds3PlcpEntry
	ACCESS	not-accessible
	STATUS	mandatory
	DESCRIPTION
		"A table entry containing DS3 PLCP statistics information."
	INDEX	{ ds3PlcpBoard, ds3PlcpModule, ds3PlcpPort }
	::= { ds3PlcpTable 1 }

Ds3PlcpEntry ::=
	SEQUENCE {
		ds3PlcpBoard		INTEGER,
		ds3PlcpModule		INTEGER,
		ds3PlcpPort		INTEGER,

		ds3PlcpFERRs		Counter,
		ds3PlcpLOFs		Counter,
		ds3PlcpBIP8s		Counter,
		ds3PlcpFEBEs		Counter,
		ds3PlcpYellows		Counter
	}

ds3PlcpBoard OBJECT-TYPE
	SYNTAX	INTEGER
	ACCESS	read-only
	STATUS	mandatory
	DESCRIPTION
		"The index of this port's switch board."
	::= { ds3PlcpEntry 1 }

ds3PlcpModule OBJECT-TYPE
	SYNTAX	INTEGER
	ACCESS	read-only
	STATUS	mandatory
	DESCRIPTION
		"The network module of this port."
	::= { ds3PlcpEntry 2 }

ds3PlcpPort OBJECT-TYPE
	SYNTAX	INTEGER
	ACCESS	read-only
	STATUS	mandatory
	DESCRIPTION
		"The number of this port."
	::= { ds3PlcpEntry 3 }

ds3PlcpFERRs OBJECT-TYPE
	SYNTAX	Counter
	ACCESS	read-only
	STATUS	mandatory
	DESCRIPTION
		"Number of Physical Layer Convergence Protocol (PLCP) octet error events."
	::= { ds3PlcpEntry 4 }

ds3PlcpLOFs OBJECT-TYPE
	SYNTAX	Counter
	ACCESS	read-only
	STATUS	mandatory
	DESCRIPTION
		"The number of seconds in which Loss Of Frame (LOF) errors were detected 
		by the PLCP (Physical Layer Convergence Protocol) receiver. LOF is declared 
		when an Out-Of-Frame state persists for more than 1ms. LOF is removed when 
		in-frame state persists for more than 12ms."
	::= { ds3PlcpEntry 5 }

ds3PlcpBIP8s OBJECT-TYPE
	SYNTAX	Counter
	ACCESS	read-only
	STATUS	mandatory
	DESCRIPTION
		"Number of BIP-8 (Bit Interleaved Parity - 8) error events. The BIP-8 is 
		calculated over the Path Overhead field and the associated ATM cell of the 
		previous frame. A BIP-N is a method of error monitoring. An N bit code is 
		generated by the transmitting equipment in such a manner that the first bit 
		of the code provides even parity over the first bit of all N-bit sequences 
		in the previous VT SPE, the second bit provides even parity over the second 
		bits of all N-bit sequences within the specified portion, etc."
	::= { ds3PlcpEntry 6 }

ds3PlcpFEBEs OBJECT-TYPE
	SYNTAX	Counter
	ACCESS	read-only
	STATUS	mandatory
	DESCRIPTION
		"Number of ATM Far End Block Error (FEBE) events."
	::= { ds3PlcpEntry 7 }

ds3PlcpYellows OBJECT-TYPE
	SYNTAX	Counter
	ACCESS	read-only
	STATUS	mandatory
	DESCRIPTION
		"The number of seconds in which Yellow alarm errors were detected by the 
		PLCP (Physical Layer Convergence Protocol) receiver. Yellow alarm is asserted 
		when 10 consecutive yellow signal bits are set to logical 1. Yellow signals 
		are used to alert upstream terminals of a downstream failure in order to 
		initiate trunk conditioning on the failure circuit."
	::= { ds3PlcpEntry 8 }

------------------------------------------------------------------------

ds3AtmTable OBJECT-TYPE
	SYNTAX	SEQUENCE OF Ds3AtmEntry
	ACCESS	not-accessible
	STATUS	mandatory
	DESCRIPTION
		"A table of DS3 ATM statistics information."
	::= { ds3StatsGroup 3 }

ds3AtmEntry OBJECT-TYPE
	SYNTAX	Ds3AtmEntry
	ACCESS	not-accessible
	STATUS	mandatory
	DESCRIPTION
		"A table entry containing DS3 ATM statistics information."
	INDEX	{ ds3AtmBoard, ds3AtmModule, ds3AtmPort }
	::= { ds3AtmTable 1 }

Ds3AtmEntry ::=
	SEQUENCE {
		ds3AtmBoard		INTEGER,
		ds3AtmModule		INTEGER,
		ds3AtmPort		INTEGER,

		ds3AtmHCSs		Counter,
		ds3AtmRxCells		Counter,
		ds3AtmTxCells		Counter
	}

ds3AtmBoard OBJECT-TYPE
	SYNTAX	INTEGER
	ACCESS	read-only
	STATUS	mandatory
	DESCRIPTION
		"The index of this port's switch board."
	::= { ds3AtmEntry 1 }

ds3AtmModule OBJECT-TYPE
	SYNTAX	INTEGER
	ACCESS	read-only
	STATUS	mandatory
	DESCRIPTION
		"The network module of this port."
	::= { ds3AtmEntry 2 }

ds3AtmPort OBJECT-TYPE
	SYNTAX	INTEGER
	ACCESS	read-only
	STATUS	mandatory
	DESCRIPTION
		"The number of this port."
	::= { ds3AtmEntry 3 }

ds3AtmHCSs OBJECT-TYPE
	SYNTAX	Counter
	ACCESS	read-only
	STATUS	mandatory
	DESCRIPTION
		"Number of header check sequence (HCS) error events. The HCS is a CRC-8 
		calculation over the first 4 octets of the ATM cell header."
	::= { ds3AtmEntry 4 }

ds3AtmRxCells OBJECT-TYPE
	SYNTAX	Counter
	ACCESS	read-only
	STATUS	mandatory
	DESCRIPTION
		"Number of ATM cells that were received."
	::= { ds3AtmEntry 5 }

ds3AtmTxCells OBJECT-TYPE
	SYNTAX	Counter
	ACCESS	read-only
	STATUS	mandatory
	DESCRIPTION
		"Number of non-null ATM cells that were transmitted."
	::= { ds3AtmEntry 6 }

END
