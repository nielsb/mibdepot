------------------------------------------------------------------------
-- @(#)$Id $
-- Copyright 1993, 1994, 1995 by Fore Systems, Inc.

Fore-DS1-MIB DEFINITIONS ::= BEGIN

IMPORTS
	Counter, Gauge, IpAddress, TimeTicks	FROM RFC1155-SMI
	OBJECT-TYPE				FROM RFC1212
	asx					FROM Fore-Switch-MIB;
	

------------------------------------------------------------------------
-- The implementation of the foreDs1 tables is mandatory
-- for all switches that have DS1 port module.

foreDs1			OBJECT IDENTIFIER ::= { asx 7 }
ds1ConfGroup		OBJECT IDENTIFIER ::= { foreDs1 1 }
ds1StatsGroup		OBJECT IDENTIFIER ::= { foreDs1 2 }


------------------------------------------------------------------------
-- The DS1 configuration Group

ds1ConfTable OBJECT-TYPE
	SYNTAX	SEQUENCE OF Ds1ConfEntry
	ACCESS	not-accessible
	STATUS	mandatory
	DESCRIPTION
		"A table of DS1 switch port configuration information."
	::= { ds1ConfGroup 1 }

ds1ConfEntry OBJECT-TYPE
	SYNTAX	Ds1ConfEntry
	ACCESS	not-accessible
	STATUS	mandatory
	DESCRIPTION
		"A table entry containing DS1 configuration information for each port. 
		Not all RFC1406 configuration table variables are included, and some 
		are modified."
	INDEX	{ ds1ConfBoard, ds1ConfModule, ds1ConfPort }
	::= { ds1ConfTable 1 }

Ds1ConfEntry ::=
	SEQUENCE {
		ds1ConfBoard		INTEGER,
		ds1ConfModule		INTEGER,
		ds1ConfPort		INTEGER,
                ds1LineType             INTEGER,
		ds1LineCoding		INTEGER,
		ds1SendCode		INTEGER,
		ds1ReceiveCode		INTEGER,
		ds1LoopbackConfig	INTEGER,
		ds1TxClockSource	INTEGER,
		ds1LineStatus		INTEGER,
		ds1IdleUnassignedCells  INTEGER,
		ds1LineTypeFraming 	INTEGER,	
		ds1LineLength		INTEGER
}		


ds1ConfBoard OBJECT-TYPE
	SYNTAX	INTEGER
	ACCESS	read-only
	STATUS	mandatory
	DESCRIPTION
		"The index of this port's switch board."
	::= { ds1ConfEntry 1 }

ds1ConfModule OBJECT-TYPE
	SYNTAX	INTEGER
	ACCESS	read-only
	STATUS	mandatory
	DESCRIPTION
		"The network module of this port."
	::= { ds1ConfEntry 2 }

ds1ConfPort OBJECT-TYPE
	SYNTAX	INTEGER
	ACCESS	read-only
	STATUS	mandatory
	DESCRIPTION
		"The number of this port."
	::= { ds1ConfEntry 3 }

ds1LineType OBJECT-TYPE
	SYNTAX	INTEGER {
		ds1Other (1), 
		ds1ESF (2), 
		ds1D4 (3)
		} 
	ACCESS	read-only
	STATUS	mandatory
	DESCRIPTION
		"This variable indicates the variety of DS1 Line implementing 
		this circuit. The type of circuit affects the number of bits 
		per second that the circuit can reasonably carry, as well as 
		the interpretation of the usage and error statistics. This 
		variable is defined in the rfc1406 configuration table as 
		dsx1LineType. According to rfc1406, the different values are:
		ds1ESF           Extended SuperFrame DS1
		ds1D4		 AT&T D4 format DS1."
	::= { ds1ConfEntry 4 }


ds1LineCoding OBJECT-TYPE
	SYNTAX	INTEGER {
		ds1Other (1), 
		ds1JBZS (2),
		ds1B8ZS (3),
		ds1HDB3 (4),
		ds1ZBTSI (5),
		ds1AMI (6)
		}
	ACCESS	read-only
	STATUS	mandatory
	DESCRIPTION
		"This variable describes the variety of Zero Code suppression used 
		on this link, which in turn affects a number of its characteristics. 
		ds1B8ZS (2) refers to the use of specified pattern of normal bits 
		and bipolar violations which are used to replaced sequences of eight 
		zero bits. This variable is defined in the rfc1406 configuration 
		table as dsx1LineCoding."
	::= { ds1ConfEntry 5 }

ds1SendCode OBJECT-TYPE
	SYNTAX	INTEGER {
		ds1SendNoCode (1),
		ds1SendLineCode (2),
		ds1SendPayloadCode (3),
		ds1SendResetCode (4),
		ds1SendQRS (5),
		ds1Send511Pattern (6),
		ds1Send3in24Pattern (7),
		ds1SendOtherTestPattern (8)
		}
	ACCESS	read-only
	STATUS	mandatory
	DESCRIPTION
		"This variable indicates what type of code is being sent across the DS1
		interface by the device. 
		The values mean:
		ds1SendNoCode		sending looped or normal data
		ds1SendLineCode		sending request for a line loopback
		ds1SendPayloadCode	sending a request for a payload loopback
		ds1SendResetCode	sending a loopback termination request
		ds1SendQRS		sending a Quasi-Random Signal (QRS) test pattern
		ds1Send511Pattern	sending a 511 bit fixed test pattern
		ds1Send3in24Pattern	sending a fixed test pattern of 3 bits set in 24
		ds1SendTestPattern	sending a test pattern other than the above."
	::= { ds1ConfEntry 6 }

ds1ReceiveCode OBJECT-TYPE
	SYNTAX	INTEGER {
		ds1ReceiveNoCode (1),
		ds1ReceiveLineCode (2),
		ds1ReceivePayloadCode (3),
		ds1ReceiveResetCode (4),
		ds1SendQRS (5),
		ds1Send511Pattern (6),
		ds1Send3in24Pattern (7),
		ds1SendOtherTestPattern (8)
		}
	ACCESS	read-only
	STATUS	mandatory
	DESCRIPTION
		"This variable indicates the type of code that was received across the DS
		interface. 
		The values mean:
		ds1ReceiveNoCode	receiving looped or normal data
		ds1ReceiveLineCode	receiving request for a line loopback
		ds1ReceivePayloadCode	receiving a request for a payload loopback
		ds1ReceiveResetCode	receiving a loopback deactivation request
		ds1ReceiveQRS		receiving a Quasi-Random Signal (QRS) test pattern
		ds1Receive511Pattern	receiving a 511 bit fixed test pattern
		ds1Receive3in24Pattern	receiving a fixed test pattern of 3 bits set in 24
		ds1ReceiveTestPattern	receiving a test pattern other than the above."
	::= { ds1ConfEntry 7 }

ds1LoopbackConfig OBJECT-TYPE
	SYNTAX	INTEGER {
		ds1NoLoop (1), 
		ds1LineLoop (2),
		ds1PayloadLoop (3),
		ds1DiagLoop (4),
		ds1OtherLoop (5)
		}
	ACCESS	read-write
	STATUS	mandatory
	DESCRIPTION
		"This variable represents the loopback configuration of the DS1 
		interface. This variable is defined in the rfc1406 configuration 
		table as dsx1LoopbackConfig, with slightly different values.
		ds1NoLoop (1) means that the interface is not in a loopback state.
		ds1LineLoop (2) means that cells that are processed by the receiving 
			component are not written into the receive FIFO, but into the 
			transmit FIFO for  retransmission.
		ds1PayloadLoop (3) means that the receive signal is looped back for 
			retransmission after it has passed through the port's reframing 
			function.	
		ds1DiagLoop (4) means that the transmit data stream is looped back to 
			the receiver.
		ds1OtherLoop (5) means that the interface is in a loopback that is not 
			defined here."
	DEFVAL { 1 }
	::= { ds1ConfEntry 8 }

ds1TxClockSource OBJECT-TYPE
	SYNTAX	INTEGER {
		rxTiming (1),
		localTiming (2)
		}
	ACCESS	read-write
	STATUS	mandatory
	DESCRIPTION
		"The source of the transmit clock. rxTiming(1) indicated that the 
		recovered receive clock is used as the transmit clock. localTiming(2)
		indicates that a local source clock is used as the transmit clock.
		To determine which local source clock is used advise the ntGlobalClock
		in the netmodTimingTable for this netmod (refer to the Fore-Switch-MIB 
		for more information)."
	DEFVAL { 2 }
	::= { ds1ConfEntry 9 }

ds1LineStatus OBJECT-TYPE
	SYNTAX	INTEGER (1..2046)
	ACCESS	read-only
	STATUS	mandatory
	DESCRIPTION
		"This variable indicates the Line Status of the interface. A similar 
		object is defined in the rfc1406 configuration table as dsx1LineStatus. 
		The variable contains loopback state information and failure state 
		information. It is a bit map represented as a sum. The ds1NoAlarm should 
		be set if and only if no other flag is set.
		The various bit positions are:
		   1  No Alarm.
		   2  Receiving PLCP Yellow Alarm Indication.
		   4  Transmitting PLCP Yellow alarm indication.
		   8  Receiving PLCP LOF.
		  16  Receiving DS1 Yellow Alarm Indication.
		  32  Transmiting DS1 Yellow Alarm Indication.
		  64  Receiving AIS failure indication.
		 128  Receiving LOF failure indication.
		 256  Receiving LOS failure indication.
		 512  Loopback State.
		 1024 Receiving a test pattern.
		 2048 Other failures."
	::= { ds1ConfEntry 12 }

ds1IdleUnassignedCells OBJECT-TYPE
	SYNTAX	INTEGER {
		unassigned(1),
		idle(2)
		}
	ACCESS	read-write
	STATUS	mandatory
	DESCRIPTION
		"This variable indicates the types of cells that should be sent 
		in case there is no real data to send. According to the ATM Forum, 
		Unassigned cells should be sent (octet 1-3 are 0's, octet 4 is 
		0000xxx0, where x is 'don't care'). According to the CCITT 
		specifications, Idle cells should be sent (everything is '0' except 
		for the CLP bit which is '1'). By default, unassigned cells are 
		transmitted is case there is no data to send."
	DEFVAL { 1 }
	::= { ds1ConfEntry 13 }

ds1LineTypeFraming OBJECT-TYPE
	SYNTAX	INTEGER {
		other (1),
		ds1Hcs (2),
                ds1Plcp (3)
		} 
	ACCESS	read-write
	STATUS	mandatory
	DESCRIPTION
		"This variable indicates the way ATM cells are constructed 
		from the DS1 stream. ds1Hcs(2) indicates that the ATM cells
		are constructed upon the Header Check Sequence (HCS) inside the
		ATM cell header. ds1Plcp(3) indicates that the ATM cells 
                are constructed from the DS1 PLCP (Physical Layer Convergence
                Protocol) bits."
	::= { ds1ConfEntry 14 }

ds1LineLength OBJECT-TYPE
	SYNTAX	INTEGER {
		ds1LineLt110 (1),
		ds1Line110-220 (2),
		ds1Line220-330 (3),
		ds1Line330-440 (4),
		ds1Line440-550 (5),
		ds1Line550-660 (6),
		ds1LineGt655 (7)
	}
	ACCESS	read-write
	STATUS	mandatory
	DESCRIPTION
		"This variable represents the length of the physical cable
	 	connected to the ds1 port. The user has to set this object to match
		the physical cable in order to get the netmod to receive the signal
		on the cable. The different values are:
		ds1LineLt110 (1) means the line is shorter than 110 ft,
		ds1Line110-220 (2) means the line length is between 110 and 220 ft,
		ds1Line220-330 (3) means the line length is between 220 and 330 ft,
		ds1Line330-440 (4) means the line length is between 330 and 440 ft,
		ds1Line440-550 (5) means the line length is between 440 and 550 ft,
		ds1Line550-660 (6) means the line length is between 550 and 660 ft,
		ds1LineGt655 (7) means the line is longer than 655 ft."
	DEFVAL { 1 }
	::= { ds1ConfEntry 15 }

------------------------------------------------------------------------
-- The DS1 Statistics Group

ds1FramingTable OBJECT-TYPE
	SYNTAX	SEQUENCE OF Ds1FramingEntry
	ACCESS	not-accessible
	STATUS	mandatory
	DESCRIPTION
		"A table of DS1 framing statistics information."
	::= { ds1StatsGroup 1 }

ds1FramingEntry OBJECT-TYPE
	SYNTAX	Ds1FramingEntry
	ACCESS	not-accessible
	STATUS	mandatory
	DESCRIPTION
		"A table entry containing DS1 framing statistics information."
	INDEX	{ ds1FramingBoard, ds1FramingModule, ds1FramingPort }
	::= { ds1FramingTable 1 }

Ds1FramingEntry ::=
	SEQUENCE {
		ds1FramingBoard		INTEGER,
		ds1FramingModule	INTEGER,
		ds1FramingPort		INTEGER,

		ds1FramingLOSs		Counter,
		ds1FramingLCVs		Counter,
		ds1FramingFERRs		Counter,
		ds1FramingOOFs		Counter,
		ds1FramingAISs		Counter,

		ds1FramingB8ZSPatterns	Counter,
		ds1Framing8Zeros	Counter,
		ds1Framing16Zeros	Counter,
		ds1FramingYellowAlarms	Counter,
		ds1FramingRedAlarms	Counter,
		ds1FramingBEEs		Counter
	}

ds1FramingBoard OBJECT-TYPE
	SYNTAX	INTEGER
	ACCESS	read-only
	STATUS	mandatory
	DESCRIPTION
		"The index of this port's switch board."
	::= { ds1FramingEntry 1 }

ds1FramingModule OBJECT-TYPE
	SYNTAX	INTEGER
	ACCESS	read-only
	STATUS	mandatory
	DESCRIPTION
		"The network module of this port."
	::= { ds1FramingEntry 2 }

ds1FramingPort OBJECT-TYPE
	SYNTAX	INTEGER
	ACCESS	read-only
	STATUS	mandatory
	DESCRIPTION
		"The number of this port."
	::= { ds1FramingEntry 3 }

ds1FramingLOSs OBJECT-TYPE
	SYNTAX	Counter
	ACCESS	read-only
	STATUS	mandatory
	DESCRIPTION
		"The number of seconds in which Loss Of Signal (LOS) errors have been detected." 
	::= { ds1FramingEntry 4 }

ds1FramingLCVs OBJECT-TYPE
	SYNTAX	Counter
	ACCESS	read-only
	STATUS	mandatory
	DESCRIPTION
		"The number of Line Code Violations (LCV) that have been detected."
	::= { ds1FramingEntry 5 }

ds1FramingFERRs OBJECT-TYPE
	SYNTAX	Counter
	ACCESS	read-only
	STATUS	mandatory
	DESCRIPTION
		"The number of Framing ERRor (FERR) events that have been detected."
	::= { ds1FramingEntry 6 }

ds1FramingOOFs OBJECT-TYPE
	SYNTAX	Counter
	ACCESS	read-only
	STATUS	mandatory
	DESCRIPTION
		"The number of Out Of Frame (OOF) error events that have been detected."
	::= { ds1FramingEntry 7 }

ds1FramingAISs OBJECT-TYPE
	SYNTAX	Counter
	ACCESS	read-only
	STATUS	mandatory
	DESCRIPTION
		"The number of seconds in which Alarm Indication Signals (AIS) have been
		detected. AIS indicates that an upstream failure has been 
                detected by the far end."
	::= { ds1FramingEntry 8 }

ds1FramingB8ZSPatterns OBJECT-TYPE
	SYNTAX	Counter
	ACCESS	read-only
	STATUS	mandatory
	DESCRIPTION
		"The number of seconds in which B8ZS Pattern error events have been detected."
	::= { ds1FramingEntry 9 }

ds1Framing8Zeros OBJECT-TYPE
	SYNTAX	Counter
	ACCESS	read-only
	STATUS	mandatory
	DESCRIPTION
		"The number of seconds in which 8 Zeros error events have been detected."
	::= { ds1FramingEntry 10 }

ds1Framing16Zeros OBJECT-TYPE
	SYNTAX	Counter
	ACCESS	read-only
	STATUS	mandatory
	DESCRIPTION
		"The number of seconds in which 16 Zeros error events have been detected."
	::= { ds1FramingEntry 11 }


ds1FramingYellowAlarms OBJECT-TYPE
	SYNTAX	Counter
	ACCESS	read-only
	STATUS	mandatory
	DESCRIPTION
		"The number of seconds in which Yellow Alarm events have been detected."
	::= { ds1FramingEntry 12 }


ds1FramingRedAlarms OBJECT-TYPE
	SYNTAX	Counter
	ACCESS	read-only
	STATUS	mandatory
	DESCRIPTION
		"The number of seconds in which Red Alarm events have been detected."
	::= { ds1FramingEntry 13 }


ds1FramingBEEs OBJECT-TYPE
	SYNTAX	Counter
	ACCESS	read-only
	STATUS	mandatory
	DESCRIPTION
		"The number of Bit Encoding Error (BEE) events that have been detected."
	::= { ds1FramingEntry 14 }


------------------------------------------------------------------------
                
ds1PlcpTable OBJECT-TYPE
	SYNTAX	SEQUENCE OF Ds1PlcpEntry
	ACCESS	not-accessible
	STATUS	mandatory
	DESCRIPTION
		"A table of DS1 Physical Layer Convergence Protocol (Procedure) statistics 
		information."
	::= { ds1StatsGroup 2 }


ds1PlcpEntry OBJECT-TYPE
	SYNTAX	Ds1PlcpEntry
	ACCESS	not-accessible
	STATUS	mandatory
	DESCRIPTION
		"A table entry containing DS1 PLCP statistics information."
	INDEX	{ ds1PlcpBoard, ds1PlcpModule, ds1PlcpPort }
	::= { ds1PlcpTable 1 }


Ds1PlcpEntry ::=
	SEQUENCE {
		ds1PlcpBoard		INTEGER,
		ds1PlcpModule		INTEGER,
		ds1PlcpPort		INTEGER,

                ds1PlcpBIP8s            Counter,
                ds1PlcpFERRs            Counter,
                ds1PlcpFEBEs            Counter,
                ds1PlcpLOFs             Counter,
                ds1PlcpYellows          Counter
        }


ds1PlcpBoard OBJECT-TYPE
	SYNTAX	INTEGER
	ACCESS	read-only
	STATUS	mandatory
	DESCRIPTION
		"The index of this port's switch board."
	::= { ds1PlcpEntry 1 }


ds1PlcpModule OBJECT-TYPE
	SYNTAX	INTEGER
	ACCESS	read-only
	STATUS	mandatory
	DESCRIPTION
		"The network module of this port."
	::= { ds1PlcpEntry 2 }


ds1PlcpPort OBJECT-TYPE
	SYNTAX	INTEGER
	ACCESS	read-only
	STATUS	mandatory
	DESCRIPTION
		"The number of this port."
	::= { ds1PlcpEntry 3 }


ds1PlcpBIP8s OBJECT-TYPE
	SYNTAX	Counter
	ACCESS	read-only
	STATUS	mandatory
	DESCRIPTION
		"Number of BIP-8 (Bit Interleaved Parity - 8) error events. The BIP-8 is 
		calculated over the Path Overhead field and the associated ATM cell of the 
		previous frame. A BIP-N is a method of error monitoring. An N bit code is 
		generated by the transmitting equipment in such a manner that the first bit 
		of the code provides even parity over the first bit of all N-bit sequences 
		in the previous VT SPE, the second bit provides even parity over the second 
		bits of all N-bit sequences within the specified portion, etc."
	::= { ds1PlcpEntry 4 }


ds1PlcpFERRs OBJECT-TYPE
	SYNTAX	Counter
	ACCESS	read-only
	STATUS	mandatory
	DESCRIPTION
		"Number of Physical Layer Convergence Protocol (PLCP) octet error events."
	::= { ds1PlcpEntry 5 }


ds1PlcpFEBEs OBJECT-TYPE
	SYNTAX	Counter
	ACCESS	read-only
	STATUS	mandatory
	DESCRIPTION
		"Number of ATM Far End Block Error (FEBE) events."
	::= { ds1PlcpEntry 6 }


ds1PlcpLOFs OBJECT-TYPE
	SYNTAX	Counter
	ACCESS	read-only
	STATUS	mandatory
	DESCRIPTION
		"The number of seconds in which Loss Of Frame (LOF) errors were detected 
		by the PLCP (Physical Layer Convergence Protocol) receiver. LOF is declared 
		when an Out-Of-Frame state persists for more than 1ms. LOF is removed when 
		in-frame state persists for more than 12ms."
	::= { ds1PlcpEntry 7 }


ds1PlcpYellows OBJECT-TYPE
	SYNTAX	Counter
	ACCESS	read-only
	STATUS	mandatory
	DESCRIPTION
		"The number of seconds in which Yellow alarm errors were detected by the 
		PLCP (Physical Layer Convergence Protocol) receiver. Yellow alarm is asserted 
		when 10 consecutive yellow signal bits are set to logical 1. Yellow signals 
		are used to alert upstream terminals of a downstream failure in order to 
		initiate trunk conditioning on the failure circuit."
	::= { ds1PlcpEntry 8 }


------------------------------------------------------------------------


ds1AtmTable OBJECT-TYPE
	SYNTAX	SEQUENCE OF Ds1AtmEntry
	ACCESS	not-accessible
	STATUS	mandatory
	DESCRIPTION
		"A table of DS1 ATM statistics information."
	::= { ds1StatsGroup 3 }

ds1AtmEntry OBJECT-TYPE
	SYNTAX	Ds1AtmEntry
	ACCESS	not-accessible
	STATUS	mandatory
	DESCRIPTION
		"A table entry containing DS1 ATM statistics information."
	INDEX	{ ds1AtmBoard, ds1AtmModule, ds1AtmPort }
	::= { ds1AtmTable 1 }

Ds1AtmEntry ::=
	SEQUENCE {
		ds1AtmBoard		INTEGER,
		ds1AtmModule		INTEGER,
		ds1AtmPort		INTEGER,

		ds1AtmHCSs		Counter,
		ds1AtmRxCells		Counter,
		ds1AtmTxCells		Counter
	}

ds1AtmBoard OBJECT-TYPE
	SYNTAX	INTEGER
	ACCESS	read-only
	STATUS	mandatory
	DESCRIPTION
		"The index of this port's switch board."
	::= { ds1AtmEntry 1 }

ds1AtmModule OBJECT-TYPE
	SYNTAX	INTEGER
	ACCESS	read-only
	STATUS	mandatory
	DESCRIPTION
		"The network module of this port."
	::= { ds1AtmEntry 2 }

ds1AtmPort OBJECT-TYPE
	SYNTAX	INTEGER
	ACCESS	read-only
	STATUS	mandatory
	DESCRIPTION
		"The number of this port."
	::= { ds1AtmEntry 3 }

ds1AtmHCSs OBJECT-TYPE
	SYNTAX	Counter
	ACCESS	read-only
	STATUS	mandatory
	DESCRIPTION
		"Number of header check sequence (HCS) error events. The HCS is a CRC-8 
		calculation over the first 4 octets of the ATM cell header."
	::= { ds1AtmEntry 4 }

ds1AtmRxCells OBJECT-TYPE
	SYNTAX	Counter
	ACCESS	read-only
	STATUS	mandatory
	DESCRIPTION
		"Number of ATM cells that were received."
	::= { ds1AtmEntry 5 }

ds1AtmTxCells OBJECT-TYPE
	SYNTAX	Counter
	ACCESS	read-only
	STATUS	mandatory
	DESCRIPTION
		"Number of non-null ATM cells that were transmitted."
	::= { ds1AtmEntry 6 }

END
