------------------------------------------------------------------------
-- ($Id: fore-sonet.mib,v 1.34 1995/07/09 18:04:41 ghoti Exp $)
-- Copyright 1993-1995 by Fore Systems, Inc.

Fore-SONET-MIB DEFINITIONS ::= BEGIN

IMPORTS
	Counter		FROM RFC1155-SMI
	OBJECT-TYPE	FROM RFC1212
	asx		FROM Fore-Switch-MIB;
	

------------------------------------------------------------------------
-- The implementation of the foreSonet tables is mandatory
-- for all switches that have SONET/SDH port modules.

foreSonet		OBJECT IDENTIFIER ::= { asx 4 }
sonetConfGroup		OBJECT IDENTIFIER ::= { foreSonet 1 }
sonetStatsGroup		OBJECT IDENTIFIER ::= { foreSonet 2 }

------------------------------------------------------------------------
-- The Sonet configuration Group

sonetConfTable OBJECT-TYPE
	SYNTAX	SEQUENCE OF SonetConfEntry
	ACCESS	not-accessible
	STATUS	mandatory
	DESCRIPTION
		"A table of SONET switch port configuration information."
	::= { sonetConfGroup 1 }

sonetConfEntry OBJECT-TYPE
	SYNTAX	SonetConfEntry
	ACCESS	not-accessible
	STATUS	mandatory
	DESCRIPTION
		"A table entry containing SONET configuration information for each port."
	INDEX	{ sonetConfBoard, sonetConfModule, sonetConfPort }
	::= { sonetConfTable 1 }

SonetConfEntry ::=
	SEQUENCE {
		sonetConfBoard			INTEGER,
		sonetConfModule			INTEGER,
		sonetConfPort			INTEGER,
		sonetLineType			INTEGER,		
		sonetLineCoding			INTEGER,
		sonetFramingStandardDefault 	INTEGER,
		sonetFramingStandardOper 	INTEGER,
		sonetPathWidth			INTEGER,
		sonetLoopbackConfig		INTEGER,
		sonetTxClockSource		INTEGER,
		sonetRxScrambling		INTEGER,
		sonetTxScrambling		INTEGER,
		sonetSectionStatus		INTEGER,
		sonetLineStatus			INTEGER,
		sonetPathStatus			INTEGER,
		sonetIdleUnassignedCells	INTEGER
	}		


sonetConfBoard OBJECT-TYPE
	SYNTAX	INTEGER
	ACCESS	read-only
	STATUS	mandatory
	DESCRIPTION
		"The index of this port's switch board."
	::= { sonetConfEntry 1 }

sonetConfModule OBJECT-TYPE
	SYNTAX	INTEGER
	ACCESS	read-only
	STATUS	mandatory
	DESCRIPTION
		"The network module of this port."
	::= { sonetConfEntry 2 }

sonetConfPort OBJECT-TYPE
	SYNTAX	INTEGER
	ACCESS	read-only
	STATUS	mandatory
	DESCRIPTION
		"The number of this port."
	::= { sonetConfEntry 3 }

sonetLineType OBJECT-TYPE
	SYNTAX	INTEGER {
		sonetOther(1), 
		sonetSingleModeShortRange(2), 
		sonetSingleModeMediumRange(3), 
		sonetMultiMode(4), 
		sonetUTP(5), 
		sonetCoax(6)
		} 
	ACCESS	read-only
	STATUS	mandatory
	DESCRIPTION
		"This variable describes the line type for this interface. The line type for
		optical SONET signals may be single-mode (short or long range) or multi-mode 
		fiber. For electrical interfaces, the line type is Unshielded Twisted Pair (UTP) 
		or coax. This variable is defined in the SONET IETF draft photonic 
		table as sonetPhotonicLineType with some different values."
	DEFVAL { 4 }
	::= { sonetConfEntry 4 }

sonetLineCoding OBJECT-TYPE
	SYNTAX	INTEGER {
		sonetOther(1), 
		sonetB3ZS(2),
		sonetCMI(3),
		sonetNRZ(4),
		sonetRZ(5)
		}
	ACCESS	read-only
	STATUS	mandatory
	DESCRIPTION
		"This variable describes the line coding for this interface. The B3ZS and CMI 
		are used for electrical SONET signals (STS-1 and STS-3). The Non-Return to 
		Zero (NRZ) and the Return to Zero (RZ) are used for optical SONET signals. 
		This variable is defined in the SONET IETF draft photonic table as 
		sonetPhotonicLineCoding."
	DEFVAL { 4 }
	::= { sonetConfEntry 5 }

sonetFramingStandardDefault OBJECT-TYPE
	SYNTAX	INTEGER {
		atmSONET(1), 
		atmSDH(2)
		}
	ACCESS	read-only
	STATUS	mandatory
	DESCRIPTION
		"This variable identify the default value of the framing standard that 
		is used by this port (SONET or SDH)."
	::= { sonetConfEntry 6 }

sonetFramingStandardOper OBJECT-TYPE
	SYNTAX	INTEGER {
		atmSONET(1), 
		atmSDH(2)
		}
	ACCESS	read-write
	STATUS	mandatory
	DESCRIPTION
		"This variable identify the operational value of the framing standard that 
		is used by this port (SONET or SDH)."
	::= { sonetConfEntry 7 }

sonetPathWidth OBJECT-TYPE
	SYNTAX	INTEGER {
		sts1(1),
		sts3c(2),
		sts9c(3),
		sts12c(4),
		sts24c(5),
		sts48c(6)
	}
	ACCESS	read-only
	STATUS	mandatory
	DESCRIPTION
		"This variable indicates the type of the SONET Path. Assigned types are the 
		STS-Nc Synchronous Payload Envelopes where N=1,3,9,12,24,48. STS-1 is equal 
		to 51.84Mbps, STS-3c is 155.52 Mbps, etc. The SDH transmission rates STM-1 
		(155.52 Mbps), STM-4 (622.08 Mbps) and STM-16 (2488.32 Mbps) are equivalent 
		to SONET rates STS-3, STS-12 and STS-48, respectively. This variable is 
		defined in the SONET IETF draft path configuration table as sonetPathWidth."
	DEFVAL { 2 }
	::= { sonetConfEntry 8 }

sonetLoopbackConfig OBJECT-TYPE
	SYNTAX	INTEGER {
		sonetNoLoop(1), 
		sonetLineLoop(2),
		sonetDiagLoop(3),
		sonetOtherLoop(4)
		}
	ACCESS	read-write
	STATUS	mandatory
	DESCRIPTION
		"This variable represents the current loopback status of the SONET interface.
		The possible values are: 
		sonetNoLoop (1) means that the interface is not in a loopback state.
		sonetLineLoop (2) means that the receive data and clock are connected to the 
		transmit data and clock.
		sonetDiagLoop (3) means that the transmit data stream and clock are looped back 
		to the receiver.
		sonetOtherLoop (4) means that the interface is in a loopback that is not defined 
		here."
	DEFVAL { 1 }
	::= { sonetConfEntry 9 }

sonetTxClockSource OBJECT-TYPE
	SYNTAX	INTEGER {
		rxTiming(1), 
		localTiming(2)
		}
	ACCESS	read-write
	STATUS	mandatory
	DESCRIPTION
		"The source of the transmit clock."
	DEFVAL { 2 }
	::= { sonetConfEntry 10 }

sonetRxScrambling OBJECT-TYPE
	SYNTAX	INTEGER {
		descrambling(1),
		noDescrambling(2)
		}
	ACCESS	read-write
	STATUS	mandatory
	DESCRIPTION
		"This variable indicates whether the information is being descrambled 
		on receiving. It should be set the same as the transmitting side." 
	DEFVAL { 1 }
	::= { sonetConfEntry 11 }

sonetTxScrambling OBJECT-TYPE
	SYNTAX	INTEGER {
		scrambling(1),
		noScrambling(2)
		}
	ACCESS	read-write
	STATUS	mandatory
	DESCRIPTION
		"This variable indicates whether the information (48 octet payload) is being 
		scrambled before transmitting. It should be set the same as the receiving side."
	DEFVAL { 1 }
	::= { sonetConfEntry 12 }

sonetSectionStatus OBJECT-TYPE
	SYNTAX	INTEGER (1..6)
	ACCESS	read-only
	STATUS	mandatory
	DESCRIPTION
		"This variable indicates the Section Status of the interface. It is defined in 
		the SONET IETF draft section configuration table as sonetSectionStatus. The 
		variable is a bit map represented as a sum, therefore, it can represent multiple 
		defects simultaneously. The sonetSectionNoDefect should be set if and only if no 
		other flag is set.
		The various bit positions are:
		  1  sonetSectionNoDefect
		  2  sonetSectionLOS	Loss Of Signal was detected. LOS is declared when
					20 +/- 3us of all zero patterns is detected.
		  4  sonetSectionLOF	Loss Of Frame was detected. LOF is declared when
					an out-of-frame condition persists for 3ms."
	DEFVAL { 1 }
	::= { sonetConfEntry 13 }

sonetLineStatus OBJECT-TYPE
	SYNTAX	INTEGER (1..6)
	ACCESS	read-only
	STATUS	mandatory
	DESCRIPTION
		"This variable indicates the Line Status of the interface. A similar variable is 
		defined in the SONET IETF draft line configuration table as sonetLineStatus. 
		The variable is a bit map represented as a sum, therefore, it can represent 
		multiple defects simultaneously. The sonetLineNoDefect should be set if and only 
		if no other flag is set.
		The various bit positions are:
		  1  sonetLineNoDefect
		  2  sonetLineAIS	Line Alarm Indication Signal was detected. Line AIS is
					asserted when a 111 binary pattern is detected in bits 
					6,7,8 of the K2 byte for five consecutive frames.
		  4  sonetLineFERF	Line Far End Receive Failure was detected. FERF is 
					asserted when a 110 binary pattern is detected in bits 
					6,7,8 of the K2 byte for five consecutive frames."
	DEFVAL { 1 }
	::= { sonetConfEntry 14 }

sonetPathStatus OBJECT-TYPE
	SYNTAX	INTEGER (1..14)
	ACCESS	read-only
	STATUS	mandatory
	DESCRIPTION
		"This variable indicates the Path Status of the interface. It is defined in 
		the SONET IETF draft path configuration table as sonetPathStatus. The variable 
		is a bit map represented as a sum, therefore, it can represent multiple 
		defects simultaneously. The sonetPathNoDefect should be set if and only if no 
		other flag is set.
		The various bit positions are:
		  1  sonetPathNoDefect
		  2  sonetPathLOP	Path Loss Of Pointer was detected. Path LOP is declared 
					when a 'normal pointer value' is not found for eight 
					consecutive frames.
		  4  sonetPathAIS	Path Alarm Indication Signal was detected. Path AIS is 
					asserted when an all ones pattern is detected in the 
					pointer bytes (H1 and H2) for three consecutive frames.
		  8  sonetPathYellow	Path Yellow alarm has been detected. Yellow alarm is 
					declared when bit 5 of the path status byte is high for 
					ten consecutive frames."
	DEFVAL { 1 }
	::= { sonetConfEntry 15 }

sonetIdleUnassignedCells OBJECT-TYPE
	SYNTAX	INTEGER {
		unassigned(1),
		idle(2)
		}
	ACCESS	read-write
	STATUS	mandatory
	DESCRIPTION
		"This variable indicates the type of cells that should be sent in 
		case there is no data to send. According to the ATM Forum, Unassigned
		cells should be sent (octet 1-3 are 0's, octet 4 is 0000xxx0, 
		where x is 'don't care'). According to the CCITT specifications,
		Idle cells should be sent (everything is '0' except for the CLP 
		bit which is '1'). By default, unassigned cells are transmitted
		in case there is no data to send."
	DEFVAL { 1 }
	::= { sonetConfEntry 16 }


------------------------------------------------------------------------
-- The SONET Statistics Group

sonetSectionTable OBJECT-TYPE
	SYNTAX	SEQUENCE OF SonetSectionEntry
	ACCESS	not-accessible
	STATUS	mandatory
	DESCRIPTION
		"A table of SONET Section statistics and errors information."
	::= { sonetStatsGroup 1 }

sonetSectionEntry OBJECT-TYPE
	SYNTAX	SonetSectionEntry
	ACCESS	not-accessible
	STATUS	mandatory
	DESCRIPTION
		"A table entry containing SONET Section statistics and errors information for 
		every port."
	INDEX	{ sonetSectionBoard, sonetSectionModule, sonetSectionPort }
	::= { sonetSectionTable 1 }

SonetSectionEntry ::=
	SEQUENCE {
		sonetSectionBoard	INTEGER,
		sonetSectionModule	INTEGER,
		sonetSectionPort	INTEGER,
		sonetSectionBIPs	Counter,
		sonetSectionLOSs	Counter,
		sonetSectionLOFs	Counter
	}

sonetSectionBoard OBJECT-TYPE
	SYNTAX	INTEGER
	ACCESS	read-only
	STATUS	mandatory
	DESCRIPTION
		"The index of this port's switch board."
	::= { sonetSectionEntry 1 }

sonetSectionModule OBJECT-TYPE
	SYNTAX	INTEGER
	ACCESS	read-only
	STATUS	mandatory
	DESCRIPTION
		"The network module of this port."
	::= { sonetSectionEntry 2 }

sonetSectionPort OBJECT-TYPE
	SYNTAX	INTEGER
	ACCESS	read-only
	STATUS	mandatory
	DESCRIPTION
		"The number of this port."
	::= { sonetSectionEntry 3 }

sonetSectionBIPs OBJECT-TYPE
	SYNTAX	Counter
	ACCESS	read-only
	STATUS	mandatory
	DESCRIPTION
		"The number of Section BIP-8 (Bit Interleaved Parity) errors that have been 
		detected since the last time the port has been reset. The calculated BIP-8 
		code is compared with the BIP-8 code extracted from the B1 byte of the 
		following frame. Differences indicate that a section level bit error has 
		occurred."
	::= { sonetSectionEntry 4 }

sonetSectionLOSs OBJECT-TYPE
	SYNTAX	Counter
	ACCESS	read-only
	STATUS	mandatory
	DESCRIPTION
		"The number of seconds in which Loss Of Signal (LOS) has occurred. A LOS 
		is declared when 20 +/- 3us of all zeros patterns is detected. LOS is cleared 
		when two valid framing words are detected and during the intervening time no 
		LOS condition is detected."
	::= { sonetSectionEntry 5 }

sonetSectionLOFs OBJECT-TYPE
	SYNTAX	Counter
	ACCESS	read-only
	STATUS	mandatory
	DESCRIPTION
		"The number of seconds in which Loss Of Frame (LOF) has occurred. A LOF 
		is declared when an out-of-frame (OOF) condition persists for 3ms. The LOF 
		is cleared when an in-frame condition persists for 3ms. While in-frame the 
		framing bytes (A1, A2) in each frame are compared against the expected 
		pattern. Out-of-frame is declared when four consecutive frames containing 
		one or more framing pattern errors have been received."
	::= { sonetSectionEntry 6 }


------------------------------------------------------------------------

sonetLineTable OBJECT-TYPE
	SYNTAX	SEQUENCE OF SonetLineEntry
	ACCESS	not-accessible
	STATUS	mandatory
	DESCRIPTION
		"A table of SONET Line statistics and errors information."
	::= { sonetStatsGroup 2 }

sonetLineEntry OBJECT-TYPE
	SYNTAX	SonetLineEntry
	ACCESS	not-accessible
	STATUS	mandatory
	DESCRIPTION
		"A table entry containing SONET Line statistics and errors information for 
		every port."
	INDEX	{ sonetLineBoard, sonetLineModule, sonetLinePort }
	::= { sonetLineTable 1 }

SonetLineEntry ::=
	SEQUENCE {
		sonetLineBoard		INTEGER,
		sonetLineModule		INTEGER,
		sonetLinePort		INTEGER,
		sonetLineBIPs		Counter,
		sonetLineFEBEs		Counter,
		sonetLineAISs		Counter,
		sonetLineFERFs		Counter
	}

sonetLineBoard OBJECT-TYPE
	SYNTAX	INTEGER
	ACCESS	read-only
	STATUS	mandatory
	DESCRIPTION
		"The index of this port's switch board."
	::= { sonetLineEntry 1 }

sonetLineModule OBJECT-TYPE
	SYNTAX	INTEGER
	ACCESS	read-only
	STATUS	mandatory
	DESCRIPTION
		"The network module of this port."
	::= { sonetLineEntry 2 }

sonetLinePort OBJECT-TYPE
	SYNTAX	INTEGER
	ACCESS	read-only
	STATUS	mandatory
	DESCRIPTION
		"The number of this port."
	::= { sonetLineEntry 3 }

sonetLineBIPs OBJECT-TYPE
	SYNTAX	Counter
	ACCESS	read-only
	STATUS	mandatory
	DESCRIPTION
		"The number of Line BIP-24 (Bit Interleaved Parity) errors that have been 
		detected since the last time the port has been reset. The calculated BIP-24 
		code is based on the line overhead and synchronous payload envelope (SPE) of 
		the STS-3c stream. The line BIP-24 code is a bit interleaved parity calculation 
		using even parity. The calculated code is compared with the BIP-24 code extracted 
		from the B2 bytes of the following frame. Differences indicate that a line layer 
		bit error has occurred."
	::= { sonetLineEntry 4 }

sonetLineFEBEs OBJECT-TYPE
	SYNTAX	Counter
	ACCESS	read-only
	STATUS	mandatory
	DESCRIPTION
		"The number of line Far End Block Errors (FEBE) that have been detected since 
		the last time the port has been reset."
	::= { sonetLineEntry 5 }

sonetLineAISs OBJECT-TYPE
	SYNTAX	Counter
	ACCESS	read-only
	STATUS	mandatory
	DESCRIPTION
		"The number of seconds in which line Alarm Indication Signal (AIS) has occurred. 
		A line AIS is asserted when a 111 binary pattern is detected in bits 6,7,8 
		of the K2 byte for five consecutive frames. A line AIS is removed when any 
		pattern other than 111 is detected in these bits for five consecutive frames."
	::= { sonetLineEntry 6 }

sonetLineFERFs OBJECT-TYPE
	SYNTAX	Counter
	ACCESS	read-only
	STATUS	mandatory
	DESCRIPTION
		"The number of seconds in which line Far End Receive Failure (FERF) has occurred. 
		A line FERF is asserted when a 110 binary pattern is detected in bits 6,7,8 
		of the K2 byte for five consecutive frames. A line FERF is removed when any 
		pattern other than 110 is detected in these bits for five consecutive frames."
	::= { sonetLineEntry 7 }

------------------------------------------------------------------------

sonetPathTable OBJECT-TYPE
	SYNTAX	SEQUENCE OF SonetPathEntry
	ACCESS	not-accessible
	STATUS	mandatory
	DESCRIPTION
		"A table of SONET Path statistics and errors information."
	::= { sonetStatsGroup 3 }

sonetPathEntry OBJECT-TYPE
	SYNTAX	SonetPathEntry
	ACCESS	not-accessible
	STATUS	mandatory
	DESCRIPTION
		"A table entry containing SONET Path statistics and errors information for 
		every port."
	INDEX	{ sonetPathBoard, sonetPathModule, sonetPathPort }
	::= { sonetPathTable 1 }

SonetPathEntry ::=
	SEQUENCE {
		sonetPathBoard		INTEGER,
		sonetPathModule		INTEGER,
		sonetPathPort		INTEGER,
		sonetPathBIPs		Counter,
		sonetPathFEBEs		Counter,
		sonetPathLOPs		Counter,
		sonetPathAISs		Counter,
		sonetPathYellows	Counter
	}

sonetPathBoard OBJECT-TYPE
	SYNTAX	INTEGER
	ACCESS	read-only
	STATUS	mandatory
	DESCRIPTION
		"The index of this port's switch board."
	::= { sonetPathEntry 1 }

sonetPathModule OBJECT-TYPE
	SYNTAX	INTEGER
	ACCESS	read-only
	STATUS	mandatory
	DESCRIPTION
		"The network module of this port."
	::= { sonetPathEntry 2 }

sonetPathPort OBJECT-TYPE
	SYNTAX	INTEGER
	ACCESS	read-only
	STATUS	mandatory
	DESCRIPTION
		"The number of this port."
	::= { sonetPathEntry 3 }

sonetPathBIPs OBJECT-TYPE
	SYNTAX	Counter
	ACCESS	read-only
	STATUS	mandatory
	DESCRIPTION
		"The number of Path BIP-8 (Bit Interleaved Parity) errors that have been 
		detected since the last time the port has been reset. A path BIP-8 error is 
		detected by comparing the path BIP-8 byte (B3) extracted from the current 
		frame, to the path BIP-8 computed for the previous frame."
	::= { sonetPathEntry 4 }

sonetPathFEBEs OBJECT-TYPE
	SYNTAX	Counter
	ACCESS	read-only
	STATUS	mandatory
	DESCRIPTION
		"The number of path Far End Block Errors (FEBE) that have been detected since 
		the last time the port has been reset. FEBEs are detected by extracting the 
		4-bit FEBE field from the path status byte (G1). The legal range for the 4 bit 
		field is between 0000 and 1000, representing zero to eight errors. Any other 
		value is interpreted as zero errors."
	::= { sonetPathEntry 5 }

sonetPathLOPs OBJECT-TYPE
	SYNTAX	Counter
	ACCESS	read-only
	STATUS	mandatory
	DESCRIPTION
		"The number of seconds in which path Loss Of Pointer (LOP) has occurred. A path
		LOP is detected when a 'normal pointer value' is not found in eight consecutive 
		frames. The LOP is cleared when a 'normal pointer value' is detected for three 
		consecutive frames."
	::= { sonetPathEntry 6 }

sonetPathAISs OBJECT-TYPE
	SYNTAX	Counter
	ACCESS	read-only
	STATUS	mandatory
	DESCRIPTION
		"The number of seconds in which path Alarm Indication Signal (AIS) has occurred. 
		A path AIS is asserted when an all-ones pattern is detected in the pointer bytes 
		(H1 and H2) for three consecutive frames. It is cleared when a valid pointer is 
		detected for three consecutive frames. AIS indicates that an upstream failure 
		has been detected."
	::= { sonetPathEntry 7 }

sonetPathYellows OBJECT-TYPE
	SYNTAX	Counter
	ACCESS	read-only
	STATUS	mandatory
	DESCRIPTION
		"The number of seconds in which path yellow alarm has occurred. A path yellow 
		alarm is detected by extracting bit 5 of the path status byte. If bit 5 is 
		high for ten consecutive frames, a yellow alarm is declared. A yellow alarm 
		is cleared when bit 5 is low for ten consecutive frames. Yellow signals are 
		used to alert upstream terminals of a downstream failure in order to initiate 
		trunk conditioning on the failure circuit."
	::= { sonetPathEntry 8 }

------------------------------------------------------------------------

sonetAtmTable OBJECT-TYPE
	SYNTAX	SEQUENCE OF SonetAtmEntry
	ACCESS	not-accessible
	STATUS	mandatory
	DESCRIPTION
		"A table of SONET ATM layer statistics and errors information."
	::= { sonetStatsGroup 4 }

sonetAtmEntry OBJECT-TYPE
	SYNTAX	SonetAtmEntry
	ACCESS	not-accessible
	STATUS	mandatory
	DESCRIPTION
		"A table entry containing SONET ATM layer statistics and errors information 
		for every port."
	INDEX	{ sonetAtmBoard, sonetAtmModule, sonetAtmPort }
	::= { sonetAtmTable 1 }

SonetAtmEntry ::=
	SEQUENCE {
		sonetAtmBoard			INTEGER,
		sonetAtmModule			INTEGER,
		sonetAtmPort			INTEGER,
		sonetAtmCorrectableHCSs		Counter,
		sonetAtmUncorrectableHCSs	Counter
}

sonetAtmBoard OBJECT-TYPE
	SYNTAX	INTEGER
	ACCESS	read-only
	STATUS	mandatory
	DESCRIPTION
		"The index of this port's switch board."
	::= { sonetAtmEntry 1 }

sonetAtmModule OBJECT-TYPE
	SYNTAX	INTEGER
	ACCESS	read-only
	STATUS	mandatory
	DESCRIPTION
		"The network module of this port."
	::= { sonetAtmEntry 2 }

sonetAtmPort OBJECT-TYPE
	SYNTAX	INTEGER
	ACCESS	read-only
	STATUS	mandatory
	DESCRIPTION
		"The number of this port."
	::= { sonetAtmEntry 3 }

sonetAtmCorrectableHCSs OBJECT-TYPE
	SYNTAX	Counter
	ACCESS	read-only
	STATUS	mandatory
	DESCRIPTION
		"The number of correctable Header Check Sequence (HCS) error events that 
		occurred since the port was reset. The HCS is a CRC-8 calculation over the 
		first 4 octets of the ATM cell header."
	::= { sonetAtmEntry 4 }

sonetAtmUncorrectableHCSs OBJECT-TYPE
	SYNTAX	Counter
	ACCESS	read-only
	STATUS	mandatory
	DESCRIPTION
		"The number of uncorrectable Header Check Sequence (HCS) error events that 
		occurred since the port was reset. The HCS is a CRC-8 calculation over the 
		first 4 octets of the ATM cell header."
	::= { sonetAtmEntry 5 }



END
