NSMAIL-MIB DEFINITIONS ::= BEGIN 

IMPORTS 
   MODULE-IDENTITY, OBJECT-TYPE, OBJECT-IDENTITY,
   enterprises 
      FROM SNMPv2-SMI 
   Counter32, Gauge32 
      FROM SNMPv2-SMI 
   Counter, IpAddress, TimeTicks 
      FROM RFC1155-SMI 
   DisplayString, TimeInterval 
      FROM SNMPv2-TC 
   TRAP-TYPE 
      FROM RFC-1215; 

netscape OBJECT IDENTIFIER ::= { enterprises 1450 } 

nsmail MODULE-IDENTITY 
   LAST-UPDATED         "9706021700Z" 
   ORGANIZATION         "Netscape Communications Corp." 
   CONTACT-INFO         "Netscape Communications Corp. 
                         501 E. Middlefield Rd. 
                         Mountain View, CA 94043" 

   DESCRIPTION          "A private MIB module for Netscape
                         Messaging Server" 

   ::= { netscape 5 } 

---- 
-- Static variables 
---- 

nsmailEntityInfo OBJECT IDENTIFIER ::= { nsmail 1 } 

nsmailEntityDescr     OBJECT-TYPE 
   SYNTAX     DisplayString (SIZE (0..255)) 
   ACCESS     read-only 
   STATUS     mandatory 
   DESCRIPTION   "A general textual description 
                  of the Netscape Mail Server." 
   ::= { nsmailEntityInfo 1 } 

nsmailEntityVers     OBJECT-TYPE 
   SYNTAX     DisplayString (SIZE (0..255)) 
   ACCESS     read-only 
   STATUS     mandatory 
   DESCRIPTION  "The Version of the Netscape Mail Server."
   ::= { nsmailEntityInfo 2 } 

nsmailEntityOrg     OBJECT-TYPE 
   SYNTAX     DisplayString (SIZE (0..255)) 
   ACCESS     read-only 
   STATUS     mandatory 
   DESCRIPTION  "Organization responsible for Netscape
                 Mail Server at this installation." 
   ::= { nsmailEntityInfo 3 } 

nsmailEntityLocation     OBJECT-TYPE 
    SYNTAX     DisplayString (SIZE (0..255)) 
    ACCESS     read-only 
    STATUS     mandatory 
    DESCRIPTION  "Physical location of this entity
                  (Netscape Mail Server). For example: 
                  hostname, building number, 
                  lab number, etc."
    ::= { nsmailEntityInfo 4 } 

nsmailEntityContact     OBJECT-TYPE 
    SYNTAX      DisplayString (SIZE (0..255)) 
    ACCESS      read-only 
    STATUS      mandatory 
    DESCRIPTION "Contact person(s) responsible for the 
                 Netscape Mail Server at this
                 installation, together with
                 information on how to contact." 
    ::= { nsmailEntityInfo 5 } 

nsmailEntityName     OBJECT-TYPE 
    SYNTAX     DisplayString (SIZE (0..255)) 
    ACCESS     read-only 
    STATUS     mandatory 
    DESCRIPTION  "Name assigned to this entity at the 
                  installation site." 
    ::= { nsmailEntityInfo 6 } 

---- 
-- mta table for statistic information 
---- 

mtaTable       OBJECT-TYPE 
    SYNTAX     SEQUENCE OF MtaEntry 
    ACCESS     not-accessible 
    STATUS     mandatory 
    ::= { nsmail 2 } 

mtaEntry       OBJECT-TYPE 
    SYNTAX     MtaEntry 
    ACCESS     not-accessible 
    STATUS     mandatory 
    INDEX     { mtaId } 
    ::= { mtaTable 1 } 

MtaEntry     ::= SEQUENCE { 
    mtaReceivedMessages         Counter32, 
    mtaStoredMessages           Gauge32, 
    mtaTransmittedMessages      Counter32, 
    mtaReceivedVolume           Counter32, 
    mtaStoredVolume             Gauge32, 
    mtaTransmittedVolume        Counter32, 
    mtaReceivedRecipients       Counter32, 
    mtaStoredRecipients         Gauge32, 
    mtaTransmittedRecipients    Counter32, 
    mtaId                       INTEGER 
    } 

mtaReceivedMessages     OBJECT-TYPE 
    SYNTAX     Counter32 
    ACCESS     read-only 
    STATUS     mandatory 
    DESCRIPTION  "The total number of messages received 
                  since MTA Initialization." 
    ::= { mtaEntry 1 } 

mtaStoredMessages     OBJECT-TYPE 
    SYNTAX     gauge32 
    ACCESS     read-only 
    STATUS     mandatory 
    DESCRIPTION  "The total number of messages currently 
                  stored in the MTA." 
    ::= { mtaEntry 2 } 

mtaTransmittedMessages     OBJECT-TYPE 
    SYNTAX     Counter32 
    ACCESS     read-only 
    STATUS     mandatory 
    DESCRIPTION  "The total number of messages
                  transmitted since MTA Initialization." 
    ::= { mtaEntry 3 } 

mtaReceivedVolume     OBJECT-TYPE 
    SYNTAX     Counter32 
    ACCESS     read-only 
    STATUS     mandatory 
    DESCRIPTION  "The number of msgs (in kilo-octets
                  received since MTA Initialization."
    ::= { mtaEntry 4 } 

mtaStoredVolume     OBJECT-TYPE 
    SYNTAX     Gauge32 
    ACCESS     read-only 
    STATUS     mandatory 
    DESCRIPTION  "The total number of msgs 
                  (in kilo-octets) currently stored 
                  in the MTA."
    ::= { mtaEntry 5 } 

mtaTransmittedVolume     OBJECT-TYPE 
    SYNTAX     Counter32 
    ACCESS     read-only 
    STATUS     mandatory 
    DESCRIPTION  "Number of msgs, in kilo-octets, 
                  transmitted since MTA initialization."
    ::= { mtaEntry 6 } 

mtaReceivedRecipients     OBJECT-TYPE 
    SYNTAX     Counter32 
    ACCESS     read-only 
    STATUS     mandatory 
    DESCRIPTION  "The number of recipients specified 
                  in all messages received since MTA 
                  Initialization. Recipients this MTA 
                  had no responsibility for are not counted."
    ::= { mtaEntry 7 } 

mtaStoredRecipients     OBJECT-TYPE 
    SYNTAX     Gauge32 
    ACCESS     read-only 
    STATUS     mandatory 
    DESCRIPTION  "The total number of recipients 
                  specified in all messages currently 
                  stored in the MTA. Recipients this MTA 
                  had no responsibility for are not counted."
    ::= { mtaEntry 8 } 

mtaTransmittedRecipients     OBJECT-TYPE 
    SYNTAX     Counter32 
    ACCESS     read-only 
    STATUS     mandatory 
    DESCRIPTION  "The number of recipients specified in
                  all messages transmitted since MTA 
                  Initialization. Recipients this MTA
                  had no responsibility for are not counted."
    ::= { mtaEntry 9 } 

mtaId          OBJECT-TYPE 
    SYNTAX     INTEGER 
    ACCESS     read-only 
    STATUS     mandatory 
    DESCRIPTION  "The id of the MTA as configured." 
    ::= { mtaEntry 10 } 

---- 
-- Traps 
---- 

nsMailServerDown     TRAP-TYPE 
    ENTERPRISE       netscape 
    VARIABLES       { nsmailEntityDescr, nsmailEntityVers,
                      nsmailEntityLocation,
                      nsmailEntityContact } 
    DESCRIPTION       "This trap is generated whenever the 
                      agent detects the Netscape Mail
                      Server to be (potentially) Down."
    ::= 5001 

nsMailServerStart    TRAP-TYPE 
    ENTERPRISE       netscape 
    VARIABLES      { nsmailEntityDescr, nsmailEntityVers,
                     nsmailEntityLocation } 
    DESCRIPTION     "This trap is generated whenever 
                     the agent detects the Netscape 
                     Mail Server to have (re)started." 
    ::= 5002 

nsMailServerNoResponse  TRAP-TYPE 
    ENTERPRISE       netscape 
    VARIABLES      { nsmailEntityDescr, nsmailEntityVers,
                     nsmailEntityLocation,
                     nsmailEntityContact } 
    DESCRIPTION     "This trap is generated whenever the 
                     agent detects the Netscape Mail Server
                     not responding to its polls. This 
                     TRAP is different from the 
                     'nsMailServerDown' TRAP, as the 
                     Netscape Mail Server is still 
                     potentially up, serving its main 
                     purpose. But, the SNMP data collection
                     entity has most likely gone down." 
    ::= 5003 

END
