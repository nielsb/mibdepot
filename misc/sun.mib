-- Copyright 1988 - 07/23/96 Sun Microsystems, Inc. All Rights Reserved.
--pragma ident  "@(#)sun.mib	2.19 96/07/23 Sun Microsystems"

-- sun.mib
-- MIB for the SNMP Agent included with SunNet Manager 2.3
-- Release version = 2.3
-- Patch level     = 0

          sun-snmp DEFINITIONS ::= BEGIN

          IMPORTS
                  enterprises, NetworkAddress, IpAddress, Counter, Gauge,
                          TimeTicks
                      FROM RFC1155-SMI
                  OBJECT-TYPE
                          FROM RFC-1212;


--  **********************************************************************
--  SUN EXTENSIONS
--  **********************************************************************
		sun		OBJECT IDENTIFIER ::= { enterprises 42 }
		products	OBJECT IDENTIFIER ::= { sun 2 }
		sunMib		OBJECT IDENTIFIER ::= { sun 3 }

		sunSystem	OBJECT IDENTIFIER ::= { sunMib 1 }
		sunInterfaces	OBJECT IDENTIFIER ::= { sunMib 2 }
		sunAt		OBJECT IDENTIFIER ::= { sunMib 3 }
		sunIp		OBJECT IDENTIFIER ::= { sunMib 4 }
		sunIcmp		OBJECT IDENTIFIER ::= { sunMib 5 }
		sunTcp		OBJECT IDENTIFIER ::= { sunMib 6 }
		sunUdp		OBJECT IDENTIFIER ::= { sunMib 7 }
		sunSnmp		OBJECT IDENTIFIER ::= { sunMib 11 }
		sunProcesses	OBJECT IDENTIFIER ::= { sunMib 12 }
		sunHostPerf	OBJECT IDENTIFIER ::= { sunMib 13 }

--  **********************************************************************
--  SUN SYSTEM GROUP
--  **********************************************************************

	agentDescr	OBJECT-TYPE
		SYNTAX	DisplayString (SIZE (0..255))
		ACCESS	read-only
		STATUS	mandatory
		DESCRIPTION
			"The SNMP agent's description of itself."
		::= { sunSystem 1 }

	hostID	OBJECT-TYPE
		SYNTAX  OCTET STRING (SIZE (4))
		ACCESS  read-only
		STATUS	mandatory
		DESCRIPTION
			"The unique Sun hardware identifier.
			The value returned is four byte binary
			string."
		::= { sunSystem 2 }

	motd	OBJECT-TYPE
		SYNTAX	DisplayString (SIZE (0..255))
		ACCESS  read-only
		STATUS	mandatory
		DESCRIPTION
			"The first line of /etc/motd."
		::= { sunSystem 3 }

	unixTime OBJECT-TYPE
		SYNTAX  Counter
		ACCESS  read-only
		STATUS  mandatory
		DESCRIPTION
			"The Unix system time.  Measured in seconds
			since January 1, 1970 GMT."
		::= { sunSystem 4 }

-- the Sun Processes group
-- the Sun Process table table
-- This table is lists all the processes currently
-- in execution.

	sunProcessTable OBJECT-TYPE
		SYNTAX  SEQUENCE OF PsEntry
		ACCESS  read-only
		STATUS  mandatory
		::= { sunProcesses 1 }

	psEntry OBJECT-TYPE
		SYNTAX  PsEntry
		ACCESS  read-only
		STATUS  mandatory
		INDEX   { psProcessID }
		::= { sunProcessTable 1 }
		PsEntry ::= SEQUENCE {
		psProcessID
		INTEGER,
		psParentProcessID
		INTEGER,
		psProcessSize
		INTEGER,
		psProcessCpuTime
		INTEGER,
		psProcessState
		DisplayString,
		psProcessWaitChannel
		DisplayString,
		psProcessTTY
		DisplayString,
		psProcessUserName
		DisplayString,
		psProcessUserID
		INTEGER,
		psProcessName
		DisplayString,
		psProcessStatus
		INTEGER
		}

	psProcessID OBJECT-TYPE
		SYNTAX  INTEGER
		ACCESS  read-only
		STATUS  mandatory
		DESCRIPTION
			"The process identifier for this process."
		::= { psEntry 1 }

	psParentProcessID OBJECT-TYPE
		SYNTAX  INTEGER
		ACCESS  read-only
		STATUS  mandatory
		DESCRIPTION
			"The process identifier of this process's parent."
		::= { psEntry 2 }

	psProcessSize OBJECT-TYPE
		SYNTAX  INTEGER
		ACCESS  read-only
		STATUS  mandatory
		DESCRIPTION
			"The combined size of the data and stack segments
			(in kilobytes.)"
		::= { psEntry 3 }

	psProcessCpuTime OBJECT-TYPE
		SYNTAX  INTEGER
		ACCESS  read-only
		STATUS  mandatory
		DESCRIPTION
			"The CPU time (including both user and system
			time) consumed so far."
		::= { psEntry 4 }

	psProcessState OBJECT-TYPE
		SYNTAX  DisplayString (SIZE (0..4))
		ACCESS  read-only
		STATUS  mandatory
		DESCRIPTION
			"The run-state of the process.
			R - Runnable
			T - Stopped
			P - In page wait
			D - Non-interruptable wait
			S - Sleeping (less than 20 seconds)
			I - Idle (more than 20 seconds)
			Z - Zombie"
		::= { psEntry 5 }

	psProcessWaitChannel OBJECT-TYPE
		SYNTAX  DisplayString (SIZE (0..16))
		ACCESS  read-only
		STATUS  mandatory
		DESCRIPTION
			"Reason process is waiting."
		::= { psEntry 6 }

	psProcessTTY OBJECT-TYPE
		SYNTAX  DisplayString (SIZE (0..16))
		ACCESS  read-only
		STATUS  mandatory
		DESCRIPTION
			"Terminal, if any, controlling this process."
		::= { psEntry 7 }

	psProcessUserName OBJECT-TYPE
		SYNTAX  DisplayString (SIZE (0..16))
		ACCESS  read-only
		STATUS  mandatory
		DESCRIPTION
			"Name of the user associated with this process."
		::= { psEntry 8 }

	psProcessUserID OBJECT-TYPE
		SYNTAX  INTEGER
		ACCESS  read-only
		STATUS  mandatory
		DESCRIPTION
			"Numeric form of the name of the user associated
			with this process."
		::= { psEntry 9 }

	psProcessName OBJECT-TYPE
		SYNTAX  DisplayString (SIZE (0..64))
		ACCESS  read-only
		STATUS  mandatory
		DESCRIPTION
			"Command name used to invoke this process."
		::= { psEntry 10 }

	psProcessStatus OBJECT-TYPE
		SYNTAX  INTEGER
		ACCESS  read-write
		STATUS  mandatory
		DESCRIPTION
			"Setting this variable will cause a signal
			of the set value to be sent to the process."
		::= { psEntry 11 }

-- the Sun Hostperf group

	rsUserProcessTime OBJECT-TYPE
		SYNTAX  Counter
		ACCESS  read-only
		STATUS  mandatory
		DESCRIPTION
			"total number of timeticks used by user processes
			since the system was last booted."
		::=  { sunHostPerf 1 }

	rsNiceModeTime OBJECT-TYPE
		SYNTAX  Counter
		ACCESS  read-only
		STATUS  mandatory
		DESCRIPTION
			"total number of timeticks used by nice mode since
			the system was last booted."
		::=  { sunHostPerf 2 }

	rsSystemProcessTime OBJECT-TYPE
		SYNTAX  Counter
		ACCESS  read-only
		STATUS  mandatory
		DESCRIPTION
			"total number of timeticks used by system processes
			since the system was last booted."
		::=  { sunHostPerf 3 }

	rsIdleModeTime OBJECT-TYPE
		SYNTAX  Counter
		ACCESS  read-only
		STATUS  mandatory
		DESCRIPTION
			"total number of timeticks used in idle mode since
			the system was last booted."
		::=  { sunHostPerf 4 }

	rsDiskXfer1 OBJECT-TYPE
		SYNTAX  Counter
		ACCESS  read-only
		STATUS  mandatory
		DESCRIPTION
			""
		::=  { sunHostPerf 5 }

	rsDiskXfer2 OBJECT-TYPE
		SYNTAX  Counter
		ACCESS  read-only
		STATUS  mandatory
		DESCRIPTION
			""
		::=  { sunHostPerf 6 }

	rsDiskXfer3 OBJECT-TYPE
		SYNTAX  Counter
		ACCESS  read-only
		STATUS  mandatory
		DESCRIPTION
			""
		::=  { sunHostPerf 7 }

	rsDiskXfer4 OBJECT-TYPE
		SYNTAX  Counter
		ACCESS  read-only
		STATUS  mandatory
		DESCRIPTION
			""
		::=  { sunHostPerf 8 }

	rsVPagesIn OBJECT-TYPE
		SYNTAX  Counter
		ACCESS  read-only
		STATUS  mandatory
		DESCRIPTION
			"Number of pages read in from disk."
		::=  { sunHostPerf 9 }

	rsVPagesOut OBJECT-TYPE
		SYNTAX  Counter
		ACCESS  read-only
		STATUS  mandatory
		DESCRIPTION
			"Number of pages written to disk."
		::=  { sunHostPerf 10 }

	rsVSwapIn OBJECT-TYPE
		SYNTAX  Counter
		ACCESS  read-only
		STATUS  mandatory
		DESCRIPTION
		"Number of pages swapped in."
		::=  { sunHostPerf 11 }

	rsVSwapOut OBJECT-TYPE
		SYNTAX  Counter
		ACCESS  read-only
		STATUS  mandatory
		DESCRIPTION
			"Number of pages swapped out."
		::=  { sunHostPerf 12 }

	rsVIntr OBJECT-TYPE
		SYNTAX  Counter
		ACCESS  read-only
		STATUS  mandatory
		DESCRIPTION
		"Number of device interrupts."
		::=  { sunHostPerf 13 }
		
	rsIfInPackets OBJECT-TYPE
		SYNTAX  Counter
		ACCESS  read-only
		STATUS  mandatory
		DESCRIPTION
			"Number of input packets."
		::=  { sunHostPerf 14 }

	rsIfOutPackets OBJECT-TYPE
		SYNTAX  Counter
		ACCESS  read-only
		STATUS  mandatory
		DESCRIPTION
			"Number of output packets."
		::=  { sunHostPerf 15 }

	rsIfInErrors OBJECT-TYPE
		SYNTAX  Counter
		ACCESS  read-only
		STATUS  mandatory
		DESCRIPTION
			"Number of input errors."
		::=  { sunHostPerf 16 }
		
	rsIfOutErrors OBJECT-TYPE
		SYNTAX  Counter
		ACCESS  read-only
		STATUS  mandatory
		DESCRIPTION
			"Number of output errors."
		::=  { sunHostPerf 17 }

	rsIfCollisions OBJECT-TYPE
		SYNTAX  Counter
		ACCESS  read-only
		STATUS  mandatory
		DESCRIPTION
			"Number of output collisions."
		::=  { sunHostPerf 18 }

END
