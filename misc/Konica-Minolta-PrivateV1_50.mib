KONICAMINOLTA-PrivateMIB DEFINITIONS ::= BEGIN

-- KONICA MINOLTA Private MIB 
--    Ver1.50 Draft  2005.9.19
--                mib-staf@mol.konicaminolta.jp


-- This definition is referred to "KONICA MINOLTA MIB 
-- Standard Specification Rev1.50 Draft". 

-- Chage history from Ver.1.4
--
--  Change string length of kmNetTcpipDnsDomainName
--  Add kmSysSecurityMode
--  Add kmNetIpVersion
--  Add kmNetIpv6ConfigTable
--  Change access of kmNetSnmpTrapIpxNodeAddress
--  Add kmNetSmtpdTable
--  Change parameter of kmJmJobType
--  Change kmJmJobDestination
--  Change kmSysGeneralSupportedID
--  Change kmNetSnmpV3UserAuthPasswd
--  Change kmNetSnmpV3UserPrivPasswd
--  Change kmNetNwPrefFServer
--  Change kmNetNwPrefContext
--  Change kmSysGeneralAlertLocation



-- This Private MIB has the basic information which Network
-- Management Utility refers to.
-- The device that has network interface should implement 
-- this private MIB. 



IMPORTS

    DateAndTime                   FROM SNMPv2-TC
    enterprises, Integer32, Counter32, IpAddress
                                  FROM SNMPv2-SMI
    OBJECT-TYPE                   FROM RFC1212
    DisplayString, PhysAddress    FROM RFC1213-MIB
    hrDeviceIndex                 FROM HOST-RESOURCES-MIB
    Ipv6Address                   FROM IPV6-TC;


konicaminolta     OBJECT IDENTIFIER ::= { enterprises 18334 }
-- This enterprise number is assigned to
-- KONICA MINOLTA HOLDINGS, INC.



kmBT            OBJECT IDENTIFIER ::= { konicaminolta 1 }
-- Konica Minolta Business Technologies, Inc.

--kmOT            OBJECT IDENTIFIER ::= { konicaminolta 2 }
-- Konica Minolta Opt, Inc.

--kmPI            OBJECT IDENTIFIER ::= { konicaminolta 3 }
-- Konica Minolta Photo Imaging, Inc.
-- Konica Minolta Camera, Inc.

--kmMG            OBJECT IDENTIFIER ::= { konicaminolta 4 }
-- Konica Minolta M&G, Inc.

--kmSE            OBJECT IDENTIFIER ::= { konicaminolta 5 }
-- Konica Minolta Sensing, Inc.

--kmTC            OBJECT IDENTIFIER ::= { konicaminolta 6 }
-- Konica Minolta Technology Center, Inc.

 kmMib             OBJECT IDENTIFIER ::= { kmBT 1 }

  kmSystem          OBJECT IDENTIFIER ::= { kmMib 1 }
  kmInterface       OBJECT IDENTIFIER ::= { kmMib 2 }
  kmDevice          OBJECT IDENTIFIER ::= { kmMib 3 }
  kmJob             OBJECT IDENTIFIER ::= { kmMib 4 }

   kmPrinter         OBJECT IDENTIFIER ::= { kmSystem 1 }
   kmScanner         OBJECT IDENTIFIER ::= { kmSystem 3 }
   kmSysMib          OBJECT IDENTIFIER ::= { kmSystem 5 }

   kmNetwork         OBJECT IDENTIFIER ::= { kmInterface 1 }

   kmJobManagement   OBJECT IDENTIFIER ::= { kmJob 1 }

-- Private System MIB 

kmSysMibVersion  OBJECT-TYPE
    SYNTAX    DisplayString (SIZE(0..7))
    ACCESS    read-only
    STATUS    mandatory
    DESCRIPTION
        "
         The version information of KONICA MINOLTA Standard MIB 
         specification.

         This indicates the version of the 
         KONICA MINOLTA Private System MIB which is implemented. 

         It is written as AA.BC.
         AA is indicating major revision, and B and C is 
         minor revision. Decimal point is ASCII-coded period.

         This definition file is corresponded to '1.50'.
        "
    ::= { kmSysMib 1 }


    kmSysGeneralInfo          OBJECT IDENTIFIER ::= { kmSysMib 2 }
    kmSysContact              OBJECT IDENTIFIER ::= { kmSysMib 3 }

    kmSysVersion              OBJECT IDENTIFIER ::= { kmSysMib 5 }
    kmSysComponent            OBJECT IDENTIFIER ::= { kmSysMib 6 }
    kmSysCounter              OBJECT IDENTIFIER ::= { kmSysMib 7 }
    kmSysMachineInfo          OBJECT IDENTIFIER ::= { kmSysMib 8 }
    kmSysConsumable           OBJECT IDENTIFIER ::= { kmSysMib 9 }

-- kmSysGeneralInfo Group
-- This group shows the general information of system.

kmSysGeneralFunctionTable  OBJECT-TYPE
    SYNTAX    SEQUENCE OF KmSysGeneralFunctionEntry
    ACCESS    not-accessible
    STATUS    mandatory
    DESCRIPTION
        "
         The table for showing that what kind of functions it has and
         the function can operate or not, in a device which has plural 
         function such as MFP, etc.
        "
    ::= { kmSysGeneralInfo 1 }

kmSysGeneralFunctionEntry OBJECT-TYPE
    SYNTAX    KmSysGeneralFunctionEntry
    ACCESS    not-accessible
    STATUS    mandatory
    DESCRIPTION
        "
         An entry for one function contained by the system.
        "
    INDEX  { kmSysGeneralFunctionIndex }
    ::= { kmSysGeneralFunctionTable 1 }

  KmSysGeneralFunctionEntry ::= SEQUENCE {
      kmSysGeneralFunctionIndex        INTEGER,
      kmSysGeneralFunctionType         INTEGER,
      kmSysGeneralFunctionStatus       INTEGER
      }

kmSysGeneralFunctionIndex  OBJECT-TYPE
    SYNTAX     INTEGER
    ACCESS     read-only
    STATUS     mandatory
    DESCRIPTION
        "
         A unique value for each function contained by the system.
         In case of MFP, system is managed by printer and scanner.
         Index of the following must be used,.
            Index    function
           --------------------------
             1       Printer
             2       Scanner

         In case of independent printer, index is must be 1.  
        "
    ::= { kmSysGeneralFunctionEntry 1 }

kmSysGeneralFunctionType  OBJECT-TYPE
    SYNTAX    INTEGER {
                  printer (2),
                  scanner (3)
                  }
    ACCESS     read-only
    STATUS     mandatory
    DESCRIPTION
        "
         An indication of the type of function in which a system has. 
        "
    ::= { kmSysGeneralFunctionEntry 2 }

kmSysGeneralFunctionStatus  OBJECT-TYPE
    SYNTAX     INTEGER {
                   other      (1),
                   unknown    (2),
                   fatal      (3),
                   error      (4),
                   warning    (5),
                   caution    (6),
                   notReady   (7),
                   busy       (8),
                   ready      (9),
                   processing (10),
                   printing   (11),
                   scanning   (12),
                   copying    (13),
                   receiving  (14),
                   sending    (15),
                   pause      (16)
               }
    ACCESS     read-only
    STATUS     mandatory
    DESCRIPTION
        "
         The current operational status of each system.
        "
    ::= { kmSysGeneralFunctionEntry 3 }

kmSysGeneralAlertLocation  OBJECT-TYPE
    SYNTAX     Integer32
    ACCESS     read-only
    STATUS     optional
    DESCRIPTION
        "
         This object should show the value of prtAlertLocation that
         is most critical alert of prtAlertTable.
         If prtAlertTable has no alerrt, this value should be -2.

         HP Web Jetadmin does not use this mib,
         this will be deleted in the future.
        "
    ::= { kmSysGeneralInfo 2 }


kmSysCurrentDateTime  OBJECT-TYPE
    SYNTAX     DateAndTime
    ACCESS     read-only
    STATUS     mandatory
    DESCRIPTION
        "Time that is set in the system and specifies by DateAndTime
         Although the time of the clock that the system has is displayed,
         the change function of the setup is not supported. Access is RO.
         If it doe not have time function, all Bytes should implement 0x00.

         In RFC definition, time zone is defined as -11:59 to +11:59,
         but time zone of some area over 12:00. 
         This object is accepted to get outside the scope of 
         RFC definition. 

         If this ibject shows UTC, 9-11byte should be '+', '0', '0'.
        "
    ::= { kmSysGeneralInfo 4 }


kmSysSecurityMode  OBJECT-TYPE
    SYNTAX   INTEGER{
                 notSupported (0),
                 off (1),
                 on (2)
                 }
    ACCESS   read-only
    STATUS   mandatory
    DESCRIPTION
        "
         This object shows current state of security mode.
         
        "
    ::= { kmSysGeneralInfo 5 }


kmSysGenericMibEnabled  OBJECT-TYPE
    SYNTAX   INTEGER{
                 own (0),
                 generic (1)
                 }
    ACCESS   read-only
    STATUS   optional --Conditionally Mandatory
    DESCRIPTION
        "This object is key of determinate Own or OEM for EFI products.
         This does not have the necessity for implement with products 
         other than EFI.
        "
    ::= { kmSysGeneralInfo 6 }

kmSysAssetNumber  OBJECT-TYPE
    SYNTAX   OCTET STRING(SIZE(0..8))
    ACCESS   read-write
    STATUS   mandatory
    DESCRIPTION
        "
         The asset number of system.
         Administrator should input any number to identify
         each systems.
         Default value should be '' (null_String).
         The implementation of RO is not acceptable.
        "
    ::= { kmSysGeneralInfo 7 }

kmSysGeneralFunctionInfo OBJECT-TYPE
    SYNTAX   INTEGER
    ACCESS   read-only
    STATUS   mandatory
    DESCRIPTION
        "
         This object shows basic function of system.

         Basic function is shown by following  Bitmap.
         
         Bit    Value     Function
         ---    -----    --------------- 
           0       1      Printer
           1       2      Copy
           2       4      Scan
           3       8      Fax

         In case of simple printer, this value should be 1.
         In case of MFP that has copy, printer, scanner and fax,
         this value should be 15.
        "
    ::= { kmSysGeneralInfo 8 }

kmSysGeneralSupportedFunction  OBJECT-TYPE
    SYNTAX   INTEGER
    ACCESS   read-only
    STATUS   mandatory
    DESCRIPTION
        "
         This object shows supported function of system
         that is not identified by OID or implementation of
         MIB.

         Supported function is shown by following  Bitmap.
         
         Bit    Value     Function
         ---    -----    ---------------
          0        1      Support of PSNC
          1        2      Support count reader function.
          2        4      Support JobLogViewer function.
          3-16            Reserved for PageScope NetCare.
          17-             Reserved for future application.

          When the functions that are required by an application
          are supported, the value of each bit is set  to 1.

          And when an additional function comes out, 
          addition to Bitmap is performed as needed.
          When describing implementation specification, 
          please confirm additional request from application. 
          At the point of this standard specification is released,
          if the device is satisfied PSNC required specifications, 
          this value should be 7.
        "
    ::= { kmSysGeneralInfo 9 }

kmSysGeneralSupportedID OBJECT-TYPE
    SYNTAX   INTEGER
    ACCESS   read-only
    STATUS   mandatory
    DESCRIPTION
        "
         This object shows revision change of 
         implementation specification.
         This value is used to identification of application that
         MIB implementation specification is changed on
         firmware released for field.

         If MIB implementation is changed,
         this value should be incremented.
         If MIB implementation is not changed on firmware update,
         this value should not be incremented.

         The default value is 17(Bit#0[ON], Bit#4[ON]).

         Basic function is shown by following  Bitmap.
         
         Bit    Value     Function
         ---    -----    --------------- 
           0          1   for PSNC
           1          2    (Initial value is 1,
           2          4     and increase it with 2, 3, 4 and ...)
           3          8    
           4         16   for WJA
           5         32    (Initial value is 16,
           6         64     and increase it with 32, 48, 64 and ...)
           7        128   
       8 - 31    256   Reserved
        "
    ::= { kmSysGeneralInfo 10 }


-- kmSysContact Group
-- This group shows the contact information of system.
-- In addition, link these items with the display item of PSWC
-- (PageScopeWebConnection.)
-- Moreover, when it has different value for every shipment destination,
-- the default value should be changed by the shipment destination setup 
-- of a system.


kmSysContactSiteName  OBJECT-TYPE
    SYNTAX    OCTET STRING(SIZE(0..63))
    ACCESS    read-write
    STATUS    mandatory
    DESCRIPTION
        "
         The name of a support contact for system.
         If device cannot support this object, device should
         be implement '-' as read-only
        "
    ::= { kmSysContact 1 }

kmSysContactInfo  OBJECT-TYPE
    SYNTAX    OCTET STRING(SIZE(0..127))
    ACCESS    read-write
    STATUS    mandatory
    DESCRIPTION
        "
         Explanation of a support contact for system.
         Default value shall be a blank, and a service person
         or a user shall input it.
         If device cannot support this object, device should
         be implement '-' as read-only
        "
    ::= { kmSysContact 2 }

kmSysProductHelpURL  OBJECT-TYPE
    SYNTAX    OCTET STRING(SIZE(0..127))
    ACCESS    read-write
    STATUS    mandatory
    DESCRIPTION
        "
         URL of the support contact for system.
         If device cannot support this object, device should
         be implement '-' as read-only
        "
    ::= { kmSysContact 3 }

kmSysCorpURL  OBJECT-TYPE
    SYNTAX    OCTET STRING(SIZE(0..127))
    ACCESS    read-write
    STATUS    mandatory
    DESCRIPTION
        "
         URL of the company which provides a system.
         If device cannot support this object, device should
         be implement '-' as read-only
        "
    ::= { kmSysContact 4 }

kmSysSuppliesInfo  OBJECT-TYPE
    SYNTAX    OCTET STRING(SIZE(0..127))
    ACCESS    read-write
    STATUS    mandatory
    DESCRIPTION
        "
         A telephone number or E-mail addresses for 
         the supplies and accessories, etc.
         In the support contact in which a system has.
         Default shall be a blank, and a service person
         or a user shall input it.
         If device cannot support this object, device should
         be implement '-' as read-only
        "
    ::= { kmSysContact 5 }

kmSysContactPhoneNumber  OBJECT-TYPE
    SYNTAX    OCTET STRING(SIZE(0..31))
    ACCESS    read-write
    STATUS    mandatory
    DESCRIPTION
        "
         A telephone number of support contact. 
         Default shall be a blank, and a service person
         or a user shall input it.
         If device cannot support this object, device should
         be implement '-' as read-only
        "
    ::= { kmSysContact 6 }

kmSysContactAddress  OBJECT-TYPE
    SYNTAX    OCTET STRING(SIZE(0..320))
    ACCESS    read-write
    STATUS    mandatory
    DESCRIPTION
        "
         E-mail addresses of support contact. 
         Default shall be a blank, and a service person
         or a user shall input it.
         If device cannot support this object, device should
         be implement '-' as read-only
        "
    ::= { kmSysContact 7 }

kmSysContactUtilityLink  OBJECT-TYPE
    SYNTAX    OCTET STRING(SIZE(0..127))
    ACCESS    read-write
    STATUS    mandatory
    DESCRIPTION
        "
         URL Link of PSWC to network utility. 
         Default shall be a blank, and a network utility
         shall input it.
         If device cannot support this object, device should
         be implement '-' as read-only.
        "
    ::= { kmSysContact 8 }


-- kmSysVersion Group

--  This group shows the version of ROM and F/W etc. 
--  in which a system has. 
--  Display the version information in which all detection
--  is possible in a system.
--  Also display the version information of Options, such as NIC.
--  However, if a system can get no version information,
--  this table needs not to implement.


kmSysVersionTable  OBJECT-TYPE
    SYNTAX    SEQUENCE OF KmSysVersionEntry
    ACCESS    not-accessible
    STATUS    mandatory
    DESCRIPTION
        "The table for showing ROM and F/W version in which a system has. 
        "
    ::= { kmSysVersion 1 }

kmSysVersionEntry OBJECT-TYPE
    SYNTAX    KmSysVersionEntry
    ACCESS    not-accessible
    STATUS    mandatory
    DESCRIPTION
        "The version information of FW or ROM.
        "
    INDEX  { kmSysVersionIndex }
    ::= { kmSysVersionTable 1 } 

    KmSysVersionEntry ::= SEQUENCE {
        kmSysVersionIndex        INTEGER,
        kmSysVerName             OCTET STRING,
        kmSysVersionCode         OCTET STRING
        }

kmSysVersionIndex  OBJECT-TYPE
    SYNTAX     INTEGER
    ACCESS     read-only
    STATUS     mandatory
    DESCRIPTION
        "
         Index for uniquely showing the version information
         in which a system has. The number and the order of
         index depends on an implementation of a model.
         Implement the maximum number of index of ROM and F/W
         which is possible to detect/display, regardless of
         the availability of installation of Option etc.
        "
    ::= { kmSysVersionEntry 1 }

kmSysVerName  OBJECT-TYPE
    SYNTAX     OCTET STRING(SIZE(0..31))
    ACCESS     read-only
    STATUS     mandatory
    DESCRIPTION
        "
         The name of the function which shows a version.
        "
    ::= { kmSysVersionEntry 2 }

kmSysVersionCode  OBJECT-TYPE
    SYNTAX     OCTET STRING(SIZE(0..31))
    ACCESS     read-only
    STATUS     mandatory
    DESCRIPTION
        "
         The version of ROM and F/W.
         When the value cannot acquire although
         index is set by Option etc., display '-' (hyphen).
        "
    ::= { kmSysVersionEntry 3 }


-- kmSysComponent Group

-- This group shows the structure information of a system. 


kmSysCompConfigID  OBJECT-TYPE
    SYNTAX    Integer32
    ACCESS    read-only
    STATUS    mandatory
    DESCRIPTION
        "
         Shows the ID by the combination of the structure of device.
         Bitmap must be implemented by assigning the following 
         classifications.
         The assignment of each Bit is device dependence.

         Bit        device Type
         -----      ---------------
          0- 7      Input Tray
          8-15      Finisher
         16-23      Finisher Option
            24      Duplex
         25-26      Optional ADF
         27-31      Reserved

         This object deals with optional device that 
         is physically installable.
         Optional controller is not intended for this object.

         If system has no option or cannot detect option installed,
         this value should be always 0.
        "
    ::= { kmSysComponent 1 }

kmSysInputTrayTable  OBJECT-TYPE
    SYNTAX    SEQUENCE OF KmSysInputTrayEntry
    ACCESS    not-accessible
    STATUS    mandatory
    DESCRIPTION
        "
         The table for showing the information of Input tray 
         that is installed in a system.
         As a principle, the un-acquirable information shall be
         displayed if there is only prtInputTable, and this table
         is premised on that PrinterMIB is being implemented.
         It shall display about InputTray which is installed
         like prtInputTable.
         If a system does not have a printer engine (has no input
         tray and no PrinterMIB), this table does not need to
         implement.
        "
    ::= { kmSysComponent 2 }

kmSysInputTrayEntry OBJECT-TYPE
    SYNTAX    KmSysInputTrayEntry
    ACCESS    not-accessible
    STATUS    mandatory
    DESCRIPTION
        "
         The information of paper input tray.
        "
    INDEX  { kmSysInputTrayIndex }
    ::= { kmSysInputTrayTable 1 }

    KmSysInputTrayEntry ::= SEQUENCE {
        kmSysInputTrayIndex             INTEGER,
        kmSysInputTrayRefIndex          INTEGER,
        kmSysInputTrayName              OCTET STRING,
        kmSysInputTrayCapacitySense     INTEGER,
        kmSysInputTrayType              INTEGER,
        kmSysInputSize                  INTEGER,
        kmSysInputSizeName              OCTET STRING,
        kmSysInputFeedDir               INTEGER,
        kmSysInputTrayMediaType         INTEGER,
        kmSysInputWide                  INTEGER,
        kmSysInputSecondSide            INTEGER,
        kmSysInputMediaWeight           INTEGER,
        kmSysInputMediaColor            INTEGER,
        kmSysInputMediaIndexType        INTEGER,
        kmSysInputMediaHole             INTEGER
        }

kmSysInputTrayIndex  OBJECT-TYPE
    SYNTAX    INTEGER
    ACCESS    read-only
    STATUS    mandatory
    DESCRIPTION
        "
         Index for showing InputTray in a system.
         Index depends on the state of the implementation of
         a model, and shall be taken the amount which is worth
         for the number of InputTray in the order from 1.
        "
    ::= { kmSysInputTrayEntry 1 }

kmSysInputTrayRefIndex  OBJECT-TYPE
    SYNTAX    INTEGER
    ACCESS    read-only
    STATUS    mandatory
    DESCRIPTION
        "
         The value of prtInputIndex of a tray which
         kmSysInputTrayIndex shows.
        "
    ::= { kmSysInputTrayEntry 2 }

kmSysInputTrayName  OBJECT-TYPE
    SYNTAX    OCTET STRING(SIZE(0..16))
    ACCESS    read-write
    STATUS    mandatory
    DESCRIPTION
        "The name of InputTray.
         Default value depends on a model. In principle,
         use the name unified by DriverUI.
         Set of the character string up to 16 characters
         shall be possible.
         implementation of RO is also accepted when there are 
         capacity restrictions of NVRAM.

         Since this item is the value used when a user does
         a remote management, it is not necessary to link it
         with a setup of a printer engine.
         SNMP agent holds value, and should just provide the
         convenience to the user who remote accesses.
        "
    ::= { kmSysInputTrayEntry 3 }

kmSysInputTrayCapacitySense  OBJECT-TYPE
    SYNTAX    INTEGER {
                  noSensor    (0),
                  emptyOnly   (1),
                  nearEmpty   (2),
                  linearSense (3)
              }
    ACCESS    read-only
    STATUS    mandatory
    DESCRIPTION
        "
         This item shows the detection method of paper residual 
         quantity, and is used for distinction of the value
         displayed in prtInputCurrentLevel. The details of a 
         residual quantity display are indicated to 
         prtInputCurrentLevel.
        "
    ::= { kmSysInputTrayEntry 4 }

kmSysInputTrayType    OBJECT-TYPE
    SYNTAX    INTEGER {
                other(1),
                unknown(2),
                fixed(3),
                universal(4),
                multiPurpose(5),
                lctInternal(6),
                lctExternal(7),
                singleManual(8),
                multiManual(9)
                }
    ACCESS    read-only
    STATUS    mandatory
    DESCRIPTION
        "Shows the type of  InputTray. 
        "
    ::= { kmSysInputTrayEntry 7 }

kmSysInputSize   OBJECT-TYPE
    SYNTAX    INTEGER {
        other(1),
        unknown(2),
        a3(259),
        a4(260),
        a5(261),
        a6(262),
        b4(516),
        b5(517),
        b6(518),
        isoB4(772),
        isoB5(773),
        isoB6(774),
        c5(1029),
        metric220x330(1285),
        na13x19(1539),
        na12x18(1540),
        na11x17(1541),
        na11x15(1542),
        na11x14(1543),  -- Printer Only
        na10x14(1545),
        na8Halfx14(1547), -- 8 1/2 x 14
        na8Halfx13Half(1548), -- 8 1/2 x 13 1/2
        na8Halfx13(1549), -- 8 1/2 x 13
        na8Halfx11(1551), -- 8 1/2 x 11
        na8Quarterx13(1553), -- 8 1/4 x 13
        na8Eighthx13Quarterx(1554), -- 8 1/8 x 13
        na8x13(1556),
        na8x10Half(1557), -- 8x10 1/2
        na8x10(1558),
        na7Quarterx10Half(1559), -- 7 1/4 x 10 1/2
        na5Halfx8Half(1560), -- 5 1/2 x 8 1/2
        letterPlus(1808),  -- 8.5x12/69 inch
        kai8(2051),  -- for MFP
        kai16(2052),  -- for MFP
        kai32(2053),  -- for MFP
        kai8P(2055),  -- for Printer
        kai16P(2056),  -- for Printer
        kai32P(2057),  -- for Printer
        ra0(2304),
        ra1(2305),
        ra2(2306),
        ra3(2307),
        ra4(2308),
        sra0(2320),
        sra1(2321),
        sra2(2322),
        sra3(2323),
        sra4(2324),
        choukei3(2562),
        choukei4(2564),
        kakukei2(2578),
        youkei1(2592),
        youkei2(2593),
        youkei4(2594),
        youkei6(2595),
        dl(2826),
        envMonarch(3073),
        envCom10(3074),
        envPersonal(3121),
        japaneseDoublePostCard(3586),
        japanesePostCard(3587),
        postCard4x6(3602),
        a3Wide(8451),
        a4Wide(8452),
        a5Wide(8453),
        b4Wide(8708),
        b5Wide(8709),
        na11x17Wide(9733),
        na8Halfx14Wide(9739), -- 8 1/2 x 14
        na8Halfx11Wide(9743), -- 8 1/2 x 11
        na5Halfx8HalfWide(9752), --5 1/2 x 8 1/2
        a3Index(16643),
        a4Index(16644),
        b4Index(16900),
        b5Index(16901),
        na8Halfx14Index(17931), -- 8 1/2 x 14
        na8Halfx11Index(17935)  -- 8 1/2 x 11
        }
    ACCESS    read-only
    STATUS    mandatory
    DESCRIPTION
        "Shows the paper size of InputTray. 
         If this value is RW and when a setup is changed by MIB,
         it shall be reflected in a setup of a printer engine.
         In a unavoidable case, the access way may be RO.
        "
    ::= { kmSysInputTrayEntry 8 }

kmSysInputSizeName    OBJECT-TYPE
    SYNTAX    OCTET STRING(SIZE(0..63))
    ACCESS    read-only
    STATUS    mandatory
    DESCRIPTION
        "
         Shows the paper name of InputTray. 
         This paper name is defined by user.
         If paper size of InputTray is standard size 
         paper, this value should be Null.
        "
    ::= { kmSysInputTrayEntry 9 }

kmSysInputFeedDir   OBJECT-TYPE
    SYNTAX    INTEGER {
        other(0),
        unknown(1),
        lef(2),
        sef(3)
        }
    ACCESS    read-only
    STATUS    mandatory
    DESCRIPTION
        "Shows the paper feed direction of InputTray. 
        "
    ::= { kmSysInputTrayEntry 10 }

kmSysInputTrayMediaType OBJECT-TYPE
    SYNTAX    INTEGER {
              other(0),
              normalPaper(1),
              recycledpaper1(17),
              recyclepdaper2(18),
              finePaper1(24),
              finePaper2(25),
              postCard1(33),
              envelope(40),
              ohp(65),
              ohp2(66),
              labelPaper(69),
              tracePaper(70),
              basePaper1(81),
              basePaper2(82),
              coatedPaper1(88),
              coatedPaper2(89),
              bookPaper(97),
              roughPaper(98),
              blankInsertSheet(99),
              userDefined1(113),
              userDefined2(114),
              userDefined3(115),
              glossy(129),
              heavyGlossy(130),
              highGloss(131),
              tabPaper(161),
              letterHead(162),
              formatedPaper(164),
              specialPaper1(177),
              specialPaper2(178),
              printedPaper1(184),
              printedPaper2(185),
              thinPaper1(209),
              thinPaper2(210),
              thinPaper3(211),
              thinPaper4(212),
              thinPaper5(213),
              thickPaper1(225),
              thickPaper2(226),
              thickPaper3(227),
              thickPaper4(228),
              thickPaper5(229),
              userCustom1(241),
              userCustom2(242),
              userCustom3(243),
              userCustom4(244),
              userCustom5(245)
              }
    ACCESS    read-only
    STATUS    mandatory
    DESCRIPTION
        "Shows the media type of InputTray. 
         If this value is RW and when a setup is changed by MIB,
         it shall be reflected in a setup of a printer engine.
         In a unavoidable case, the access way may be RO.
        "
    ::= { kmSysInputTrayEntry 11 }

kmSysInputWide    OBJECT-TYPE
    SYNTAX    INTEGER {
        regular(0),
        wide(1)
        }
    ACCESS    read-only
    STATUS    mandatory
    DESCRIPTION
        "Shows the wide attribute of InputTray. 
        "
    ::= { kmSysInputTrayEntry 12 }

kmSysInputSecondSide    OBJECT-TYPE
    SYNTAX    INTEGER {
        notSpecified(0),
        secondSide(1)
        }
    ACCESS    read-only
    STATUS    mandatory
    DESCRIPTION
        "
         Shows the type of side of InputTray. 
        "
    ::= { kmSysInputTrayEntry 13 }

kmSysInputMediaWeight   OBJECT-TYPE
    SYNTAX    INTEGER {
                normal(0),
                thinPaper1(17),
                thinPaper2(18),
                thinPaper3(19),
                thinPaper4(20),
                thinPaper5(21),
                thickPaper1(33),
                thickPaper2(34),
                thickPaper3(35),
                thickPaper4(36),
                thickPaper5(37),
                thickPaper6(38),
                other(255)
                }
    ACCESS    read-only
    STATUS    optional --Conditionally Mandatory
    DESCRIPTION
        "
         Shows the paper weight  of  InputTray.
         This object is only for device of POD use.
         In device for  office use, this object should not be
         implemented.
        "
    ::= { kmSysInputTrayEntry 14 }

kmSysInputMediaColor   OBJECT-TYPE
    SYNTAX    INTEGER {
                notSpecified(0),
                white(1),
                transparency(2),
                yellow(3),
                pink(4),
                blue(5),
                green(6),
                other(15)
                }
    ACCESS    read-only
    STATUS    optional --Conditionally Mandatory
    DESCRIPTION
        "
         Shows the paper color  of  InputTray.
         This object is only for device of POD use.
         In device for  office use, this object should not be
         implemented.
        "
    ::= { kmSysInputTrayEntry 15 }

kmSysInputMediaIndexType   OBJECT-TYPE
    SYNTAX    INTEGER {
                noIndex(0),
                index1(1),
                index2(2),
                index3(3),
                index4(4),
                index5(5),
                index6(6),
                index7(7),
                index8(8),
                index9(9),
                index10(10),
                index11(11),
                index12(12),
                index13(13),
                index14(14),
                index15(15),
                other(255)
                }
    ACCESS    read-only
    STATUS    optional --Conditionally Mandatory
    DESCRIPTION
        "
         Shows the index paper type of  InputTray.
         This object is only for device of POD use.
         In device for  office use, this object should not be
         implemented.
        "
    ::= { kmSysInputTrayEntry 16 }

kmSysInputMediaHole   OBJECT-TYPE
    SYNTAX    INTEGER {
                regular(0),
                holePaper(1)
                }
    ACCESS    read-only
    STATUS    optional --Conditionally Mandatory
    DESCRIPTION
        "
         Shows the hole paper type of  InputTray.
         This object is only for device of POD use.
         In device for  office use, this object should not be
         implemented.
        "
    ::= { kmSysInputTrayEntry 17 }


kmSysOutputTrayTable  OBJECT-TYPE
    SYNTAX    SEQUENCE OF KmSysOutputTrayEntry
    ACCESS    not-accessible
    STATUS    mandatory
    DESCRIPTION
        "The table for showing the information of OutputTray
         relation in a system. Index shall be kmSysOutputTrayIndex.
         This table is for displaying the tray information of
         OutputOption (Finisher), and shall not include the
         function information of Finisher.
         If a system does not have a printer engine 
         (has no output tray and no PrinterMIB),
         this table may not be implemented.
        "
    ::= { kmSysComponent 3 }

kmSysOutputTrayEntry OBJECT-TYPE
    SYNTAX    KmSysOutputTrayEntry
    ACCESS    not-accessible
    STATUS    mandatory
    DESCRIPTION
        "The information of paper output tray.
        "
    INDEX  { kmSysOutputTrayIndex }
    ::= { kmSysOutputTrayTable 1 }

    KmSysOutputTrayEntry ::= SEQUENCE {
        kmSysOutputTrayIndex              INTEGER,
        kmSysOutputTrayRefIndex           INTEGER,
        kmSysOutputTrayDefaultName        OCTET STRING,
        kmSysOutputTrayNickName           OCTET STRING,
        kmSysOutputTrayType               INTEGER,
        kmSysOutputTrayLocation           INTEGER
        }

kmSysOutputTrayIndex  OBJECT-TYPE
    SYNTAX    INTEGER
    ACCESS    read-only
    STATUS    mandatory
    DESCRIPTION
        "
         Index for showing OutputTray in a system. 
         Index depends on the implementation of a model,
         and shall be taken the amount which is worth for
         the number of Output in the order from 1.
         In principle, when the top tray is set as 1, 
         index shall be increased in progress of going to 
         the lower part. As for the middle processing tray
         that does not become papers' final output destination,
         is not treated as OutputTray.
        "
    ::= { kmSysOutputTrayEntry 1 }

kmSysOutputTrayRefIndex  OBJECT-TYPE
    SYNTAX    INTEGER
    ACCESS    read-only
    STATUS    mandatory
    DESCRIPTION
        "
         Value of prtOutputIndex of the tray which 
         kmSysOutputTrayIndex shows.
        "
    ::= { kmSysOutputTrayEntry 2 }

kmSysOutputTrayDefaultName  OBJECT-TYPE
    SYNTAX    OCTET STRING(SIZE(0..31))
    ACCESS    read-only
    STATUS    mandatory
    DESCRIPTION
        "
         The name of OutputTray. Unify with the notation of
         a manual or a driver.
        "
    ::= { kmSysOutputTrayEntry 3 }

kmSysOutputTrayNickName  OBJECT-TYPE
    SYNTAX    OCTET STRING(SIZE(0..31))
    ACCESS    read-write
    STATUS    mandatory
    DESCRIPTION
        "
         The name of OutputTray in which a user can set up.
         In MailBin, use it in order to indicate a user's
         name, etc. which each Tray set up.
         The default strings must be the same as kmSysOutputTrayDefaultName.

         Set of the character string up to 31 characters shall be possible,
         and neither retrenchment of the number of characters
         which can be written in, nor implementation of RO
         shall be accepted.
         However, the implementation of RO is accepted only
         to the thing without MailBin as OutputOption.
         Moreover, being reflected in the display screen of
         a printer driver is desirable.
         Since this item is the value used when a user does
         a remote management, it is not necessary to link it
         with a setup of a printer engine. SNMP agent holds value,
         and should just provide the convenience to the user who
         remote accesses.

         If device cannot support this function, this object 
         should be '-' as ReadOnly.
        "
    ::= { kmSysOutputTrayEntry 4 }

kmSysOutputTrayType  OBJECT-TYPE
    SYNTAX    INTEGER {
                  other        (0),
                  standardTray(10),
                  mainTray(11),
                  subTray(12),
                  bookletTray(13),
                  stackBin(21),
                  mailBin(22)
              }
    ACCESS    read-only
    STATUS    mandatory
    DESCRIPTION
        "
         Shows the type of tray in OutputTray. 
         This is an item for judging whether it is MailBin,
         and it is used in order to judge whether the writing
         of Nickname should be possible.
        "
    ::= { kmSysOutputTrayEntry 5 }

kmSysOutputTrayLocation  OBJECT-TYPE
    SYNTAX    INTEGER {
                  other    (1),
                  unknown  (2),
                  binLoc1  (3),
                  binLoc2  (4),
                  binLoc3  (5),
                  binLoc4  (6),
                  binLoc5  (7),
                  binLoc6  (8)
                  }
    ACCESS    read-only
    STATUS    optional --Conditionally Mandatory
    DESCRIPTION
        "
         Shows the location of OutputTray. 
        "
    ::= { kmSysOutputTrayEntry 6 }


kmSysFinishingTable  OBJECT-TYPE
    SYNTAX    SEQUENCE OF KmSysFinishingEntry
    ACCESS    not-accessible
    STATUS    mandatory
    DESCRIPTION
        "The table for showing the information of Finisher
         relation of a system. Index shall be kmSysFinishingIndex.
         This is for showing the function which Finisher has and
         the information of OutputTray shall not be included.
         This Table does not need to be displayed when Finisher
         is not installed.
        "
    ::= { kmSysComponent 4 }

kmSysFinishingEntry OBJECT-TYPE
    SYNTAX    KmSysFinishingEntry
    ACCESS    not-accessible
    STATUS    mandatory
    DESCRIPTION
        "The information of finisher's functions.
        "
    INDEX  { kmSysFinishingIndex }
    ::= { kmSysFinishingTable 1 }

    KmSysFinishingEntry ::= SEQUENCE {
        kmSysFinishingIndex           INTEGER,
        kmSysFinishingName            OCTET STRING,
        kmSysFinishingFunction        INTEGER
        }

kmSysFinishingIndex  OBJECT-TYPE
    SYNTAX    INTEGER
    ACCESS    read-only
    STATUS    mandatory
    DESCRIPTION
        "Index for showing Finisher in a system. 
         Index shall depend on an implementation of a model.
         When Finisher which is installed is one, the value
         of index shall be always 1 regardless of types.
        "
    ::= { kmSysFinishingEntry 1 }

kmSysFinishingName  OBJECT-TYPE
    SYNTAX    OCTET STRING (SIZE(0..31))
    ACCESS    read-only
    STATUS    mandatory
    DESCRIPTION
        "The name of installed Finisher. 
         Unify with a manual and the notation of a driver.
        "
    ::= { kmSysFinishingEntry 2 }

kmSysFinishingFunction  OBJECT-TYPE
    SYNTAX    INTEGER
    ACCESS    read-only
    STATUS    mandatory
    DESCRIPTION
        "Finishing function is expressed with Bitmap
         and the function in which Finisher has is 
         shown with the total.

           Bit   Value    Finishing Type
           ---   -----    ---------------
             0      1       shift
             1      2       mailBin
             2      4       cornerStaple
             3      8       sideStaple
             4     16       holePunch2Point
             5     32       holePunch3point
             6     64       holePunch4Point
             7    128       halfFold
             8    256       multihalfFold
             9    512       zFold
            10   1024       zigzagFold
            11   2048       triFold
            12   4096       multiTriFold
            13   8192       doubleParallelFold
            14  16384       gateFold
            15  32768       halfFoldCenterStaple
            16  65536       perfectBinding 
            17 131072       coverSheetFeeder
            18 262144       trimming
        "
    ::= { kmSysFinishingEntry 3 }


kmSysOptionTable  OBJECT-TYPE
    SYNTAX    SEQUENCE OF KmSysOptionEntry
    ACCESS    not-accessible
    STATUS    mandatory
    DESCRIPTION
        "The table for showing the information of installed
         option relation of a system.
         Index shall be kmSysOptionIndex.
         This is for showing the name and status of option
         that is identified by kmSysCompConfigID.

         This Table does not need to be displayed when no option.
        "
    ::= { kmSysComponent 5 }

kmSysOptionEntry OBJECT-TYPE
    SYNTAX    KmSysOptionEntry
    ACCESS    not-accessible
    STATUS    mandatory
    DESCRIPTION
        "
         The information of options.
        "
    INDEX  { kmSysFinishingIndex }
    ::= { kmSysOptionTable 1 }

    KmSysOptionEntry ::= SEQUENCE {
        kmSysOptionIndex    INTEGER,
        kmSysOptionType     INTEGER,
        kmSysOptionName     OCTET STRING,
        kmSysOptionStatus   INTEGER
        }

kmSysOptionIndex  OBJECT-TYPE
    SYNTAX    INTEGER
    ACCESS    read-only
    STATUS    mandatory
    DESCRIPTION
        "
         Index for showing option in a system. 
         Index shall depend on an implementation of a model.
         In principal, index order should be same as
         bit order of kmSysCompConfigID.
        "
    ::= { kmSysOptionEntry 1 }

kmSysOptionType  OBJECT-TYPE
    SYNTAX    INTEGER{
            other          (1),
            unknown        (2),
            inputTray      (3),
            drawerBase     (4),
            finisher       (5),
            finisherOption (6),
            duplex         (7),
            adf            (8)
            }
    ACCESS    read-only
    STATUS    mandatory
    DESCRIPTION
        "
         Shows the type of option. 
        "
    ::= { kmSysOptionEntry 2 }


kmSysOptionName  OBJECT-TYPE
    SYNTAX    OCTET STRING(SIZE(0..31))
    ACCESS    read-only
    STATUS    mandatory
    DESCRIPTION
        "
         The name of Option.
         Unify with the notation of a manual or a driver.
        "
    ::= { kmSysOptionEntry 3 }

kmSysOptionStatus  OBJECT-TYPE
    SYNTAX    INTEGER{
                notPresent(1),
                available(2),
                disable(3)
                }
    ACCESS    read-only
    STATUS    mandatory
    DESCRIPTION
        "
         The status of option.
        "
    ::= { kmSysOptionEntry 4 }


kmSysTandemInfo  OBJECT IDENTIFIER ::= { kmSysComponent 6 }

kmSysTandemConnection    OBJECT-TYPE
    SYNTAX    INTEGER {
                other (1),
                unknown (2),
                yes (3),
                no (4),
                notPresent (5)
                }
    ACCESS    read-only
    STATUS    optional --Conditionally Mandatory
    DESCRIPTION
        "
         Shows that device is connected or not as 
         tandem printer. 
        "
    ::= { kmSysTandemInfo 1 }


kmSysTandemType    OBJECT-TYPE
    SYNTAX    INTEGER {
                other (1),
                unknown (2),
                master (3),
                slave (4),
                notConnected (5)
                }
    ACCESS    read-only
    STATUS    optional --Conditionally Mandatory
    DESCRIPTION
        "
         Shows the status of device that is connected as 
         tandem printer. 
        "
    ::= { kmSysTandemInfo 2 }


-- kmSysCounter Group

--   Group of the counter relation corresponding to the account
--   management system. 
--
--   It shall have the following 3 groups.
--   1. kmSysCounterConfig Group
--        The setup item relevant to whole counter
--   2. kmSysSystemCounter Group
--        The counter item which a device has
--   3. kmSysServiceCounter Group
--        The counter item for service purpose
--
--   In addition, Syntax of all the counters defined in
--   kmSysCounterGroup shall be Integer32, and when a model
--   does not support the defined counter, should implement -1.
--

    kmSysCounterConfig    OBJECT IDENTIFIER ::= { kmSysCounter 1 }
    kmSysSystemCounter    OBJECT IDENTIFIER ::= { kmSysCounter 2 }

    kmSysServiceCounter   OBJECT IDENTIFIER ::= { kmSysCounter 4 }

-- kmSysCounterConfig Group

kmSysCounterSupportedType  OBJECT-TYPE
    SYNTAX    INTEGER
    ACCESS    read-only
    STATUS    mandatory
    DESCRIPTION
        "
         Shows the type of a counter supported in a system.
         The counter which a system has can specify by referring
         to this.
         Displays the counter to support with Bitmap and shows
         the supporting counter by the total integer value.

         Bit    Value    CounterType
         ---    -----    ---------------
          0        1     GeneralCounter
          1        2     PrintFunctionCounter
          2        4     ScanFunctionCounter
          3        8     PapersSizeCounter

          5       32     TonerLifeCounter
          6       64     ServiceGeneralCounter
          7      128     JamCounter
          8      256     TroubleCounter
          9      512     UnitLifeCounter

        "
    ::= { kmSysCounterConfig 1 }

kmSysDuplexCountMode  OBJECT-TYPE
    SYNTAX    INTEGER {
                  unknown (0),
                  singleCount (1),
                  doubleCount (2)
              }
    ACCESS    read-write
    STATUS    mandatory
    DESCRIPTION
        "
         Sets up whether Duplex printing is counted two times
         to TotalCounter at the time.
         This setup is reflected to all TotalCounters.
         This object may be implemented with RO access.
         If a system doesn't have this setting (e.g. printer), 
         the value of the static count mode (1 or 2) must be implemented.
         Basically this value must not be '0'.
        "
    ::= { kmSysCounterConfig 2 }

kmSysLargeSizeCountMode  OBJECT-TYPE
    SYNTAX    INTEGER {
                  unknown (0),
                  singleCount (1),
                  doubleCount (2)
              }
    ACCESS    read-write
    STATUS    mandatory
    DESCRIPTION
        "
         Sets up whether LargeSize is counted two times
         to TotalCounter at the time.
         This setup is reflected to all TotalCounters.
         This object should be implemented with RO access.
         This setting is the item of a service setting. 
         A setup of a service setting is reflected to this object.
         "
    ::= { kmSysCounterConfig 3 }

kmSysLargeSizeMode  OBJECT-TYPE
    SYNTAX    INTEGER {
                  noLargeSize (0),
                  modeA       (1),
                  modeB       (2),
                  modeC       (3) 
                  }
    ACCESS    read-write
    STATUS    mandatory
    DESCRIPTION
        "
         Sets up the type of paper counted as LargeSize.

         noLargeSize(0): indicates that the count of LargeSize is
                         not performed or not detect large size type.
         typeA(1): 11x17, A3
         typeB(2): 11x17, A3, B4, 8_1/2x14(Legal)
         typeC(3): 11x17, A3, B4, 8_1/2x14(Legal), 220x330(FLS4),  
                   8_1/2x13_1/2(F4),  8_1/2x13(F4/FLS3), 
                   8_1/4x13(F4/FLS2), 8_1/8x13_1/4(F4), 
                   8x13(F4/FLS1)      

         This object should be implemented with RO access.
        "
    ::= { kmSysCounterConfig 4 }

kmSysColorCountSupportType  OBJECT-TYPE
    SYNTAX    INTEGER
    ACCESS    read-only
    STATUS    mandatory
    DESCRIPTION
        "
         It is shown what kind of counter by the color is supported.
         The color counter which a device supports can be specified
         by referring to this. Displays the type of counter to
         support with Bitmap and shows the supporting counter by
         the total. The type counter that is shown in here shall
         be held by the color-related counter.

         Bit    Value    CounterType
         ---    -----    -----------------
          0        1     total            -- Total (BW & Color)
          1        2     bw               --The monochrome counter
                                          --in a color machine
          2        4     fourColor  (4c)  --Full color
                                          -- (All of C, M, Y, and K are used)
          3        8     threeColor (3c)  --Monochrome color 
                                          --(monochrome is taken out using
                                          -- three colors of C, M, and Y)
          4       16     cmy              --CMY:  (using any 1 color of C/M/Y)

          5       32     rgb              --RGB: (using three colors of CMY)

          6       64     monoColor        --The total of 3C, CMY, and RGB

          7      128     paperPath        --PaperPath counter

          8      256     twoColor

         For Example,
         MFP has full color mode should be 
         bw(2)+fourColor(4)+monoColor(64)+twoColor(256) = 326 
        "
    ::= { kmSysCounterConfig 5 }

-- kmSysSystemCounter Group

    kmSysGeneralCounter    OBJECT IDENTIFIER ::= { kmSysSystemCounter 1 }

-- kmSysGeneralCounter Group

--  The counter group which all devices have to implement.
--  Especially the total counter is indispensable.
--  About Large and Duplex, in the device which does not have
--  that function, it always shall be the implementation of -1.


kmSysTotalCount  OBJECT-TYPE
    SYNTAX    Integer32
    ACCESS    read-only
    STATUS    mandatory
    DESCRIPTION
        "
         The total print count of a system.
         Displays the total of Copy, Print.
         About the count method of Duplex and LargeSize,
         it depends on a setup. 
         About a color machine, it shall be the total of all
         color classifications.
        "
    ::= { kmSysGeneralCounter 1 }

kmSysLargeSizeCount  OBJECT-TYPE
    SYNTAX    Integer32
    ACCESS    read-only
    STATUS    mandatory
    DESCRIPTION
        "
         The total print count of LargeSize paper.
         About the type of LargeSize, it depends on
         a setup of kmSysLargeSizeMode.
         When the setup of kmSysLargeSizeMode is noLargesize(0),
         this counter always should be -1.
         In addition, also in the system without A4 machine, etc.,
         this counter should be -1.
        "
    ::= { kmSysGeneralCounter 2 }

kmSysDuplexCount  OBJECT-TYPE
    SYNTAX    Integer32
    ACCESS    read-only
    STATUS    mandatory
    DESCRIPTION
        "
         The total print count of Duplex (back). 
         In the system without Duplex mechanism, it should be -1.
        "
    ::= { kmSysGeneralCounter 3 }

kmSysLargeDuplexCount  OBJECT-TYPE
    SYNTAX    Integer32
    ACCESS    read-only
    STATUS    mandatory
    DESCRIPTION
        "
         The total print count of LargeSize, and also Duplex (back).
         About the type of LargeSize, it depends on a setup of
         kmSysLargeSizeMode. 
         When the setup of kmSysLargeSizeMode is noLargeSize (0),
         this counter always shall be -1.
         In addition, in the system of A4 machine or in the 
         system without Duplex, this counter always should be -1.

         In MFP, since this counter is not supported,
         the value of this object should be always -1. 
        "
    ::= { kmSysGeneralCounter 4 }

kmSysScanTotalCount  OBJECT-TYPE
    SYNTAX    Integer32
    ACCESS    read-only
    STATUS    mandatory
    DESCRIPTION
        "
         Total count scanned as scanner functions 
         (Fax, Scan) in the system.
         It shall be the total of kmSysScanReadTotalCount
         of kmSysScanCounterTable.

         In the device without Scan function,
         it always shall be -1.
        "
    ::= { kmSysGeneralCounter 5 }

kmSysTotalJamCount  OBJECT-TYPE
    SYNTAX    Integer32
    ACCESS    read-only
    STATUS    mandatory
    DESCRIPTION
        "
         The number of times of Jam occurred in the system.
         It shall be the total of all Jam counters.
         (including ADF jams).
        "
    ::= { kmSysGeneralCounter 6 }

kmSysTotalTroubleCount  OBJECT-TYPE
    SYNTAX    Integer32
    ACCESS    read-only
    STATUS    mandatory
    DESCRIPTION
        "
         The number of times of Trouble (FatalError) occurred in
         the system. It shall be the total of all Trouble counters.
        "
    ::= { kmSysGeneralCounter 7 }

kmSysTotalOriginalCount  OBJECT-TYPE
    SYNTAX    Integer32
    ACCESS    read-only
    STATUS    mandatory
    DESCRIPTION
        "
         The total count of originals for printing.
         It shall be the total of all Trouble counters.
        "
    ::= { kmSysGeneralCounter 8 }

kmSysTotalPaperCount  OBJECT-TYPE
    SYNTAX    Integer32
    ACCESS    read-only
    STATUS    mandatory
    DESCRIPTION
        "
         The total count of printed papers.
         It shall be the total of all Trouble counters.
        "
    ::= { kmSysGeneralCounter 9 }


-- kmSysPrintFunctionCounterTable 

kmSysPrintFunctionCounterTable  OBJECT-TYPE
    SYNTAX    SEQUENCE OF KmSysPrintFunctionCounterEntry
    ACCESS    not-accessible
    STATUS    optional --Conditionally Mandatory
    DESCRIPTION
        "
         The table for showing the counter by the color and function.

         In the BW printer, it is not necessary to implement.
         
         The BW MFP should have this table as copy/print function
         counter, with color type is only bw.
        "
    ::= { kmSysSystemCounter 2 }

kmSysPrintFunctionCounterEntry OBJECT-TYPE
    SYNTAX    KmSysPrintFunctionCounterEntry
    ACCESS    not-accessible
    STATUS    optional --Conditionally Mandatory
    DESCRIPTION
        "
         The counters of color and print functions.
        "
    INDEX  { kmSysPrintFunctionColorIndex, kmSysPrintFunctionIndex }
    ::= { kmSysPrintFunctionCounterTable 1 }

    KmSysPrintFunctionCounterEntry ::= SEQUENCE {
        kmSysPrintFunctionColorIndex              INTEGER,
        kmSysPrintFunctionIndex                   INTEGER,
        kmSysPrintFunctionColorType               INTEGER,
        kmSysPrintFunctionType                    INTEGER,
        kmSysPrintFunctionTotalCount              Integer32,
        kmSysPrintFunctionDuplexCount             Integer32,
        kmSysPrintFunctionLargeSizeCount          Integer32,
        kmSysPrintFunctionLargeDuplexCount        Integer32
        }

kmSysPrintFunctionColorIndex  OBJECT-TYPE
    SYNTAX    INTEGER
    ACCESS    read-only
    STATUS    optional --Conditionally Mandatory
    DESCRIPTION
        "
         Index for showing the color in the counter
         by color/function.
         By the color, index should  be ordered by bw, 4c , 
         other colors.
        "
    ::= { kmSysPrintFunctionCounterEntry 1 }

kmSysPrintFunctionIndex  OBJECT-TYPE
    SYNTAX    INTEGER
    ACCESS    read-only
    STATUS    optional --Conditionally Mandatory
    DESCRIPTION
        "
         Index for showing the function in the counter
         by color/function.
         By the function, index should  be ordered by 
         copy, print.
        "
    ::= { kmSysPrintFunctionCounterEntry 2 }

kmSysPrintFunctionColorType  OBJECT-TYPE
    SYNTAX    INTEGER {
                  bw         (1),
                  fourColor  (2),
                  monoColor  (6),
                  paperPath  (7),
                  twoColor   (8)
              }
    ACCESS    read-only
    STATUS    optional --Conditionally Mandatory
    DESCRIPTION
        "
         Shows the color mode in the counter by color/function.
        "
    ::= { kmSysPrintFunctionCounterEntry 3 }

kmSysPrintFunctionType  OBJECT-TYPE
    SYNTAX    INTEGER {
                  copyFunction       (1),
                  printFunction      (2),
                  reportPrint        (5),
                  totalPrint         (6)
              }
    ACCESS    read-only
    STATUS    optional --Conditionally Mandatory
    DESCRIPTION
        "
         Shows the function in the counter by color/function.
        "
    ::= { kmSysPrintFunctionCounterEntry 4 }

kmSysPrintFunctionTotalCount  OBJECT-TYPE
    SYNTAX    Integer32
    ACCESS    read-only
    STATUS    optional --Conditionally Mandatory
    DESCRIPTION
        "
         The total print counts in a specified function.
         About the count method, complies with GeneralCounter
        "
    ::= { kmSysPrintFunctionCounterEntry 5 }

kmSysPrintFunctionDuplexCount  OBJECT-TYPE
    SYNTAX    Integer32
    ACCESS    read-only
    STATUS    optional --Conditionally Mandatory
    DESCRIPTION
        "
         The print count of Duplex (back) in a specified function.
         The print count of the LargeSize paper in
         a specified function.
         About the count method, complies with GeneralCounter.

         If device has not this counter, this value should be always -1.
        "
    ::= { kmSysPrintFunctionCounterEntry 6 }

kmSysPrintFunctionLargeSizeCount  OBJECT-TYPE
    SYNTAX    Integer32
    ACCESS    read-only
    STATUS    optional --Conditionally Mandatory
    DESCRIPTION
        "
         The print count of the LargeSize paper in
         a specified function.
         About the count method, complies with GeneralCounter.
         If device has not this counter, this value should be always -1.
        "
    ::= { kmSysPrintFunctionCounterEntry 7 }

kmSysPrintFunctionLargeDuplexCount  OBJECT-TYPE
    SYNTAX    Integer32
    ACCESS    read-only
    STATUS    optional --Conditionally Mandatory
    DESCRIPTION
        "
         The print count of LargeSize and Duplex (back)
         in a specified function.
         About the count method, complies with GeneralCounter.
         If device has not this counter, this value should be always -1.

         In MFP, this counter is usually not supported,
         this value should be -1.
        "
    ::= { kmSysPrintFunctionCounterEntry 8 }


-- kmSysScanFunctionCounterTable

kmSysScanFunctionCounterTable  OBJECT-TYPE
    SYNTAX    SEQUENCE OF KmSysScanFunctionCounterEntry
    ACCESS    not-accessible
    STATUS    optional --Conditionally Mandatory
    DESCRIPTION
        "
         The table for showing the counter in a scan function.
         It is not necessary to implement in the system without
         Scan function counter.
        "
    ::= { kmSysSystemCounter 3 }

kmSysScanFunctionCounterEntry OBJECT-TYPE
    SYNTAX    KmSysScanFunctionCounterEntry
    ACCESS    not-accessible
    STATUS    optional --Conditionally Mandatory
    DESCRIPTION
        "
         The information of scan function counter.
        "
    INDEX  { kmSysScanFunctionIndex }
    ::= { kmSysScanFunctionCounterTable 1 }

    KmSysScanFunctionCounterEntry ::= SEQUENCE {
        kmSysScanFunctionIndex         INTEGER,
        kmSysScanFunctionType          INTEGER,

        kmSysScanReadTotalCount        Integer32,
        kmSysScanReadLargeSizeCount    Integer32,
        kmSysScanPrintTotalCount       Integer32,
        kmSysScanPrintLargeSizeCount   Integer32,
        kmSysScanSendCount             Integer32,
        kmSysScanReceiveCount          Integer32
        }

kmSysScanFunctionIndex  OBJECT-TYPE
    SYNTAX    INTEGER
    ACCESS    read-only
    STATUS    optional --Conditionally Mandatory
    DESCRIPTION
        "
        Index for showing the function in
        a scan function counter.
        Index should be device dependence,
        however, it is recommended that the Index
        is given in the order of scan, fax. 
        If device has not functional counter,
        this value should be 1 as fixed value.
        "
    ::= { kmSysScanFunctionCounterEntry 1 }

kmSysScanFunctionType  OBJECT-TYPE
    SYNTAX    INTEGER {
                  other (0),
                  sendTotal (1),
                  scanner (4),
                  fax (5)
              }
    ACCESS    read-only
    STATUS    optional --Conditionally Mandatory
    DESCRIPTION
        "
         Shows the function in a scan function counter.
        "
    ::= { kmSysScanFunctionCounterEntry 2 }

kmSysScanReadTotalCount  OBJECT-TYPE
    SYNTAX    Integer32
    ACCESS    read-only
    STATUS    optional --Conditionally Mandatory
    DESCRIPTION
        "
         Scan read count.
         One is counted for one Scan of one side.
         Handling of large size must be compliant
         with device specification. 
        "
    ::= { kmSysScanFunctionCounterEntry 5 }

kmSysScanReadLargeSizeCount  OBJECT-TYPE
    SYNTAX    Integer32
    ACCESS    read-only
    STATUS    optional --Conditionally Mandatory
    DESCRIPTION
        "
         Scan read count of large size.
         One is counted for one Scan of one side of large size.
         Handling of large size must be compliant 
         with device specification

         When the setting of kmSysLargeSizeMode is noLargeSize (0),
         this counter should be always -1. 
         In device of A4size, this counter should be always -1.
        "
    ::= { kmSysScanFunctionCounterEntry 6 }

kmSysScanPrintTotalCount  OBJECT-TYPE
    SYNTAX    Integer32
    ACCESS    read-only
    STATUS    optional --Conditionally Mandatory
    DESCRIPTION
        "
         The counts of print impression of scan function,
         include fax receive and print from scan box.
         Unit is impression.
        "
    ::= { kmSysScanFunctionCounterEntry 7 }

kmSysScanPrintLargeSizeCount  OBJECT-TYPE
    SYNTAX    Integer32
    ACCESS    read-only
    STATUS    optional --Conditionally Mandatory
    DESCRIPTION
        "
         The counts of large size print impression of scan function,
         include fax receive and print from scan box.
         Unit is impression.
         About the type of LargeSize, it depends on 
         device specifications.

         If device has no Large size scan counter,
         this object should be always -1.
        "
    ::= { kmSysScanFunctionCounterEntry 8 }

kmSysScanSendCount  OBJECT-TYPE
    SYNTAX    Integer32
    ACCESS    read-only
    STATUS    optional --Conditionally Mandatory
    DESCRIPTION
        "
         The counts of send impression of scan function.
         In fax function, this counter must be implemented.

         In scanner function, this counter should be always
         -1. (need not to implement this counter).
        "
    ::= { kmSysScanFunctionCounterEntry 9 }

kmSysScanReceiveCount  OBJECT-TYPE
    SYNTAX    Integer32
    ACCESS    read-only
    STATUS    optional --Conditionally Mandatory
    DESCRIPTION
        "
         The counts of receive impression of scan function.
         In fax function, this counter must be implemented.

         In scanner function, this counter should be always
         -1. (need not to implement this counter).
        "
    ::= { kmSysScanFunctionCounterEntry 10 }


-- kmSysSizeCounterTable 

kmSysSizeCounterTable  OBJECT-TYPE
    SYNTAX    SEQUENCE OF KmSysSizeCounterEntry
    ACCESS    not-accessible
    STATUS    optional --Conditionally Mandatory
    DESCRIPTION
        "The table of the counter by the paper sizes and types.
         The model which supports plural paper sizes/types has
         to implement.
         Regardless of shipment destination, having a counter
         to all the paper sizes/types that can be printed is recommended.
         By implementation, implementing different size counter
         by shipment destination is also accepted.
         It shall also have index by the functions so that
         it can correspond to the counter by sizes by the functions.
        "
    ::= { kmSysSystemCounter 4 }

kmSysSizeCounterEntry  OBJECT-TYPE
    SYNTAX    KmSysSizeCounterEntry
    ACCESS    not-accessible
    STATUS    optional --Conditionally Mandatory
    DESCRIPTION
        "The information of paper size counters.
        "
    INDEX  { kmSysSizeFunctionIndex, kmSysSizeTypeIndex }
    ::= { kmSysSizeCounterTable 1 }

    KmSysSizeCounterEntry ::= SEQUENCE {
        kmSysSizeFunctionIndex      INTEGER,
        kmSysSizeTypeIndex          INTEGER,
        kmSysSizeFunction           INTEGER,
        kmSysSizeType               INTEGER,
        kmSysSizeCount              Integer32,
        kmSysSizeMediaType          INTEGER
        }

kmSysSizeFunctionIndex  OBJECT-TYPE
    SYNTAX    INTEGER
    ACCESS    read-only
    STATUS    optional --Conditionally Mandatory
    DESCRIPTION
        "
         Index for showing the function which becomes
         the count object in the counter by paper sizes.
        "
    ::= { kmSysSizeCounterEntry 1 }

kmSysSizeTypeIndex  OBJECT-TYPE
    SYNTAX    INTEGER
    ACCESS    read-only
    STATUS    optional --Conditionally Mandatory
    DESCRIPTION
        "
         Index for showing the paper which becomes
         the count object in the counter by paper sizes.
         Only the type of corresponding paper shall be
         taken in the order from 1.
         MFP should have 10 indexes.
        "
    ::= { kmSysSizeCounterEntry 2 }

kmSysSizeFunction  OBJECT-TYPE
    SYNTAX    INTEGER {
                  total               (0),
                  copyFunction        (1),
                  printFunction       (2),
                  iFaxReceiveFunction (3),
                  faxReceiveFunction  (4)
              }
    ACCESS    read-only
    STATUS    optional --Conditionally Mandatory
    DESCRIPTION
        "Shows the function which becomes the count
         object in the counter by paper size.

        In MFP, this value should be only total(0).
        "
    ::= { kmSysSizeCounterEntry 3 }

kmSysSizeType  OBJECT-TYPE
    SYNTAX    INTEGER {
        other(1),  -- for Special
        unknown(2),
        a3(259),
        a4(260),
        a5(261),
        a6(262),
        b4(516),
        b5(517),
        b6(518),
        isoB4(772),
        isoB5(773),
        isoB6(774),
        c5(1029),
        metric220x330(1285),
        na13x19(1539),
        na12x18(1540),
        na11x17(1541),
        na11x15(1542),
        na11x14(1543),  -- Printer Only
        na10x14(1545),
        na8Halfx14(1547), -- 8 1/2 x 14
        na8Halfx13Half(1548), -- 8 1/2 x 13 1/2
        na8Halfx13(1549), -- 8 1/2 x 13
        na8Halfx11(1551), -- 8 1/2 x 11
        na8Quarterx13(1553), -- 8 1/4 x 13
        na8Eighthx13Quarterx(1554), -- 8 1/8 x 13
        na8x13(1556),
        na8x10Half(1557), -- 8x10 1/2
        na8x10(1558),
        na7Quarterx10Half(1559), -- 7 1/4 x 10 1/2
        na5Halfx8Half(1560), -- 5 1/2 x 8 1/2
        letterPlus(1808),  -- 8.5x12/69 inch
        kai8(2051),  -- for MFP
        kai16(2052),  -- for MFP
        kai32(2053),  -- for MFP
        kai8P(2055),  -- for Printer
        kai16P(2056),  -- for Printer
        kai32P(2057),  -- for Printer
        ra0(2304),
        ra1(2305),
        ra2(2306),
        ra3(2307),
        ra4(2308),
        sra0(2320),
        sra1(2321),
        sra2(2322),
        sra3(2323),
        sra4(2324),
        choukei3(2562),
        choukei4(2564),
        kakukei2(2578),
        youkei1(2592),
        youkei2(2593),
        youkei4(2594),
        youkei6(2595),
        dl(2826),
        envMonarch(3073),
        envCom10(3074),
        envPersonal(3121),
        japaneseDoublePostCard(3586),
        japanesePostCard(3587),
        postCard4x6(3602),
        a3Wide(8451),
        a4Wide(8452),
        a5Wide(8453),
        b4Wide(8708),
        b5Wide(8709),
        na11x17Wide(9733),
        na8Halfx14Wide(9739), -- 8 1/2 x 14
        na8Halfx11Wide(9743), -- 8 1/2 x 11
        na5Halfx8HalfWide(9752), --5 1/2 x 8 1/2
        a3Index(16643),
        a4Index(16644),
        b4Index(16900),
        b5Index(16901),
        na8Halfx14Index(17931), -- 8 1/2 x 14
        na8Halfx11Index(17935)  -- 8 1/2 x 11
        }
    ACCESS    read-only
    STATUS    optional --Conditionally Mandatory
    DESCRIPTION
        "
         Shows the paper size for counted. 
         Other(1) is used for other paper size (and for Special). 
        "
    ::= { kmSysSizeCounterEntry 4 }

kmSysSizeCount  OBJECT-TYPE
    SYNTAX    Integer32
    ACCESS    read-only
    STATUS    optional --Conditionally Mandatory
    DESCRIPTION
        "
         The number of print of the specified function
         and specified size, media type.
        "
    ::= { kmSysSizeCounterEntry 5 }

kmSysSizeMediaType  OBJECT-TYPE
    SYNTAX    INTEGER {
              noSelection(0),  -- Counter is not care paper types.
              normalPaper(1),
              recycledpaper1(17),
              recyclepdaper2(18),
              finePaper1(24),
              finePaper2(25),
              postCard1(33),
              envelope(40),
              ohp(65),
              ohp2(66),
              labelPaper(69),
              tracePaper(70),
              basePaper1(81),
              basePaper2(82),
              coatedPaper1(88),
              coatedPaper2(89),
              bookPaper(97),
              roughPaper(98),
              blankInsertSheet(99),
              userDefined1(113),
              userDefined2(114),
              userDefined3(115),
              glossy(129),
              heavyGlossy(130),
              highGloss(131),
              tabPaper(161),
              letterHead(162),
              formatedPaper(164),
              specialPaper1(177),
              specialPaper2(178),
              printedPaper1(184),
              printedPaper2(185),
              thinPaper1(209),
              thinPaper2(210),
              thinPaper3(211),
              thinPaper4(212),
              thinPaper5(213),
              thickPaper1(225),
              thickPaper2(226),
              thickPaper3(227),
              thickPaper4(228),
              thickPaper5(229),
              userCustom1(241),
              userCustom2(242),
              userCustom3(243),
              userCustom4(244),
              userCustom5(245),

              -- for Color Paper (0x0F##)
              colorPaper(3841), -- normal paper

              -- for Second Side (0x1###)
              normalPaperSecondSide(4097),
              thickPaper1SecondSide(4321),
              thickPaper2SecondSide(4322),
              thickPaper3SecondSide(4323)
              }
    ACCESS    read-only
    STATUS    optional --Conditionally Mandatory
    DESCRIPTION
        "
        Shows the media type for counted.
        "
    ::= { kmSysSizeCounterEntry 6 }

-- kmSysTonerLifeCounterTable 

kmSysTonerLifeCounterTable  OBJECT-TYPE
    SYNTAX    SEQUENCE OF KmSysTonerLifeCounterEntry
    ACCESS    not-accessible
    STATUS    optional --Conditionally Mandatory
    DESCRIPTION
        "
         The table of toner life counter.
        "
    ::= { kmSysSystemCounter 5 }

kmSysTonerLifeCounterEntry  OBJECT-TYPE
    SYNTAX    KmSysTonerLifeCounterEntry
    ACCESS    not-accessible
    STATUS    optional --Conditionally Mandatory
    DESCRIPTION
        "
         The information of toner life counters.
        "
    INDEX  { kmSysTonerTypeIndex }
    ::= { kmSysTonerLifeCounterTable 1 }

    KmSysTonerLifeCounterEntry ::= SEQUENCE {
        kmSysTonerTypeIndex        INTEGER,
        kmSysTonerType             INTEGER,
        kmSysTonerTypeCount        Counter32
        }

kmSysTonerTypeIndex  OBJECT-TYPE
    SYNTAX    INTEGER
    ACCESS    read-only
    STATUS    optional --Conditionally Mandatory
    DESCRIPTION
        "
         Index for Toner used as the count object in TonerLife 
         counter.
        "
    ::= { kmSysTonerLifeCounterEntry 1 }

kmSysTonerType   OBJECT-TYPE
    SYNTAX    INTEGER {
                  other (0),
                  cyan (1),
                  magenta (2),
                  yellow (3),
                  black (4) 
                  }
    ACCESS    read-only
    STATUS    optional --Conditionally Mandatory
    DESCRIPTION
        "
         Toner used as the count object in TonerLife counter is shown.
        "
    ::= { kmSysTonerLifeCounterEntry 2 }

kmSysTonerTypeCount  OBJECT-TYPE
    SYNTAX    Counter32
    ACCESS    read-only
    STATUS    optional --Conditionally Mandatory
    DESCRIPTION
        "
         TonerLife count.
         This is used for calculation of Coverage, 
         by the amount of Toner consumption, etc.
         by counting Dot number used for every Toner.

         Count unit is 2Mpixel(2097152pixcel) when 1 pixel 
         is 1 dot of 1200x1200dpi.
        "
    ::= { kmSysTonerLifeCounterEntry 3 }


-- kmSysServiceCounter Group

kmSysSrvGeneralCounter  OBJECT IDENTIFIER ::= { kmSysServiceCounter 1 }

kmSysSrvDeveloperCount  OBJECT-TYPE
    SYNTAX    Counter32
    ACCESS    read-only
    STATUS    optional --Conditionally Mandatory
    DESCRIPTION
        "
         The count of developer.
        "
    ::= { kmSysSrvGeneralCounter 1 }

kmSysSrvDrumCount  OBJECT-TYPE
    SYNTAX    Counter32
    ACCESS    read-only
    STATUS    optional --Conditionally Mandatory
    DESCRIPTION
        "
         The count of drum.
        "
    ::= { kmSysSrvGeneralCounter 2 }

kmSysSrvPMCount   OBJECT-TYPE
    SYNTAX    Counter32
    ACCESS    read-only
    STATUS    optional --Conditionally Mandatory
    DESCRIPTION
        "
         The count of pre maintenance.
        "
    ::= { kmSysSrvGeneralCounter 3 }


kmSysSrvJamCounterTable OBJECT-TYPE
    SYNTAX    SEQUENCE OF KmSysSrvJamCounterEntry
    ACCESS    not-accessible
    STATUS    optional --Conditionally Mandatory
    DESCRIPTION
        "
         The table for showing the counter of jam.
         It is not necessary to implement in the system without
         the way of counts reading function (ftp etc.)
        "
    ::= { kmSysServiceCounter 2 }

kmSysSrvJamCounterEntry OBJECT-TYPE
    SYNTAX    KmSysSrvJamCounterEntry
    ACCESS    not-accessible
    STATUS    optional --Conditionally Mandatory
    DESCRIPTION
        "
         The information of jam counter.
        "
    INDEX  { kmSysSrvJamCounterIndex }
    ::= { kmSysSrvJamCounterTable 1 }

    KmSysSrvJamCounterEntry ::= SEQUENCE {
        kmSysSrvJamCounterIndex INTEGER,
        kmSysSrvJamType         OCTET STRING,
        kmSysSrvJamCount        Counter32
        }

kmSysSrvJamCounterIndex  OBJECT-TYPE
    SYNTAX    INTEGER
    ACCESS    read-only
    STATUS    optional --Conditionally Mandatory
    DESCRIPTION
        "
         Index for jam occurred point.
        "
    ::= { kmSysSrvJamCounterEntry 1 }

kmSysSrvJamType   OBJECT-TYPE
    SYNTAX    OCTET STRING(SIZE(0..31))
    ACCESS    read-only
    STATUS    optional --Conditionally Mandatory
    DESCRIPTION
        "
         This object shows jam occurred point.
        "
    ::= { kmSysSrvJamCounterEntry 2 }

kmSysSrvJamCount  OBJECT-TYPE
    SYNTAX    Counter32
    ACCESS    read-only
    STATUS    optional --Conditionally Mandatory
    DESCRIPTION
        "
         The counter of jam. 
        "
    ::= { kmSysSrvJamCounterEntry 3 }


kmSysSrvTroubleCounterTable OBJECT-TYPE
    SYNTAX    SEQUENCE OF KmSysSrvTroubleCounterEntry
    ACCESS    not-accessible
    STATUS    optional --Conditionally Mandatory
    DESCRIPTION
        "
         The table for showing the counter of trouble 
         (fatal error).
         It is not necessary to implement in the system without
         the way of counts reading function (ftp etc.)
        "
    ::= { kmSysServiceCounter 3 }

kmSysSrvTroubleCounterEntry OBJECT-TYPE
    SYNTAX    KmSysSrvTroubleCounterEntry
    ACCESS    not-accessible
    STATUS    optional --Conditionally Mandatory
    DESCRIPTION
        "
         The information of trouble (fatal error) counter.
        "
    INDEX  { kmSysSrvTroubleCounterIndex }
    ::= { kmSysSrvTroubleCounterTable 1 }

    KmSysSrvTroubleCounterEntry ::= SEQUENCE {
        kmSysSrvTroubleCounterIndex  INTEGER,
        kmSysSrvTroubleType          OCTET STRING,
        kmSysSrvTroubleCount         Counter32
        }

kmSysSrvTroubleCounterIndex  OBJECT-TYPE
    SYNTAX    INTEGER
    ACCESS    read-only
    STATUS    optional --Conditionally Mandatory
    DESCRIPTION
        "
         Index for trouble occurred point.
        "
    ::= { kmSysSrvTroubleCounterEntry 1 }

kmSysSrvTroubleType    OBJECT-TYPE
    SYNTAX    OCTET STRING(SIZE(0..31))
    ACCESS    read-only
    STATUS    optional --Conditionally Mandatory
    DESCRIPTION
        "
         This object shows trouble occurred point.
        "
    ::= { kmSysSrvTroubleCounterEntry 2 }

kmSysSrvTroubleCount  OBJECT-TYPE
    SYNTAX    Counter32
    ACCESS    read-only
    STATUS    optional --Conditionally Mandatory
    DESCRIPTION
        "
         The counter of trouble numbers. 
        "
    ::= { kmSysSrvTroubleCounterEntry 3 }


kmSysSrvUnitLifeCounterTable OBJECT-TYPE
    SYNTAX    SEQUENCE OF KmSysSrvUnitLifeCounterEntry
    ACCESS    not-accessible
    STATUS    optional --Conditionally Mandatory
    DESCRIPTION
        "
         The table for showing the counter of Unit life.
         It is not necessary to implement in the system without
         the way of counts reading function (ftp etc.)
        "
    ::= { kmSysServiceCounter 4 }

kmSysSrvUnitLifeCounterEntry OBJECT-TYPE
    SYNTAX    KmSysSrvUnitLifeCounterEntry
    ACCESS    not-accessible
    STATUS    optional --Conditionally Mandatory
    DESCRIPTION
        "
         The information of unit life counter.
        "
    INDEX  { kmSysSrvUnitLifeCounterIndex }
    ::= { kmSysSrvUnitLifeCounterTable 1 }

    KmSysSrvUnitLifeCounterEntry ::= SEQUENCE {
        kmSysSrvUnitLifeCounterIndex  INTEGER,
        kmSysSrvUnitLifeType          OCTET STRING,
        kmSysSrvUnitLifeCount         Counter32
        }

kmSysSrvUnitLifeCounterIndex   OBJECT-TYPE
    SYNTAX    INTEGER
    ACCESS    read-only
    STATUS    optional --Conditionally Mandatory
    DESCRIPTION
        "
         Index for consumable unit that is counted.
        "
    ::= { kmSysSrvUnitLifeCounterEntry 1 }

kmSysSrvUnitLifeType    OBJECT-TYPE
    SYNTAX    OCTET STRING(SIZE(0..31))
    ACCESS    read-only
    STATUS    optional --Conditionally Mandatory
    DESCRIPTION
        "
         This object shows consumable name.
        "
    ::= { kmSysSrvUnitLifeCounterEntry 2 }

kmSysSrvUnitLifeCount  OBJECT-TYPE
    SYNTAX    Counter32
    ACCESS    read-only
    STATUS    optional --Conditionally Mandatory
    DESCRIPTION
        "
         The counter of consumable unit. 
         Unit is dependent for consumable unit.
        "
    ::= { kmSysSrvUnitLifeCounterEntry 3 }


-- kmSysSrvOsJobCounterTable

kmSysSrvOsJobCounterTable OBJECT-TYPE
    SYNTAX    SEQUENCE OF KmSysSrvOsJobCounterEntry
    ACCESS    not-accessible
    STATUS    optional --Conditionally Mandatory
    DESCRIPTION
        "
         The table for showing the counter of job by OS.
         It is not necessary to implement in the system without
         the way of counts reading function (ftp etc.)

         This table is only for printer device with CSIC.
        "
    ::= { kmSysServiceCounter 11 }

kmSysSrvOsJobCounterEntry OBJECT-TYPE
    SYNTAX    KmSysSrvOsJobCounterEntry
    ACCESS    not-accessible
    STATUS    optional --Conditionally Mandatory
    DESCRIPTION
        "
         The information of Job counter by OS.
        "
    INDEX  { kmSysSrvOsJobCounterIndex }
    ::= { kmSysSrvOsJobCounterTable 1 }

    KmSysSrvOsJobCounterEntry ::= SEQUENCE {
        kmSysSrvOsJobCounterIndex  INTEGER,
        kmSysSrvOsType             INTEGER,
        kmSysSrvOsJobCount         Counter32
        }

kmSysSrvOsJobCounterIndex    OBJECT-TYPE
    SYNTAX    INTEGER
    ACCESS    read-only
    STATUS    optional --Conditionally Mandatory
    DESCRIPTION
        "
         Index for OS that is counted.
        "
    ::= { kmSysSrvOsJobCounterEntry 1 }

kmSysSrvOsType    OBJECT-TYPE
    SYNTAX    INTEGER {
                other (0),
                win95 (11),
                win98 (12),
                winMe (13),
                winNT (21),
                win2K (22),
                winXP (23),
                winServer2003 (24),
                winLonghorn (25),
                win64Bits (26),
                macClassic (31),
                macX (32),
                linux (41),
                unix (42)
              }
    ACCESS    read-only
    STATUS    optional --Conditionally Mandatory
    DESCRIPTION
        "
         This object shows OS type
        "
    ::= { kmSysSrvOsJobCounterEntry 2 }

kmSysSrvOsJobCount  OBJECT-TYPE
    SYNTAX    Counter32
    ACCESS    read-only
    STATUS    optional --Conditionally Mandatory
    DESCRIPTION
        "
         The counter of job by OS. 
         Unit is jobs.
        "
    ::= { kmSysSrvOsJobCounterEntry 3 }


-- kmSysSrvResolutionCounterTable

kmSysSrvResolutionCounterTable OBJECT-TYPE
    SYNTAX    SEQUENCE OF KmSysSrvResolutionCounterEntry
    ACCESS    not-accessible
    STATUS    optional --Conditionally Mandatory
    DESCRIPTION
        "
         The table for showing the counter of job by resolution.
         It is not necessary to implement in the system without
         the way of counts reading function (ftp etc.)

         This table is only for printer device with CSIC.
        "
    ::= { kmSysServiceCounter 12 }

kmSysSrvResolutionCounterEntry OBJECT-TYPE
    SYNTAX    KmSysSrvResolutionCounterEntry
    ACCESS    not-accessible
    STATUS    optional --Conditionally Mandatory
    DESCRIPTION
        "
         The information of Job counter by OS.
        "
    INDEX  { kmSysSrvResolutionCounterIndex }
    ::= { kmSysSrvResolutionCounterTable 1 }

    KmSysSrvResolutionCounterEntry ::= SEQUENCE {
        kmSysSrvResolutionCounterIndex   INTEGER,
        kmSysSrvResolutionType           INTEGER,
        kmSysSrvResolutionCount          Counter32
        }

kmSysSrvResolutionCounterIndex    OBJECT-TYPE
    SYNTAX    INTEGER
    ACCESS    read-only
    STATUS    optional --Conditionally Mandatory
    DESCRIPTION
        "
         Index for resolution that is counted.
        "
    ::= { kmSysSrvResolutionCounterEntry 1 }

kmSysSrvResolutionType     OBJECT-TYPE
    SYNTAX    INTEGER {
                other (0),
                rez600x600 (1),
                rez600x600-4bit (2),
                rez1200x600 (3),
                rez1200x1200 (4),
                rez2400x1200 (5),
                rez2400x2400 (6)
                }
    ACCESS    read-only
    STATUS    optional --Conditionally Mandatory
    DESCRIPTION
        "
         This object shows resolution type
        "
    ::= { kmSysSrvResolutionCounterEntry 2 }

kmSysSrvResolutionCount   OBJECT-TYPE
    SYNTAX    Counter32
    ACCESS    read-only
    STATUS    optional --Conditionally Mandatory
    DESCRIPTION
        "
         The counter of job by resolution. 
         Unit is jobs.
        "
    ::= { kmSysSrvResolutionCounterEntry 3 }


-- kmSysMachineInfo Group

kmSysMachineCustomerInfo   OBJECT IDENTIFIER ::= { kmSysMachineInfo 1 }

kmSysMachineCusomerID   OBJECT-TYPE
    SYNTAX    OCTET STRING(SIZE(0..255))
    ACCESS    read-write
    STATUS    optional --Conditionally Mandatory
    DESCRIPTION
        "
         The information of customer management.
         Default value should be null.
        "
    ::= { kmSysMachineCustomerInfo 1 }

kmSysMachineProductInfo  OBJECT IDENTIFIER ::= { kmSysMachineInfo 2 }

kmSysMachineProductID   OBJECT-TYPE
    SYNTAX    OCTET STRING(SIZE(0..255))
    ACCESS    read-write
    STATUS    optional --Conditionally Mandatory
    DESCRIPTION
        "
         The information of machine identification.
         Default value should be null.
        "
    ::= { kmSysMachineProductInfo 1 }


-- kmSysConsumable Group

kmSysTonerCartridgeInfo   OBJECT IDENTIFIER ::= { kmSysConsumable 1 }

kmSysTcInfoTable  OBJECT-TYPE
    SYNTAX    SEQUENCE OF KmSysTcInfoEntry
    ACCESS    not-accessible
    STATUS    optional --Conditionally Mandatory
    DESCRIPTION
        "
         The table for showing that information of 
         toner cartridge.
         This table should be implemented on device has 
         toner cartridge.
         Specially, printer single function device must implement
         this table.
         If this table is implemented, kmSysTonerLifeCounterTable
         must be implemented too.
        "
    ::= { kmSysTonerCartridgeInfo  1 }

kmSysTcInfoEntry OBJECT-TYPE
    SYNTAX    KmSysTcInfoEntry
    ACCESS    not-accessible
    STATUS    optional --Conditionally Mandatory
    DESCRIPTION
        "
         An entry for toner cartridge information.
        "
    INDEX  { kmSysTcInfoIndex }
    ::= { kmSysTcInfoTable 1 }

  KmSysTcInfoEntry ::= SEQUENCE {
        kmSysTcInfoIndex                INTEGER,
        kmSysTcColor                    INTEGER,
        kmSysTcID                       OCTET STRING,
        kmSysTcUniqueNumber             OCTET STRING,
        kmSysTcLatestTotalCountOfNew    Integer32,
        kmSysTcLatestTotalCountOfEmpty  Integer32,
        kmSysTcLatestTotalCountOfDead   Integer32,
        kmSysTcLatestDotCountOfNew      Integer32,
        kmSysTcLatestDotCountOfEmpty    Integer32,
        kmSysTcLatestDotCountOfDead     Integer32,
        kmSysTcLatestDateOfNew          DateAndTime,
        kmSysTcLatestDateOfEmpty        DateAndTime,
        kmSysTcLatestDateOfDead         DateAndTime,
        kmSysTcLatestFlag               INTEGER,
        kmSysTcNewDetectNumbers         Counter32,
        kmSysTcNewGenuineDetectNumbers  Counter32
        }

kmSysTcInfoIndex  OBJECT-TYPE
    SYNTAX     INTEGER
    ACCESS     read-only
    STATUS     optional --Conditionally Mandatory
    DESCRIPTION
        "
         Index for identification of toner cartridge.
         In case of monochrome device,
         Index of the following should be used,.

            Index    Color
           --------------------------
             1       Black
         
         In case of color device,
         Index of the following should be used,.
            Index    Color
           --------------------------
             1       Cyan
             2       Magenta
             3       Yellow
             4       Black
        "
    ::= { kmSysTcInfoEntry 1 }

kmSysTcColor  OBJECT-TYPE
    SYNTAX    INTEGER {
                cyan (1),
                magenta (2),
                yellow (3),
                black (4)
                }
    ACCESS     read-only
    STATUS     optional --Conditionally Mandatory
    DESCRIPTION
        "
         This object shows the color of toner cartridge. 
        "
    ::= { kmSysTcInfoEntry 2 }

kmSysTcID  OBJECT-TYPE
    SYNTAX     OCTET STRING(SIZE(0..63))
    ACCESS     read-only
    STATUS     optional --Conditionally Mandatory
    DESCRIPTION
        "
         This object shows the ID of toner cartridge. 
        "
    ::= { kmSysTcInfoEntry 3 }

kmSysTcUniqueNumber  OBJECT-TYPE
    SYNTAX     OCTET STRING(SIZE(0..8))
    ACCESS     read-only
    STATUS     optional --Conditionally Mandatory
    DESCRIPTION
        "
         This object shows the unique number of CSIC. 
         Format is 64bits (Prefix+SerialNo.+FamilyCode).
        "
    ::= { kmSysTcInfoEntry 4 }

kmSysTcLatestTotalCountOfNew  OBJECT-TYPE
    SYNTAX     Integer32
    ACCESS     read-only
    STATUS     optional --Conditionally Mandatory
    DESCRIPTION
        "
         The latest total counts  value of new 
         toner cartridge detection time.
         Default value is 0.
         This value should be updated every new T/C
         detection.
        "
    ::= { kmSysTcInfoEntry 5 }

kmSysTcLatestTotalCountOfEmpty  OBJECT-TYPE
    SYNTAX     Integer32
    ACCESS     read-only
    STATUS     optional --Conditionally Mandatory
    DESCRIPTION
        "
         The latest total count  value of toner 
         empty detection time.
         Default value is 0.
         This value should be updated every empty
         detection.
        "
    ::= { kmSysTcInfoEntry 6 }

kmSysTcLatestTotalCountOfDead  OBJECT-TYPE
    SYNTAX     Integer32
    ACCESS     read-only
    STATUS     optional --Conditionally Mandatory
    DESCRIPTION
        "
         The latest total count  value of toner 
         dead detection time.
         Default value is 0.
         This value should be updated every dead
         detection.
        "
    ::= { kmSysTcInfoEntry 7 }

kmSysTcLatestDotCountOfNew  OBJECT-TYPE
    SYNTAX     Integer32
    ACCESS     read-only
    STATUS     optional --Conditionally Mandatory
    DESCRIPTION
        "
         The latest dot count (kmSysTonerTypeCount)
         value of new toner cartridge detection time.
         Default value is 0.
         This value should be updated every new T/C
         detection.
        "
    ::= { kmSysTcInfoEntry 8 }

kmSysTcLatestDotCountOfEmpty  OBJECT-TYPE
    SYNTAX     Integer32
    ACCESS     read-only
    STATUS     optional --Conditionally Mandatory
    DESCRIPTION
        "
         The latest dot count (kmSysTonerTypeCount)
         value of toner empty detection time.
         Default value is 0.
         This value should be updated every empty
         detection.
        "
    ::= { kmSysTcInfoEntry 9 }

kmSysTcLatestDotCountOfDead  OBJECT-TYPE
    SYNTAX     Integer32
    ACCESS     read-only
    STATUS     optional --Conditionally Mandatory
    DESCRIPTION
        "
         The latest dot count (kmSysTonerTypeCount)
         value of toner dead detection time.
         Default value is 0.
         This value should be updated every dead
         detection.
        "
    ::= { kmSysTcInfoEntry 10 }

kmSysTcLatestDateOfNew  OBJECT-TYPE
    SYNTAX     DateAndTime
    ACCESS     read-only
    STATUS     optional --Conditionally Mandatory
    DESCRIPTION
        "
         The latest Date of new toner cartridge detection time.
         If device has no clock, this value should be the date 
         information that is included print job to sent first time
         after new T/C detection.

         If device cannot detect date information,
         this value should be null.
        "
    ::= { kmSysTcInfoEntry 11 }

kmSysTcLatestDateOfEmpty  OBJECT-TYPE
    SYNTAX     DateAndTime
    ACCESS     read-only
    STATUS     optional --Conditionally Mandatory
    DESCRIPTION
        "
         The latest Date of toner empty detection time.
         If device has no clock, this value should be the date 
         information that is included print job to sent first time
         after toner empty detection.

         If device cannot detect date information,
         this value should be null.
        "
    ::= { kmSysTcInfoEntry 12 }

kmSysTcLatestDateOfDead  OBJECT-TYPE
    SYNTAX     DateAndTime
    ACCESS     read-only
    STATUS     optional --Conditionally Mandatory
    DESCRIPTION
        "
         The latest Date of toner dead detection time.
         If device has no clock, this value should be the date 
         information that is included print job to sent first time
         after toner dead detection.

         If device cannot detect date information,
         this value should be null.
        "
    ::= { kmSysTcInfoEntry 13 }

kmSysTcLatestFlag  OBJECT-TYPE
    SYNTAX    INTEGER {
                other (0),
                genuine (1),
                unknown (2)
                }
    ACCESS     read-only
    STATUS     optional --Conditionally Mandatory
    DESCRIPTION
        "
         The genuine flag of toner cartridge.
        "
    ::= { kmSysTcInfoEntry 14 }

kmSysTcNewDetectNumbers  OBJECT-TYPE
    SYNTAX     Counter32
    ACCESS     read-only
    STATUS     optional --Conditionally Mandatory
    DESCRIPTION
        "
         The counter of new toner detection times.
        "
    ::= { kmSysTcInfoEntry 15 }

kmSysTcNewGenuineDetectNumbers  OBJECT-TYPE
    SYNTAX     Counter32
    ACCESS     read-only
    STATUS     optional --Conditionally Mandatory
    DESCRIPTION
        "
         The counter of new genuine toner detection times.
         If device cannot detect genuine TC, this value 
         should be always 0.
        "
    ::= { kmSysTcInfoEntry 16 }



-- Private Printer MIB 


kmPrinterMib    OBJECT IDENTIFIER ::= { kmPrinter 6 }

kmPrtMibVersion  OBJECT-TYPE
    SYNTAX     DisplayString (SIZE (0..7))
    ACCESS     read-only
    STATUS     mandatory
    DESCRIPTION
        " 
         The version information of KONICA MINOLTA Standard MIB specification.

         This indicates the version of the KONICA MINOLTA Private Printer MIB 
         which is implemented. 

         It is written as AA.BC.
         AA is indicating major revision, and B and C is 
         minor revision. Decimal point is ASCII-coded period.

         This definition file is corresponded to '1.50'.
        "
    ::= { kmPrinterMib 1 }


   kmPrtCtrlInfo      OBJECT IDENTIFIER ::= { kmPrinterMib 2 }

   kmPrtLocalIfInfo    OBJECT IDENTIFIER ::= { kmPrinterMib 3 }

   kmPrtCommand       OBJECT IDENTIFIER ::= { kmPrinterMib 4 }
   kmPrtConfig        OBJECT IDENTIFIER ::= { kmPrinterMib 5 }
   kmPrtFont          OBJECT IDENTIFIER ::= { kmPrinterMib 6 }
   kmPrtPaper         OBJECT IDENTIFIER ::= { kmPrinterMib 7 }

   kmPrtOverLay       OBJECT IDENTIFIER ::= { kmPrinterMib 12 }
   kmPrtColorMatching OBJECT IDENTIFIER ::= { kmPrinterMib 13 }


-- kmPrtCtrlInfo Group

kmPrtCtrlName  OBJECT-TYPE
    SYNTAX     OCTET STRING (SIZE (0..31))
    ACCESS     read-only
    STATUS     mandatory
    DESCRIPTION
        " 
         This object shows the name of printer controller.
         If device has no independent printer controller or no 
         product name of it, this value should be  same as sysDescr.
         In case of printer, this value should be same as sysDescr.
        "  
    ::= { kmPrtCtrlInfo 1 }


-- kmPrtLocalIfInfo Group

-- This group shows information of local interface
-- (Parallel and USB).

kmPrtLocalParallel  OBJECT IDENTIFIER ::= { kmPrtLocalIfInfo 1 }

kmPrtLocalParallelTimeout  OBJECT-TYPE
    SYNTAX    INTEGER
    ACCESS    read-write
    STATUS    optional
    DESCRIPTION
        "
         Timeout setting of parallel interface. 
         Unit is seconds.
         The setting rage and default value depend on 
         device specification.

         However, unified specification of KONICA MINOLTA
         defines this setting as range is 10 to 1000,
         default value is 60.

         In each devices, Setting range and default value 
         should be specified in implementation specifications.
         If device has no timeout setting of parallel interface,
         this object should be -1 as RO.
        "
    ::= { kmPrtLocalParallel 1 }


kmPrtLocalParallelMode  OBJECT-TYPE
    SYNTAX   INTEGER{
                notSupported (0),
                ecp (1),
                nibble (2),
                compatible (3)
                }
    ACCESS   read-write
    STATUS   optional
    DESCRIPTION
        "
        Operation mode of parallel interface setting. 
        "
      ::= { kmPrtLocalParallel 2 }


kmPrtLocalUsb  OBJECT IDENTIFIER ::= { kmPrtLocalIfInfo 2 }

kmPrtLocalUsbTimeout  OBJECT-TYPE
    SYNTAX    INTEGER
    ACCESS    read-write
    STATUS    optional
    DESCRIPTION
        "
         Timeout setting of USB interface. Unit is seconds.
         The setting rage and default value depend 
         on device specification. However, 
         unified specification of KONICA MINOLTA defines
         this setting as range is 10 to 1000, default value is 60.

         In each devices, Setting range and default value
         should be specified in implementation specifications.
         If device has no timeout setting of USB interface, 
         this object should be -1 as RO.
        "
    ::= { kmPrtLocalUsb 1 }




-- kmPrtCommand Group

-- The command information for performing various commands
-- to a printer, control of printing job, and printing of
-- ConfigPage, etc. are included.

kmPrtCommandTable  OBJECT-TYPE
    SYNTAX     SEQUENCE OF KmPrtCommandEntry
    ACCESS     not-accessible
    STATUS     mandatory
    DESCRIPTION
        "
        The table for showing the command information of 
        printer. This table must be implemented 
        even if no function in this table are supported 
        by a model. 
        "
    ::= { kmPrtCommand 1 }

kmPrtCommandEntry OBJECT-TYPE
    SYNTAX      KmPrtCommandEntry
    ACCESS      not-accessible
    STATUS      mandatory
    DESCRIPTION
        "
        An entry exists in this table for each
        device entry in the hostmib device table whose type
        is 'printer'.
        "
      INDEX  { hrDeviceIndex }
      ::= {kmPrtCommandTable 1 }

   KmPrtCommandEntry ::= SEQUENCE {
       kmPrtCommandOnline        INTEGER,
       kmPrtCommandJobCancel     INTEGER,
       kmPrtCommandJobProceed    INTEGER
       }

kmPrtCommandOnline  OBJECT-TYPE
    SYNTAX   INTEGER{
                notSupported (0),
                onLine (1),
                offLine (2)
                }
    ACCESS   read-write
    STATUS   mandatory
    DESCRIPTION
        "
        Indicate printer online or offline.
        If printer has no online button,
        this value should be notSupported (0) as read-only.
        "
      ::= { kmPrtCommandEntry 1 }

kmPrtCommandJobCancel  OBJECT-TYPE
     SYNTAX   INTEGER{
                notSupported (0),
                notCancel (1),
                jobCancel (2)
                }
     ACCESS   read-write
     STATUS   mandatory
     DESCRIPTION
         "
         Command of cancel job.
         If printer has not job cancel function,
         this value should be notSupported (0) as read-only.
         In normal condition, this value should 
         be notCancel (1). If canceling job, 
         set this object jobCancel (2).
         "
      ::= { kmPrtCommandEntry 2 }

kmPrtCommandJobProceed  OBJECT-TYPE
    SYNTAX   INTEGER{
                notSupported (0),
                notProceed (1),
                jobProceed (2)
                }
    ACCESS   read-write
    STATUS   mandatory
    DESCRIPTION
        "
        Command of proceeds.
        If printer has not proceed function,
        this value should be notSupported (0) as read-only.
        In normal condition, this value should 
        be notProceed (1). If proceeding job, 
        set this object proceed (2).
        "
      ::= { kmPrtCommandEntry 3 }


kmPrtPrintPageTable  OBJECT-TYPE
    SYNTAX     SEQUENCE OF KmPrtPrintPageEntry
    ACCESS     not-accessible
    STATUS     optional --Conditionally Mandatory
    DESCRIPTION
        "
        A table of printable configuration print.
        If a printer does not support print the test pages 
        from network access, this table needs not to be implemented.
        "
      ::= { kmPrtCommand 2 }

kmPrtPrintPageEntry OBJECT-TYPE
    SYNTAX      KmPrtPrintPageEntry
    ACCESS      not-accessible
    STATUS      optional --Conditionally Mandatory
    DESCRIPTION
          "Information about printer's configuration prints.
           Entries may exist in the table for each device
           index whose device type is 'printer'.
          "
       INDEX  { hrDeviceIndex, kmPrtPrintPageIndex }
        ::= {kmPrtPrintPageTable 1 }

  KmPrtPrintPageEntry ::= SEQUENCE {
        kmPrtPrintPageIndex     INTEGER,
        kmPrtPrintPageName      OCTET STRING,
        kmPrtPrintCommand       INTEGER
        }

kmPrtPrintPageIndex  OBJECT-TYPE
    SYNTAX   INTEGER (0..65535) 
    ACCESS   read-only
    STATUS   optional --Conditionally Mandatory
    DESCRIPTION
        "
        Index for uniquely distinguishing the page held within a printer.
        Although the value of index depends on an implementation, 
        "
      ::= { kmPrtPrintPageEntry 1 }

kmPrtPrintPageName  OBJECT-TYPE
    SYNTAX   OCTET STRING (SIZE(0..31))
    ACCESS   read-only
    STATUS   optional --Conditionally Mandatory
    DESCRIPTION
        "
        The name of the page, which can be printed.
        The value that should be implemented depends
        on an implementation of a model and it should
        be common with a manual etc.
        "
      ::= { kmPrtPrintPageEntry 2 }

kmPrtPrintCommand  OBJECT-TYPE
    SYNTAX   INTEGER{
                supported (1),
                print (2)
                }
        ACCESS   read-write
        STATUS   optional --Conditionally Mandatory
        DESCRIPTION
        "
        Command of print page.
        In normal condition , this value should 
        be supported (1).
        If print page, set this object print (2).
        "
       ::= { kmPrtPrintPageEntry 3 }


-- kmPrtConfig Group

-- This group shows the various setup information of a printer.

kmPrtSysConfigTable  OBJECT-TYPE
    SYNTAX     SEQUENCE OF KmPrtSysConfigEntry
    ACCESS     not-accessible
    STATUS     mandatory
    DESCRIPTION
        "
         A table of configurations for printer.
         This table must be implemented even if 
         no functions in this table are supported.
        "
    ::= { kmPrtConfig 1 }

kmPrtSysConfigEntry OBJECT-TYPE
    SYNTAX      KmPrtSysConfigEntry
    ACCESS      not-accessible
    STATUS      mandatory
    DESCRIPTION
        "
        An entry exists in this table for each
        device entry in the hostmib device table whose type
        is 'printer'.
        "
      INDEX  { hrDeviceIndex }
     ::= {kmPrtSysConfigTable 1 }

  KmPrtSysConfigEntry ::= SEQUENCE {
      kmPrtJobLanguage    INTEGER,
      kmPrtPowerSave      INTEGER,
      kmPrtAutoContinue   INTEGER,
      kmPrtPaperTimeOut   INTEGER,
      kmPrtPsErrorPrint   INTEGER,
      kmPrtSpoolMode      INTEGER,
      kmPrtBanner         INTEGER,
      kmPrtCopyJobTimeOut INTEGER,
      kmPrtConvertPaperSize INTEGER,
      kmPrtPaperPriorityChoice INTEGER
      }

kmPrtJobLanguage  OBJECT-TYPE
    SYNTAX   INTEGER {
                auto (0),
                pcl (1),
                ps (2),
                gdi (3),
                linePrinter(4),
                pdf (5),
                tiff (6),
                other (7)
                }
    ACCESS   read-write
    STATUS   mandatory
    DESCRIPTION
        "
        Configuration printer job language.
        Only in the case that a printer has a function of
        setting(changing) this default printer language, 
        this object is implemented as RW. 
        In the other case, this object should be implemented as RO.

        In case of PCL/PS printer, default value is Auto(0).
        If necessary, PCL(1)/PS(2) is changeable.
        In case of printer has only one interpreter (PCL or PS),
        this object should be pcl(1) or ps (2) as RO.
        In case of GDI printer, this value is GDI(3) (RO).
        "
      ::= { kmPrtSysConfigEntry 1 }

kmPrtPowerSave  OBJECT-TYPE
    SYNTAX   INTEGER
    ACCESS   read-write
    STATUS   mandatory
    DESCRIPTION
        "
        Timer value setting before the power save mode is 
        asserted. Unit is minutes.
        If '0' is selected, the controller doesn't enter
        Power Save mode.
        If this value is -1, printer doesn't support power save mode.
        If out of spec value is set, Error is returned.

        Since it is originally defined as a setup item of a printer 
        simple substance, when adapting to MFP, it is necessary to 
        specify that it is the setup of either printer controller or 
        a MFP itself.
        Since it is the item of printer relation, in being adapted to MFP, 
        PowerSave function of a printer controller should be set up and 
        control of the copier is not performed.
        Use it for control of a printer simple substance and the printer 
        in MFP of a printer base.
        "
     ::= { kmPrtSysConfigEntry 2 }

kmPrtAutoContinue  OBJECT-TYPE
    SYNTAX   INTEGER{
               notSupported (0),
               off (1),
               ac0Sec (2),
               ac10Sec (3),
               ac20Sec (4),
               ac30Sec (5),
               ac60Sec (6),
               ac90Sec (7),
               ac120Sec (8)
               }
    ACCESS   read-write
    STATUS   mandatory
    DESCRIPTION
        "
        The setting whether printing will automatically
        recover or not when an Error or Caution occurred.
        In MFP, since there seems many cases that the function 
        of AutoContinue becomes the function of not printer 
        controller but the copier, in that case, uses notSupported(0).
        It should be used for control of a printer simple substance and
        the printer in MFP of a printer base.
        If a device support only the value of 1(off) and 2(ac0Sec),
        this implementation is allowed.
        "
      ::= { kmPrtSysConfigEntry 3 }

kmPrtPaperTimeOut  OBJECT-TYPE
    SYNTAX   INTEGER{
               notSupported(0),
               off (1),
               proceedJob (2),
               cancelJob (3)
               }
    ACCESS   read-write
    STATUS   mandatory
    DESCRIPTION
         "
         Setting which decides whether automatic recover
         should be proceed or not when an error related to paper 
         occurred.

         In MFP, since there seems many cases that the function 
         of PaperTimeout becomes the function of not printer
         controller but the copier (or sometimes this function
         does not exist), in that case, use notSupported(0).
         It should be used for control of a printer simple
         substance and the printer in MFP of a printer base.
         "
       ::= { kmPrtSysConfigEntry 4 }

kmPrtPsErrorPrint  OBJECT-TYPE
    SYNTAX   INTEGER{
                notSupported (0),
                off (1),
                on (2)
                }
    ACCESS   read-write
    STATUS   mandatory
    DESCRIPTION
        "
        The setting whether the printer prints PostScript Error
        Page when PostScript Error occurred during job processing.
        About PS error, since it is the function of a printer
        controller, all the devices with PS should be implemented
        If a device has no PostScript interpreter, this value
        should be always notSupported(0) as RO.
        "
      ::= { kmPrtSysConfigEntry 5 }

kmPrtSpoolMode  OBJECT-TYPE
    SYNTAX   INTEGER{
                notSupported (0),
                yes (3),
                no (4),
                auto (5)
                }
    ACCESS   read-write
    STATUS   mandatory
    DESCRIPTION
        "
         The setting of printer spool.

        If a device has no spool setting function, this value
        should be always notSupported(0) as RO.
        "
      ::= { kmPrtSysConfigEntry 6 }

kmPrtBanner  OBJECT-TYPE
    SYNTAX   INTEGER{
                notSupported (0),
                yes (3),
                no (4)
                }
    ACCESS   read-write
    STATUS   mandatory
    DESCRIPTION
        "
        The setting of printer banner page.
        This banner is not LPR banner and Netware banner
        but printer controller's original.

        If a device has no banner page, this value
        should be always notSupported(0) as RO.
        "
      ::= { kmPrtSysConfigEntry 7 }


kmPrtCopyJobTimeOut  OBJECT-TYPE
    SYNTAX   INTEGER
    ACCESS   read-write
    STATUS   mandatory
    DESCRIPTION
        "
        The setting of copy job time out.
        This setting range is 0 to 300. Unit is seconds.

        If a device cannot support this function,
        This value must be -1 as RO.
        "
      ::= { kmPrtSysConfigEntry 8 }

kmPrtConvertPaperSize  OBJECT-TYPE
    SYNTAX   INTEGER{
                notSupported (0),
                off (1),  -- no size convert
                on (2),  -- size convert enable
                inchToMetric (3), -- only inch to metric
                metricToInch (4)  -- only metric to inch
                }
    ACCESS   read-write
    STATUS   optional
    DESCRIPTION
        "
        The setting of paper size converts.

        This setting convert paper size from 
        metric(A3/A4) to inch (Ledger/Letter),
        inch (Ledger/Letter) to metric(A3/A4), 
        when original size are different from required
        paper source tray size. 

        If a device has no paper size convert function,
        this value should be always notSupported(0) as RO.
        "
      ::= { kmPrtSysConfigEntry 9 }



kmPrtPaperPriorityChoice  OBJECT-TYPE
    SYNTAX   INTEGER{
                notSupported (0),
                on (1),  -- tray change
                off (2)  -- show alert
                }
    ACCESS   read-write
    STATUS   optional
    DESCRIPTION
        "
        The setting of paper priority choice.

        This setting is whether change tray or show alert, 
        when selected paper tray has not required paper
        size.

        If a device has not this function,
        this value should be always notSupported(0) as RO.
        "
      ::= { kmPrtSysConfigEntry 10 }



kmPrtPrintConfigTable  OBJECT-TYPE
    SYNTAX     SEQUENCE OF KmPrtPrintConfigEntry
    ACCESS     not-accessible
    STATUS     mandatory
    DESCRIPTION
        "
        A table of configurations for printer.
        This table must be implemented even if 
        no functions in this table are supported.
        "
  ::= { kmPrtConfig 2 }

kmPrtPrintConfigEntry OBJECT-TYPE
    SYNTAX      KmPrtPrintConfigEntry
    ACCESS      not-accessible
    STATUS      mandatory
    DESCRIPTION
        "
        An entry exists in this table for each
        device entry in the hostmib device table whose type
        is 'printer'
        "
        INDEX  { hrDeviceIndex }
      ::= { kmPrtPrintConfigTable 1 }

    KmPrtPrintConfigEntry ::= SEQUENCE {
         kmPrtCopies       INTEGER,
         kmPrtPaperSize    INTEGER,
         kmPrtPaperSource  INTEGER,
         kmPrtFineArt      INTEGER,
         kmPrtTonerSave    INTEGER,
         kmPrtPaperType    INTEGER,
         kmPrtPaperExit    INTEGER,
         kmPrtDuplex       INTEGER,
         kmPrtBinding      INTEGER,
         kmPrtStaple       INTEGER,
         kmPrtPunch        INTEGER
         }

kmPrtCopies  OBJECT-TYPE
    SYNTAX   INTEGER
    ACCESS   read-write
    STATUS   mandatory
    DESCRIPTION
        "
        The number of printing copies.
        If set value is over limit, printer should return error.

        About device which has no default copies setting, 
        This value should be -1.
        "
      ::= { kmPrtPrintConfigEntry 1 }

kmPrtPaperSize   OBJECT-TYPE
    SYNTAX   INTEGER
    ACCESS   read-write
    STATUS   mandatory
    DESCRIPTION
        "
        Paper size of printing.
        The value of the kmPrtPaperSizeIndex corresponding to
        the current paper size.

        About device which has no default paper size setting, 
        This value should be -1.
        "
      ::= { kmPrtPrintConfigEntry 2 }

kmPrtPaperSource  OBJECT-TYPE
    SYNTAX   INTEGER
    ACCESS   read-write
    STATUS   mandatory
    DESCRIPTION
        "
        Feeders for printing.
        The value of prtInputIndex corresponding to the default
        input sub-unit: that is, this object selects the default
        source of input media.
        If value is 0, this means 'Auto'.

        About device which has no default paper source setting, 
        This value should be -1.
        "
      ::= { kmPrtPrintConfigEntry 3 }

kmPrtFineArt  OBJECT-TYPE
    SYNTAX   INTEGER{
                notSupported (0),
                on (1),            -- Use 2step setting
                offSwitch (2),     -- Use 2step setting
                dark (3),          -- Use 4step setting
                medium (4),        -- Use 4step setting
                light (5),         -- Use 4step setting
                offStep (6)        -- Use 4step setting
                }
    ACCESS   read-write
    STATUS   mandatory
    DESCRIPTION
        "
        Smoothing setting.
        If printer has no smoothing function, this value should 
        be notSupported(0) and RO.

        If printer supports only On/Off , this value should be 
        on(1) or offSwitch(2).

        If printer supports 4 steps, this value should be 
        dark(3), medium(4), light(5) and  offStep(6). 
        "
      ::= { kmPrtPrintConfigEntry 4 }

kmPrtTonerSave  OBJECT-TYPE
    SYNTAX   INTEGER{
                notSupported (0),
                on (1),
                off (2)
                }
    ACCESS   read-write
    STATUS   mandatory
    DESCRIPTION
        "
        Toner saving setting.
        If printer is not supporting toner save function,
        this value should be notSupported(0) and RO.

        If printer is supporting toner save function,
        this value should be on(1) or off(2) and RW.
        "
      ::= { kmPrtPrintConfigEntry 5 }

kmPrtPaperType  OBJECT-TYPE
    SYNTAX   INTEGER{
              other(0),
              normalPaper(1),
              recycledpaper1(17),
              recyclepdaper2(18),
              finePaper1(24),
              finePaper2(25),
              postCard1(33),
              envelope(40),
              ohp(65),
              ohp2(66),
              labelPaper(69),
              tracePaper(70),
              basePaper1(81),
              basePaper2(82),
              coatedPaper1(88),
              coatedPaper2(89),
              bookPaper(97),
              roughPaper(98),
              blankInsertSheet(99),
              userDefined1(113),
              userDefined2(114),
              userDefined3(115),
              glossy(129),
              heavyGlossy(130),
              highGloss(131),
              tabPaper(161),
              letterHead(162),
              formatedPaper(164),
              specialPaper1(177),
              specialPaper2(178),
              printedPaper1(184),
              printedPaper2(185),
              thinPaper1(209),
              thinPaper2(210),
              thinPaper3(211),
              thinPaper4(212),
              thinPaper5(213),
              thickPaper1(225),
              thickPaper2(226),
              thickPaper3(227),
              thickPaper4(228),
              thickPaper5(229),
              userCustom1(241),
              userCustom2(242),
              userCustom3(243),
              userCustom4(244),
              userCustom5(245)
              }
    ACCESS   read-write
    STATUS   mandatory
    DESCRIPTION
        "
        Default paper type setting.
        If printer is not supporting this setting item,
        this value should be notSupported(99) and RO.
        "
    ::= { kmPrtPrintConfigEntry 6 }

kmPrtPaperExit  OBJECT-TYPE
    SYNTAX   INTEGER
    ACCESS   read-write
    STATUS   optional
    DESCRIPTION
        "
        Paper exit for printing.
        The value of prtOutputIndex corresponding to the default
        output sub-unit: that is, this object selects the default
        paper exit tray.
        If value is 0, this means 'Auto'.

        About device which has no default paper exit setting, 
        This value should be -1.
        "
      ::= { kmPrtPrintConfigEntry 7 }

kmPrtDuplex  OBJECT-TYPE
    SYNTAX   INTEGER{
                notSupported (0),
                simplex (1),
                duplex (2)
                }
    ACCESS   read-write
    STATUS   optional
    DESCRIPTION
        "
        Default duplex setting.
        If printer is not supporting duplex function,
        this value should be notSupported(0) and RO.
        "
      ::= { kmPrtPrintConfigEntry 8 }

kmPrtBinding  OBJECT-TYPE
    SYNTAX   INTEGER{
                notSupported (0),
                topSideBinding (1),
                leftSideBinding (2),
                rightSideBinding (3)
                }
    ACCESS   read-write
    STATUS   optional
    DESCRIPTION
        "
        Default binding setting.
        If printer is not supporting binding function,
        this value should be notSupported(0) and RO.
        "
      ::= { kmPrtPrintConfigEntry 9 }

kmPrtStaple  OBJECT-TYPE
    SYNTAX   INTEGER{
                notSupported (0),
                off (1),
                onePoint (2), -- no position specified.
                twoPoint (3), 
                onePointLeft (4),
                onePointRight (5)
                }
    ACCESS   read-write
    STATUS   optional
    DESCRIPTION
        "
        Default staple setting.
        If printer is not supporting binding function,
        this value should be notSupported(0) and RO.
        "
      ::= { kmPrtPrintConfigEntry 10 }

kmPrtPunch  OBJECT-TYPE
    SYNTAX   INTEGER{
                notSupported (0),
                off (1),
                on (2), -- no hole number specific.
                twoHolePunch (3),
                threeHolePunch (4),
                fourHolePunch (5)
                }
    ACCESS   read-write
    STATUS   optional
    DESCRIPTION
        "
        Default punch setting.
        If printer is not supporting binding function,
        this value should be notSupported(0) and RO.
        "
      ::= { kmPrtPrintConfigEntry 11 }



kmPrtPclConfigTable  OBJECT-TYPE
    SYNTAX     SEQUENCE OF KmPrtPclConfigEntry
    ACCESS     not-accessible
    STATUS     optional
    DESCRIPTION
        "
        A table of configurations for PCL controller.
        "
  ::= { kmPrtConfig 4 }

kmPrtPclConfigEntry OBJECT-TYPE
    SYNTAX      KmPrtPclConfigEntry
    ACCESS      not-accessible
    STATUS      optional
    DESCRIPTION
        "
        An entry exists in this table for each
        device entry in the hostmib device table whose type
        is 'printer'
        "
        INDEX  { hrDeviceIndex }
      ::= { kmPrtPclConfigTable 1 }

   KmPrtPclConfigEntry ::= SEQUENCE {
         kmPrtPclTypeFace     INTEGER,
         kmPrtPclLinePerPage  INTEGER,
         kmPrtPclFontSizeUnit INTEGER,
         kmPrtPclFontSize     INTEGER,
         kmPrtPclCrLfMapping  INTEGER,
         kmPrtPclErrorPrint   INTEGER
         }

kmPrtPclTypeFace  OBJECT-TYPE
    SYNTAX   INTEGER
    ACCESS   read-write
    STATUS   optional
    DESCRIPTION
        "
        Default PCL font for printing.
        The value of the kmPrtPclFontIndex corresponding to
        the current PCL font type face.

        About device which has no default PCL font setting, 
        This value should be -1.
        "
      ::= { kmPrtPclConfigEntry 1 }


kmPrtPclLinePerPage  OBJECT-TYPE
    SYNTAX   INTEGER
    ACCESS   read-write
    STATUS   optional
    DESCRIPTION
        "
        The line number per page of PCL printing.
        Setting range depends device specification.
        (In unified specification, range is 5 to 128, 
         Default value should be 60(US)/64(other than US))
        "
      ::= { kmPrtPclConfigEntry 2 }

kmPrtPclFontSizeUnit  OBJECT-TYPE
    SYNTAX   INTEGER{
                notSupported (0),
                fixedHundredthOfPoint (1),  -- optional
                fixedHundredthOfPitch (2),  -- optional
                hundredthOfPoint (3),
                hundredthOfPitch (4)      -- Default value
                }
    ACCESS   read-write
    STATUS   optional
    DESCRIPTION
        "
        The setting of Font size unit.
        "
      ::= { kmPrtPclConfigEntry 3 }

kmPrtPclFontSize  OBJECT-TYPE
    SYNTAX   INTEGER
    ACCESS   read-write
    STATUS   optional
    DESCRIPTION
        "
        The setting of PCL font size.
        Setting range depends device specification.

        In unified specification, range is 400 to 99975
        (4.00 to 999.75 point) if kmPrtPclFontSizeUnit
        is hundredthOfPoint (3),
        44 to 9900
        (0.44 to 99.00 pitch) if kmPrtPclFontSizeUnit
        is hundredthOfPitch (4).
        "
      ::= { kmPrtPclConfigEntry 4 }

kmPrtPclCrLfMapping  OBJECT-TYPE
    SYNTAX   INTEGER{
                notSupported (0),
                noChange (1),
                addLf (2),
                addCr (3),
                addCrLf (4)
                }
    ACCESS   read-write
    STATUS   optional
    DESCRIPTION
        "
        The setting of  CR-LF mapping.
        "
      ::= { kmPrtPclConfigEntry 5 }

kmPrtPclErrorPrint  OBJECT-TYPE
    SYNTAX   INTEGER{
                notSupported (0),
                off (1),
                on (2) 
                }
    ACCESS   read-write
    STATUS   optional
    DESCRIPTION
        "
        The setting of PCL Error Print.
        "
      ::= { kmPrtPclConfigEntry 6 }



-- kmPrtFont Group

-- Includes the information about the font, which a printer holds.
-- The printer that does not have a font, such as GDI,
-- does not need to implement this group.

kmPrtPclFontTable  OBJECT-TYPE
    SYNTAX     SEQUENCE OF KmPrtPclFontEntry
    ACCESS     not-accessible
    STATUS     optional --Conditionally Mandatory
    DESCRIPTION
        "
        This table shows PCL font information of printer has.
        Since it is a function peculiar to PCL, it is not necessary 
        to implement this table in the device in which PCL is not 
        installed or PCL font management function is not installed.
        "
      ::= { kmPrtFont 1 }

kmPrtPclFontEntry OBJECT-TYPE
    SYNTAX      KmPrtPclFontEntry
    ACCESS      not-accessible
    STATUS      optional --Conditionally Mandatory
    DESCRIPTION
        "
        Information about printer's PCL fonts.
        Entries may exist in the table for each device
        index whose device type is 'printer'.
        "
        INDEX  { hrDeviceIndex, kmPrtPclFontIndex }
    ::= {kmPrtPclFontTable 1 }

    KmPrtPclFontEntry ::= SEQUENCE {
        kmPrtPclFontIndex  INTEGER,
        kmPrtPclFontName   OCTET STRING,
        kmPrtPclFontNumber INTEGER,
        kmPrtPclFontSource INTEGER
        }

kmPrtPclFontIndex  OBJECT-TYPE
    SYNTAX   INTEGER (1..65535) 
    ACCESS   read-only
    STATUS   optional --Conditionally Mandatory
    DESCRIPTION
        "
        A unique value used to identify this entry. 
        "
      ::= { kmPrtPclFontEntry 1 }

kmPrtPclFontName  OBJECT-TYPE
    SYNTAX   OCTET STRING (SIZE(0..63)) 
    ACCESS   read-only
    STATUS   optional --Conditionally Mandatory
    DESCRIPTION
        "
        The name of PCL Font. 
        "
      ::= { kmPrtPclFontEntry 2 }

kmPrtPclFontNumber  OBJECT-TYPE
    SYNTAX   INTEGER(0..65535) 
    ACCESS   read-only
    STATUS   optional --Conditionally Mandatory
    DESCRIPTION
        "
        The number of PCL Font. 
        The number for managing the font, which a printer holds inside.
        "
      ::= { kmPrtPclFontEntry 3 }

kmPrtPclFontSource  OBJECT-TYPE
    SYNTAX   INTEGER{
                unknown (0),
                internalRom (1),
                internalHd (2),
                downLoadRam (3),
                downLoadHd (4),
                downLoadFlashRom (5)
                }
    ACCESS   read-only
    STATUS   optional --Conditionally Mandatory
    DESCRIPTION
        "
        The information of a place that PCL font exists.
        "
    ::= { kmPrtPclFontEntry 4 }


kmPrtPsFontTable  OBJECT-TYPE
    SYNTAX     SEQUENCE OF KmPrtPsFontEntry
    ACCESS     not-accessible
    STATUS     optional --Conditionally Mandatory
    DESCRIPTION
        "
        This table shows PostScript font information of printer has.
        Since it is a function peculiar to PS, it is not necessary 
        to implement this table in the device in which PS is not installed.
        "
      ::= { kmPrtFont 2 }

kmPrtPsFontEntry OBJECT-TYPE
    SYNTAX      KmPrtPsFontEntry
    ACCESS      not-accessible
    STATUS      optional --Conditionally Mandatory
    DESCRIPTION
        "
        Information about printer's PS fonts.
        Entries may exist in the table for each device
        index whose device type is 'printer'.
        "
    INDEX  { hrDeviceIndex, kmPrtPsFontIndex }
    ::= { kmPrtPsFontTable 1 }

    KmPrtPsFontEntry ::= SEQUENCE {
        kmPrtPsFontIndex  INTEGER,
        kmPrtPsFontName   OCTET STRING,
        kmPrtPsFontNumber INTEGER,
        kmPrtPsFontSource INTEGER,
        kmPrtPsFontFontFileName OCTET STRING
        }

kmPrtPsFontIndex  OBJECT-TYPE
    SYNTAX   INTEGER (1..65535) 
    ACCESS   read-only
    STATUS   optional --Conditionally Mandatory
    DESCRIPTION
        "
        A unique value used to identify this entry. 
        "
      ::= { kmPrtPsFontEntry 1 }

kmPrtPsFontName  OBJECT-TYPE
    SYNTAX   OCTET STRING (SIZE(0..63)) 
    ACCESS   read-only
    STATUS   optional --Conditionally Mandatory
    DESCRIPTION
        "
        The name of PS Font. 
        "
      ::= { kmPrtPsFontEntry 2 }

kmPrtPsFontNumber  OBJECT-TYPE
    SYNTAX   INTEGER(0..65535) 
    ACCESS   read-only
    STATUS   optional --Conditionally Mandatory
    DESCRIPTION
        "
        The number of PS Font. 
        This number is used in order to administrate
        printer's fonts.
        If a printer does not manage this number, 
        this value should be implemented same as kmPrtPsFontIndex.
        "
      ::= { kmPrtPsFontEntry 3 }

kmPrtPsFontSource  OBJECT-TYPE
    SYNTAX   INTEGER{
                unknown (0),
                internalRom (1),
                internalHd (2),
                downLoadRam (3),
                downLoadHd (4),
                downLoadFlashRom (5)
                }
    ACCESS   read-only
    STATUS   optional --Conditionally Mandatory
    DESCRIPTION
        "
        The information of a place that PS font exists
        "
      ::= { kmPrtPsFontEntry 4 }

kmPrtPsFontFontFileName  OBJECT-TYPE
    SYNTAX   OCTET STRING (SIZE(0..63)) 
    ACCESS   read-only
    STATUS   optional --Conditionally Mandatory
    DESCRIPTION
        "
        The file name of PS Font file. 
        "
      ::= { kmPrtPsFontEntry 5 }


-- kmPrtPaper Group

-- Includes the information of the paper size, which a printer can print.
-- The paper size showing here should be the size, which printer controller
-- can process (size can specified by a driver), and it does not have to be
-- matched with the paper size that MFP can process.


kmPrtPaperSizeTable  OBJECT-TYPE
    SYNTAX     SEQUENCE OF KmPrtPaperSizeEntry
    ACCESS     not-accessible
    STATUS     mandatory
    DESCRIPTION
        "
        A table of the printer selectable paper sizes.
        Even if a printer can not recognize the supportable paper, 
        one object ('unknown' or 'other') must be loaded at least. 
        "
      ::= { kmPrtPaper 1 }

kmPrtPaperSizeEntry OBJECT-TYPE
    SYNTAX      KmPrtPaperSizeEntry
    ACCESS      not-accessible
        STATUS      mandatory
        DESCRIPTION
        "
        An entry exists in this table for each
        device entry in the hostmib device table whose type
        is 'printer'
        "
        INDEX  { hrDeviceIndex, kmPrtPaperSizeIndex }
        ::= {kmPrtPaperSizeTable 1 }

    KmPrtPaperSizeEntry ::= SEQUENCE {
        kmPrtPaperSizeIndex   INTEGER,
        kmPrtPaperSizeName    OCTET STRING,
        kmPrtPaperFeedDir     INTEGER
        }

kmPrtPaperSizeIndex  OBJECT-TYPE
    SYNTAX   INTEGER (1..65535) 
    ACCESS   read-only
    STATUS   mandatory
    DESCRIPTION
        "
        A unique value used to identify this entry. 
        "
      ::= { kmPrtPaperSizeEntry  1 }

kmPrtPaperSizeName  OBJECT-TYPE
    SYNTAX   OCTET STRING (SIZE(0..31)) 
    ACCESS   read-only
    STATUS   mandatory
    DESCRIPTION
        "
        The name of paper size.
        e.g., letter, legal, A4, B5 etc. 
        "
      ::= { kmPrtPaperSizeEntry  2 }

kmPrtPaperFeedDir  OBJECT-TYPE
    SYNTAX   INTEGER{
                other (0),  -- unknown feed direction
                    -- (In the case of supporting both of SEF and LEF)
                sef (1),   -- Portrait(short edge Feed)
                lef (2)    -- Landscape(long edge feed) 
                }
    ACCESS   read-only
    STATUS   mandatory
    DESCRIPTION
        "
        This value shows paper feeding orientation.
        "
      ::= { kmPrtPaperSizeEntry  3 }


-- kmPrtOverLay Group

-- The information of downloaded Overlay files
-- If a printer have a function of downloading the overlays 
-- and a function of managing it from network access, 
-- this group should be implemented.

kmPrtOverLayTable OBJECT-TYPE
    SYNTAX     SEQUENCE OF KmPrtOverLayEntry
    ACCESS     not-accessible
    STATUS     optional --Conditionally Mandatory
    DESCRIPTION
        "
        This table shows downloaded Overlay files.
        "
      ::= { kmPrtOverLay 1 }

kmPrtOverLayEntry OBJECT-TYPE
    SYNTAX      KmPrtOverLayEntry
    ACCESS      not-accessible
    STATUS      optional --Conditionally Mandatory
    DESCRIPTION
        "
        "
      INDEX  { hrDeviceIndex, kmPrtOverLayIndex }
    ::= { kmPrtOverLayTable 1 }

    KmPrtOverLayEntry ::= SEQUENCE {
        kmPrtOverLayIndex      INTEGER,
        kmPrtOverLayLangType   INTEGER,
        kmPrtOverLayFileName   OCTET STRING,
        kmPrtOverLayOwnerName  OCTET STRING
        }

kmPrtOverLayIndex  OBJECT-TYPE
    SYNTAX   INTEGER (1..65535) 
    ACCESS   read-only
    STATUS   optional --Conditionally Mandatory
    DESCRIPTION
        "
        A unique value used to identify page description
        language of over lay files.
        "
        ::= { kmPrtOverLayEntry 1 }

kmPrtOverLayLangType  OBJECT-TYPE
    SYNTAX   INTEGER {
                unknown (0),
                pcl (1),
                ps (2),
                gdi (3),
                linePrinter (4),
                ipds (5),
                ppml (6),
                other (7)
                }
    ACCESS   read-only
    STATUS   optional --Conditionally Mandatory
    DESCRIPTION
        "
         The page description language of over lay file.
        "
      ::= { kmPrtOverLayEntry 2 }

kmPrtOverLayFileName  OBJECT-TYPE
    SYNTAX   OCTET STRING (SIZE(0..31)) 
    ACCESS   read-only
    STATUS   optional --Conditionally Mandatory
    DESCRIPTION
        "
        The file name of over lay file.
        "
      ::= { kmPrtOverLayEntry 3 }

kmPrtOverLayOwnerName  OBJECT-TYPE
    SYNTAX   OCTET STRING (SIZE(0..31)) 
    ACCESS   read-only
    STATUS   optional --Conditionally Mandatory
    DESCRIPTION
        "
        Owner's name of over lay file.
        "
      ::= { kmPrtOverLayEntry 4 }


-- kmPrtColorMatching Group

-- The information of CM Profiles.
-- If a printer has a function of downloading
-- the Color Matching Profile and a function of managing
-- it from network access, this group should be implemented.

kmPrtCMProfileTable OBJECT-TYPE
    SYNTAX     SEQUENCE OF KmPrtCMProfileEntry
    ACCESS     not-accessible
    STATUS     optional --Conditionally Mandatory
    DESCRIPTION
        "
        This table shows information of color matching profiles.
        "
      ::= { kmPrtColorMatching 1 }

kmPrtCMProfileEntry OBJECT-TYPE
    SYNTAX      KmPrtCMProfileEntry
    ACCESS      not-accessible
    STATUS      optional --Conditionally Mandatory
    DESCRIPTION
        "
        "
        INDEX  { hrDeviceIndex, kmPrtCMProfileIndex }
    ::= {  kmPrtCMProfileTable 1 }

    KmPrtCMProfileEntry ::= SEQUENCE {
        kmPrtCMProfileIndex       INTEGER,
        kmPrtCMSourceType         INTEGER,
        kmPrtCMProfileName        OCTET STRING,
        kmPrtCMProfileFileName    OCTET STRING,
        kmPrtCMProfileClass       INTEGER,
        kmPrtCMProfileColorSpace  INTEGER,
        kmPrtCMProfileAvailability  INTEGER
        }

kmPrtCMProfileIndex  OBJECT-TYPE
    SYNTAX   INTEGER (1..65535) 
    ACCESS   read-only
    STATUS   optional --Conditionally Mandatory
    DESCRIPTION
        "
        A unique value used to identify CM profile.
        "
      ::= { kmPrtCMProfileEntry 1 }

kmPrtCMSourceType  OBJECT-TYPE
    SYNTAX   INTEGER {
                unknown (0),
                internalRom (1),
                internalHd (2),
                downLoadRam (3),
                downLoadHd (4),
                downLoadFlashRom (5)
                }
    ACCESS   read-only
    STATUS   optional --Conditionally Mandatory
    DESCRIPTION
        "
         The source type of CM profiles.
        "
      ::= { kmPrtCMProfileEntry 2 }

kmPrtCMProfileName  OBJECT-TYPE
    SYNTAX   OCTET STRING (SIZE(0..31)) 
    ACCESS   read-only
    STATUS   optional --Conditionally Mandatory
    DESCRIPTION
        "
        The name of CM profile.
        "
      ::= { kmPrtCMProfileEntry 3 }

kmPrtCMProfileFileName  OBJECT-TYPE
    SYNTAX   OCTET STRING (SIZE(0..31)) 
    ACCESS   read-only
    STATUS   optional --Conditionally Mandatory
    DESCRIPTION
        "
        The file name of CM profile.
        "
      ::= { kmPrtCMProfileEntry 4 }

kmPrtCMProfileClass  OBJECT-TYPE
    SYNTAX   INTEGER {
              other(0),
              scnr(1), -- inputDeviceProfile
              mntr(2), -- displayDeviceProfile
              prtr(3), -- outputDeviceProfile
              link(4), -- deviceLinkProfile
              spac(5), -- colorSpaceConversionProfile
              abst(6), -- abstructProfile
              nmcl(7)  -- namedColorProfile
             }
    ACCESS   read-only
    STATUS   optional --Conditionally Mandatory
    DESCRIPTION
        "
        The type of ICC Profile.
        "
      ::= { kmPrtCMProfileEntry 5 }

kmPrtCMProfileColorSpace  OBJECT-TYPE
    SYNTAX   INTEGER {
              other(0),
              xyz(1),
              lab(2),
              luv(3),
              yCbCr(4),
              yxy(5),
              rgb(6),
              gray(7),
              hsv(8),
              hls(9),
              cmyk(10),
              cmy(11),
              clr2(12),
              clr3(13),
              clr4(14),
              clr5(15),
              clr6(16),
              clr7(17),
              clr8(18),
              clr9(19),
              clrA(20),
              clrB(21),
              clrC(22),
              clrD(23),
              clrE(24),
              clrF(25)
             }
    ACCESS   read-only
    STATUS   optional --Conditionally Mandatory
    DESCRIPTION
        "
        The color space of ICC Profile.
        "
      ::= { kmPrtCMProfileEntry 6 }

kmPrtCMProfileAvailability  OBJECT-TYPE
    SYNTAX   INTEGER {
              available (3),
              unavailable (4)
             }
    ACCESS   read-only
    STATUS   optional --Conditionally Mandatory
    DESCRIPTION
        "
        The availability of ICC Profile for printer. 
        "
      ::= { kmPrtCMProfileEntry 7 }


-- Private Scanner MIB

kmScannerMib      OBJECT IDENTIFIER ::= { kmScanner 5 }

kmScnMibVersion  OBJECT-TYPE
    SYNTAX     DisplayString (SIZE(0..7))
    ACCESS     read-only
    STATUS     mandatory
    DESCRIPTION
        " 
         The version information of Konica-Minolta Standard MIB specification.

         This indicates the version of the Konica-Minolta Private Scanner MIB 
         which is implemented. 

         It is written as AA.BC.
         AA is indicating major revision, and B and C is 
         minor revision. Decimal point is ASCII-coded period.

         This definition file is corresponded to '1.50'.
        "
    ::= { kmScannerMib 1 }

   kmScnGeneral    OBJECT IDENTIFIER ::= { kmScannerMib 2 }
   kmScnODH        OBJECT IDENTIFIER ::= { kmScannerMib 3 }
   kmScnSensor     OBJECT IDENTIFIER ::= { kmScannerMib 4 }
   kmScnCapability OBJECT IDENTIFIER ::= { kmScannerMib 7 }
   kmScnAlert      OBJECT IDENTIFIER ::= { kmScannerMib 10 }


-- The General Scanner Group

-- This group shows general information of Scanner. 

kmScnGeneralTable OBJECT-TYPE
    SYNTAX     SEQUENCE OF KmScnGeneralEntry
    ACCESS     not-accessible
    STATUS     mandatory
    DESCRIPTION
         "
          A table of general information of scanner.
         "
    ::= { kmScnGeneral 1 }

kmScnGeneralEntry OBJECT-TYPE
    SYNTAX      KmScnGeneralEntry
    ACCESS      not-accessible
    STATUS      mandatory
    DESCRIPTION
        "
         An entry exists in this table for each
         device entry in the hostmib device table whose type
         is 'scanner'.
        "
     INDEX  {  hrDeviceIndex }
     ::= { kmScnGeneralTable 1 }

    KmScnGeneralEntry ::= SEQUENCE {
          kmScnGeneralReset             INTEGER,
          kmScnODHDefaultIndex          INTEGER,
          kmScnSensorDefaultIndex       INTEGER,
          kmScnGeneralStatus            INTEGER
         }

kmScnGeneralReset  OBJECT-TYPE
    SYNTAX    INTEGER{
                   notSupported (2),
                   notResetting (3),
                   powerCycleReset (4), -- Cold Start
                   resetToNVRAM (5), -- Warm Start
                   resetToFactoryDefaults (6) -- Reset contents of
                                              -- NVRAM to factory defaults
                   }
    ACCESS     read-write
    STATUS     mandatory
    DESCRIPTION
        "
         Setting this MIB will reset the scanner.
         Default value for this is noResetting(3).
         By setting resetToFactoryDefaults(6),
         all the setting should revert to the factory
         default settings.
         If the Scanner does not support 'Reset',
         device should return notSupported(2).
        "
    ::= { kmScnGeneralEntry 1 }

kmScnODHDefaultIndex OBJECT-TYPE
     SYNTAX     INTEGER(1..65535)
     ACCESS     read-write
     STATUS     mandatory
     DESCRIPTION
          "
          The value of kmScnODHIndex corresponding to the default ODH
          sub-unit.
          -- ODH (Original Document Handler)

          If device cannot support to change default ODH,
          this object may implement as ReadOnly.
          At least '1' must be implemented. 
          "
     ::= { kmScnGeneralEntry 2 }

kmScnSensorDefaultIndex OBJECT-TYPE
     SYNTAX     INTEGER(1..65535)
     ACCESS     read-write
     STATUS     mandatory
     DESCRIPTION
          "
          The value of kmScnSensorIndex corresponding to the default
          sensor sub-unit; that is, this object selects the default
          sensor.

          If device cannot support to change default Sensor,
          this object may implement as ReadOnly.
          At least '1' must be implemented. 
         "
     ::= { kmScnGeneralEntry 3 }

kmScnGeneralStatus OBJECT-TYPE
    SYNTAX    INTEGER {
                   unknown (0),
                   fatalError (1),
                   error (2),
                   warning (3),
                   scanning (4),
                   busy (5),
                   ready (6)
               }
    ACCESS     read-only
    STATUS     mandatory
    DESCRIPTION
         "Indicates scanner general status."
    ::= { kmScnGeneralEntry 4 }


kmScnCtrlName OBJECT-TYPE
    SYNTAX    OCTET STRING(SIZE(0..31))
    ACCESS     read-only
    STATUS     mandatory
    DESCRIPTION
         "
         This object shows the name of scanner controller.
         If device has no independent scanner controller or no 
         product name of it, this value should be  same as sysDescr.
         In case of printer, this value should be same as sysDescr.
        "  
    ::= { kmScnGeneral 2 }


--  The Original Document Handler Group

-- This group shows the information of Original Document Handler (ODH).

kmScnODHTable OBJECT-TYPE
     SYNTAX     SEQUENCE OF KmScnODHEntry
     ACCESS     not-accessible
     STATUS     mandatory
     DESCRIPTION
          "
           A table of the devices capable of providing original
          documents for input to the scanning process, handling those
          originals during scanning, and depositing the original
          documents in an output bin.
         "
     ::= { kmScnODH 1 }

kmScnODHEntry OBJECT-TYPE
     SYNTAX     KmScnODHEntry
     ACCESS     not-accessible
     STATUS     mandatory
     DESCRIPTION
          "Attributes of a Original Document Handler (ODH) device.
          Entries may exist in the table for each device index whose
          device type is `scanner'."
     INDEX  {  hrDeviceIndex, kmScnODHIndex }
     ::= { kmScnODHTable 1 }

     KmScnODHEntry ::= SEQUENCE {
          kmScnODHIndex                       INTEGER,
          kmScnODHType                        INTEGER,
          kmScnODHDimUnit                     INTEGER,
          kmScnODHMaxDimFeedDir               INTEGER,
          kmScnODHMaxDimXFeedDir              INTEGER,
          kmScnODHMinDimFeedDir               INTEGER,
          kmScnODHMinDimXFeedDir              INTEGER,
          kmScnODHCapacityUnit                INTEGER,
          kmScnODHInputMaxCapacity            INTEGER,
          kmScnODHInputCurrentLevel           INTEGER,
          kmScnODHOutputMaxCapacity           INTEGER,
          kmScnODHOutputRemainingCapacity     INTEGER,
          kmScnODHSpeedUnit                   INTEGER,
          kmScnODHMaxSpeed                    INTEGER,
          kmScnODHMaxMediaWeight              INTEGER,
          kmScnODHSimplexDuplex               INTEGER,
          kmScnODHDocumentScanOrder           INTEGER,
          kmScnODHInterleaving                INTEGER,
          kmScnODHDescription                 OCTET STRING
         }

kmScnODHIndex OBJECT-TYPE
     SYNTAX     INTEGER (1..65535)
     ACCESS     read-only
     STATUS     mandatory
     DESCRIPTION
          "A unique value used by the scanner to identify this ODH sub-
          unit. Although these values may change due to a major
          reconfiguration of the device (e.g. the addition of new ODH
          sub-units to the scanner), values are expected to remain
          stable across successive scanner power cycles."
     ::= { kmScnODHEntry 1 }

kmScnODHType OBJECT-TYPE
  --  This value is a type 2 enumeration
     SYNTAX     INTEGER {
          other(1),
          unknown(2),
          automaticDocumentFeeder(3),
          automaticBookReader(4),
          flatbedManual(5),
          sheetFeedManual(6),
          handScanner(7),
          digitalCamera(8)
         }
     ACCESS     read-only
     STATUS     mandatory
     DESCRIPTION
          "The type of technology employed by the ODH sub-unit."
     ::= { kmScnODHEntry 2 }

kmScnODHDimUnit OBJECT-TYPE
     SYNTAX     INTEGER {
                other(1),
                unknown(2),
                tenThousandthsOfInches(3),  -- .0001
                micrometers(4)
                }
     ACCESS     read-only
     STATUS     mandatory
     DESCRIPTION
          "The unit of measurement for use calculating and relaying
          dimensional values for this ODH sub-unit."
     ::= { kmScnODHEntry 3 }

kmScnODHMaxDimFeedDir OBJECT-TYPE
     SYNTAX     INTEGER
     ACCESS     read-only
     STATUS     mandatory
     DESCRIPTION
          "This object provides the value of the maximum dimension, in
          the feed direction, of the original document media that is
          accepted by this ODH sub-unit. The feed direction is parallel
          to the direction in which the media moves. This dimension is
          measured in ODH sub-unit dimensional units (kmScnODHDimUnit).
          This is NOT the size of each original. If the scanner is able
          to sense the size of the original during the scanning process
          of an individual original document, that information may be
          provided in the image data. The value (-1) means other and
          specifically means that this sub-unit places no restriction on
          this parameter. The value (-2) indicates unknown."
     ::= { kmScnODHEntry 4 }

kmScnODHMaxDimXFeedDir OBJECT-TYPE
     SYNTAX     INTEGER
     ACCESS     read-only
     STATUS     mandatory
     DESCRIPTION
          "This object provides the value of the maximum dimension, in
          the cross feed direction, of the media that is accepted by
          this input sub-unit. The cross  feed direction is ninety
          degrees relative to direction of media movement associated
          with this sub-unit. This dimension is measured in ODH sub-unit
          dimensional units (kmScnODHDimUnit). This is NOT the size of
          each original. If the scanner is able to sense the size of the
          original during the scanning process of an individual original
          document, that information may be provided in the image data.
          The value (-1) means other and specifically means that this
          sub-unit places no restriction on this parameter. The value (-
          2) indicates unknown."
     ::= { kmScnODHEntry 5 }

kmScnODHMinDimFeedDir OBJECT-TYPE
     SYNTAX     INTEGER
     ACCESS     read-only
     STATUS     mandatory
     DESCRIPTION
          "This object provides the value of the minimum dimension, in
          the feed direction, of the media that is accepted by this ODH
          sub-unit. This dimension is measured in ODH sub-unit
          dimensional units (kmScnODHDimUnit). This is NOT the size of
          each original. If the scanner is able to sense the size of the
          original during the scanning process of an individual original
          document, that information may be provided in the image data.
          The value (-1) means other and specifically means that this
          sub-unit places no restriction on this parameter. The value (-
          2) indicates unknown."
     ::= { kmScnODHEntry 6 }

kmScnODHMinDimXFeedDir OBJECT-TYPE
     SYNTAX     INTEGER
     ACCESS     read-only
     STATUS     mandatory
     DESCRIPTION
          "This object provides the value of the minimum dimension, in
          the cross feed direction, of the media that is accepted by
          this input sub-unit. The cross  feed direction is ninety
          degrees relative to the feed direction associated with this
          sub-unit. This dimension is measured in ODH sub-unit
          dimensional units (kmScnODHDimUnit). This is NOT the size of
          each original. If the scanner is able to sense the size of the
          original during the scanning process of an individual original
          document, that information may be provided in the image data.
          The value (-1) means other and specifically means that this
          sub-unit places no restriction on this parameter. The value (-
          2) indicates unknown."
     ::= { kmScnODHEntry 7 }

kmScnODHCapacityUnit OBJECT-TYPE
     SYNTAX     INTEGER{
                     other (1),
                     unknown (2),
                     tenThousandthsOfInches (3),  -- .0001
                     micrometers (4),
                     sheets (8),
                     feet (16),
                     meters (17)
                    }
     ACCESS     read-only
     STATUS     mandatory
     DESCRIPTION
          "The unit of measurement for use in calculating and relaying
          capacity values for this input sub-unit."
     ::= { kmScnODHEntry 8 }

kmScnODHInputMaxCapacity OBJECT-TYPE
     SYNTAX     INTEGER
     ACCESS     read-only
     STATUS     mandatory
     DESCRIPTION
          "The claimed maximum capacity of the input portion of the ODH
          sub-unit in ODH sub-unit capacity units (kmScnODHCapacityUnit).
          If this ODH sub-unit can reliably sense this value, the value
          is sensed by the scanner and may not be changed by management
          requests; otherwise, the value may be written (by a Remote
          Control Panel or a Management Application). The value (-1)
          means other and specifically indicates that the sub-unit
          places no restrictions on this parameter.  The value (-2)
          means unknown."
     ::= { kmScnODHEntry 9 }

kmScnODHInputCurrentLevel OBJECT-TYPE
     SYNTAX     INTEGER
     ACCESS     read-only
     STATUS     mandatory
     DESCRIPTION
          "The current capacity of the input portion of the ODH sub-unit
          in ODH sub-unit capacity units (kmScnODHCapacityUnit). If this
          ODH sub-unit can reliably sense this value, the value is
          sensed by the scanner and may not be changed by management
          requests; otherwise, the value may be written (by a Remote
          Control Panel or a Management Application). The value (-1)
          means other and specifically indicates that the sub-unit
          places no restrictions on this parameter.  The value (-2)
          means unknown. The value (-3) means that the scanner knows
          that at least one unit remains."
     ::= { kmScnODHEntry 10 }

kmScnODHOutputMaxCapacity OBJECT-TYPE
     SYNTAX     INTEGER
     ACCESS     read-only
     STATUS     mandatory
     DESCRIPTION
          "The claimed maximum capacity of the output portion of the ODH
          sub-unit in ODH sub-unit capacity units (kmScnODHCapacityUnit).
          If this ODH sub-unit can reliably sense this value, the value
          is sensed by the scanner and may not be changed by management
          requests; otherwise, the value may be written (by a Remote
          Control Panel or a Management Application). The value (-1)
          means other and specifically indicates that the sub-unit
          places no restrictions on this parameter.  The value (-2)
          means unknown."
     ::= { kmScnODHEntry 11 }

kmScnODHOutputRemainingCapacity OBJECT-TYPE
     SYNTAX     INTEGER
     ACCESS     read-only
     STATUS     mandatory
     DESCRIPTION
          "The remaining capacity of output portion of the ODH sub-unit
          in ODH sub-unit capacity units (kmScnODHCapacityUnit). If this
          ODH sub-unit can reliably sense this value, the value is
          sensed by the scanner and may not be changed by management
          requests; otherwise, the value may be written (by a Remote
          Control Panel or a Management Application). The value (-1)
          means other and specifically indicates that the sub-unit
          places no restrictions on this parameter.  The value (-2)
          means unknown.  The value (-3) means that the scanner knows
          that there remains capacity for at least one unit."
     ::= { kmScnODHEntry 12 }

kmScnODHSpeedUnit OBJECT-TYPE
     SYNTAX     INTEGER{
                   other (1),
                   unknown (2),
                   tenThousandthsOfInchesPerHour(3),   -- .0001/hour
                   micrometersPerHour(4),
                   impressionsPerHour(7),
                   sheetsPerHour(8),
                   feetPerHour(16),
                   metersPerHour(17)
                  }
     ACCESS     read-only
     STATUS     mandatory
     DESCRIPTION
          "The unit scanning speed of this ODH expressed in scans.
           If unit is impressionsPerHour(7) or sheetsPerHour(8),
           reference paper size is A4 or letter"
     ::= { kmScnODHEntry 13 }

kmScnODHMaxSpeed OBJECT-TYPE
     SYNTAX     INTEGER
     ACCESS     read-only
     STATUS     mandatory
     DESCRIPTION
          "The maximum scanning speed of this ODH expressed in scans. 
           A value of (-1) implies 'other'.
           The value (-2) indicates unknown."
     ::= { kmScnODHEntry 14 }

kmScnODHMaxMediaWeight  OBJECT-TYPE
     SYNTAX     INTEGER
     ACCESS     read-only
     STATUS     mandatory
     DESCRIPTION
          "The max weight of the medium associated with this input sub-
          unit in grams / per meter squared. The value (-1) means other
          and specifically indicates that the sub-unit places no
          restrictions on this parameter. The value (-2) means unknown."
     ::= { kmScnODHEntry 15 }

kmScnODHSimplexDuplex OBJECT-TYPE
  --   This value is a type 2 enumeration
     SYNTAX     INTEGER {
          other(1),
          unknown(2),
          simplex(3),
          duplexConcurrent(4),
          duplexSequential(5)
          }
     ACCESS     read-only
     STATUS     mandatory
     DESCRIPTION
          "The type of scanning performed by this ODH and sensor
          combination. Simplex indicates that one side of the original
          document is sensed. DuplexConcurrent indicates that both sides
          of the document are imaged at the same time using dual
          sensors. DuplexSequential indicates that first one side and
          then the other side is imaged using the same sensor mechanism,
          with automatic flipping of the original document."
     ::= { kmScnODHEntry 16 }

kmScnODHDocumentScanOrder OBJECT-TYPE
  --   This value is a type 2 enumeration
     SYNTAX     INTEGER {
          other(1),
          unknown(2),
          firstToLast(3),
          lastToFirst(4)
          }
     ACCESS     read-only
     STATUS     mandatory
     DESCRIPTION
          "The order of document traversal performed by this ODH.
          FirstToLast indicates that the first page of the document is
          scanned first and the last page is scanned last, which is
          'Scanner Order' or 'Fax Order'. LastToFirst indicates that the
          last page is scanned first and the first page is scanned last.
          This is 'Copier Order'."
     ::= { kmScnODHEntry 17 }

kmScnODHInterleaving OBJECT-TYPE
     SYNTAX     INTEGER
     ACCESS     read-only
     STATUS     mandatory
     DESCRIPTION
          "The number of scans that the duplex pages are offset from
          each other. (0) indicates that the first side and opposite
          side is scanned concurrently. (1) indicates that the opposite
          side is scanned one page after the first side (i.e. 1,2,3. . .
          order). (2) indicates that the first side leads the opposite
          side by 2 pages (1,3,2,5,. . . order). (3) indicates that the
          first side leads the opposite side by 3 pages, and so forth.
          The value (32767) indicates that the entire first side is
          imaged prior to the opposite side. The terms 'first side' and
          'opposite side' is determined by the kmScnODHDocumentScanOrder
          attribute.

          The value (-1) means other and specifically indicates
          that the sub-unit places no restrictions on this parameter.
          The value (-2) means unknown."
     ::= { kmScnODHEntry 18 }

kmScnODHDescription OBJECT-TYPE
     SYNTAX     OCTET STRING (SIZE(0..255))
     ACCESS read-only
     STATUS     mandatory
     DESCRIPTION
          "The manufacturer-provided description of this ODH in the
          localization specified by prtGeneralCurrentLocalization.

          If no information for this sub-unit, this value should be 
          (zero_length)."
     ::= { kmScnODHEntry 19 }


-- The Image Sensor Group

kmScnSensorTable OBJECT-TYPE
     SYNTAX     SEQUENCE OF KmScnSensorEntry
     ACCESS     not-accessible
     STATUS     mandatory
     DESCRIPTION
          "This table contains information about the various image
          sensor sub-units in the scanner."
     ::= { kmScnSensor 1 }

kmScnSensorEntry OBJECT-TYPE
     SYNTAX     KmScnSensorEntry
     ACCESS     not-accessible
     STATUS     mandatory
     DESCRIPTION
          "Entries may exist in the table for each device index whose
          device type is `scanner'."
     INDEX  {  hrDeviceIndex, kmScnSensorIndex }
     ::= { kmScnSensorTable 1 }

     KmScnSensorEntry ::= SEQUENCE {
          kmScnSensorIndex                  INTEGER,
          kmScnSensorTech                   INTEGER,
          kmScnSensorLifeCount              Counter,
          kmScnSensorPowerOnCount           Counter,
          kmScnSensorColorSpace             INTEGER,
          kmScnSensorResolutionUnit         INTEGER,
          kmScnSensorOpticalResolFeedDir    INTEGER,
          kmScnSensorOpticalResolXFeedDir   INTEGER,
          kmScnSensorImageContrast          INTEGER,
          kmScnSensorImageBrightness        INTEGER,
          kmScnSensorXOffset                INTEGER,
          kmScnSensorYOffset                INTEGER,
          kmScnSensorOutputResolFeedDir     INTEGER,
          kmScnSensorOutputResolXFeedDir    INTEGER,
          kmScnSensorOpticalBitsPerPixel    INTEGER,
          kmScnSensorOutputBitsPerPixel     INTEGER
         }

kmScnSensorIndex OBJECT-TYPE
     SYNTAX     INTEGER (1..65535)
     ACCESS     read-only
     STATUS     mandatory
     DESCRIPTION
          "A unique value used by the scanner to identify this sensing
          sub-unit.  Although these values may change due to a major
          reconfiguration of the device (e.g. the addition of new
          marking sub-units to the scanner), values are expected to
          remain stable across successive scanner power cycles."
     ::= { kmScnSensorEntry 1 }

kmScnSensorTech OBJECT-TYPE
  -- This value is a type 2 enumeration
     SYNTAX     INTEGER {
          other(1),
          unknown(2),
          linearCCD(3),
          rectangularCCD(4),
          contactImageSensor(5),
          laserScanner(6)
         }
     ACCESS     read-only
     STATUS     mandatory
     DESCRIPTION
          "The type of sensing technology used for this sensing sub-
          unit."
     ::= { kmScnSensorEntry 2 }

kmScnSensorLifeCount OBJECT-TYPE
     SYNTAX     Counter
     ACCESS     read-only
     STATUS     mandatory
     DESCRIPTION
          "The count of the number of images scanned during the life of
          scanner.

          If device cannot support scan count function,
          this value should be always (0).
          "
     ::= { kmScnSensorEntry 3 }

kmScnSensorPowerOnCount OBJECT-TYPE
     SYNTAX     Counter
     ACCESS     read-only
     STATUS     mandatory
     DESCRIPTION
          "The count of the number of images scanned since the equipment
          was most recently powered on.

          If device cannot support scan count function,
          this value should be always (0).
          "
     ::= { kmScnSensorEntry 4 }

kmScnSensorColorSpace OBJECT-TYPE
     SYNTAX     INTEGER {
                 other(1),
                 unknown(2),
                 colorSpaceNative(3),
                 colorSpacesRGB(4),           -- sRGB
                 colorSpaceCIEXYZ(5),         -- CIEXYZ
                 colorSpaceCIELAB(6),
                 colorSpaceCMYK(7),
                 colorSpaceBiLevelMinWhite(8), -- Each pixel is a single bit.
                                               --  0 is white.
                 colorSpaceBiLevelMinBlack(9), -- Each pixel is a single bit.
                                               --  0 is black.
                 colorSpaceGrayScale(10),      -- Each pixel is composed of a
                                               --  single gray sample.
                 colorSpacePallette(11)        -- Each pixel indexes into a
                 }                              --  color mapping table.
     ACCESS     read-only
     STATUS     mandatory
     DESCRIPTION
          "The value of color space currently enabled for the
          sensor."
     ::= { kmScnSensorEntry 5 }

kmScnSensorResolutionUnit OBJECT-TYPE
  --   This value is a type 1 enumeration
     SYNTAX     INTEGER {
          other (1),
          unknown (2),
          tenThousandthsOfInches(3),  -- .0001
          micrometers(4)
          }
     ACCESS     read-only
     STATUS     mandatory
     DESCRIPTION
          "The unit of measure of distances."
     ::= { kmScnSensorEntry 6 }

kmScnSensorOpticalResolFeedDir OBJECT-TYPE
     SYNTAX     INTEGER
     ACCESS     read-only
     STATUS     mandatory
     DESCRIPTION
          "The number of addressable optical sensing positions in the
          feed direction per 10000 units of measure specified by
          Resolution Unit. A value of (-1) implies 'other' or 'infinite'
          while a value of (-2) implies 'unknown'."
     ::= { kmScnSensorEntry 7 }

kmScnSensorOpticalResolXFeedDir OBJECT-TYPE
     SYNTAX     INTEGER
     ACCESS     read-only
     STATUS     mandatory
     DESCRIPTION
          "The number of addressable optical sensing positions in the
          cross feed direction in 10000 units of measure specified by
          Resolution Unit. A value of (-1) implies 'other' or 'infinite'
          while a value of (-2) implies 'unknown'."
     ::= { kmScnSensorEntry 8 }

kmScnSensorImageContrast OBJECT-TYPE
     SYNTAX     INTEGER
     ACCESS     read-only
     STATUS     mandatory
     DESCRIPTION
          "This value indicates the relative sharpness of the image,
          with 0 being the lowest possible and 100 the highest possible
          contrast.  The value of -1 means other and specifically
          indicates that the sensor is using an automatic adjustment
          feature.  For sensors where this setting is not continuously
          variable, a write to this object will set the value to the
          closest implemented value.  For example, a sensor with five
          possible settings can only achieve 0, 25, 50, 75, and 100. A
          write value of 30 will result in a read response of 25.

          The value (-2) means unknown.
          "
     ::= { kmScnSensorEntry 9 }

kmScnSensorImageBrightness OBJECT-TYPE
     SYNTAX     INTEGER
     ACCESS     read-only
     STATUS     mandatory
     DESCRIPTION
          "This value indicates the relative brightness of the image,
          with 0 being the lightest possible and 100 the darkest
          possible image.  The value of -1 means other and specifically
          indicates that the sensor is using an automatic adjustment
          feature.  For sensors where this setting is not continuously
          variable, a write to this object will set the value to the
          closest implemented value.  For example, a sensor with five
          possible settings can only achieve 0, 25, 50, 75, and 100. A
          write with a value of 30 will result in a read response of
          25.
          The value (-2) means unknown.
          "
     ::= { kmScnSensorEntry 10 }

kmScnSensorXOffset OBJECT-TYPE
     SYNTAX     INTEGER
     ACCESS     read-only
     STATUS     mandatory
     DESCRIPTION
          "The offset, in units identified by Resolution Unit, from the X
          reference edge of the original document to the output scanned
          image.  The X reference edge is 180 degrees from the leading
          edge of the original document, as defined by the direction of
          the scan.  Negative margin values are typical and indicate
          that extra area is imaged that is never part of the original
          document.  Refer to the scan offsets figure.

          If device cannot recognize offset values,
          this value should be (0)."
     ::= { kmScnSensorEntry 11 }

kmScnSensorYOffset OBJECT-TYPE
     SYNTAX     INTEGER
     ACCESS read-only
     STATUS     mandatory
     DESCRIPTION
          "The offset, in units identified by Resolution Unit, from the
          leading edge of the original document, as defined by the
          direction of the scan, to the output scanned image.  Negative
          margin values are typical and indicate that extra area is
          imaged that is never part of the original document. Refer to
          the scan offsets figure.

          If device cannot recognize offset values,
          this value should be (0)."
     ::= { kmScnSensorEntry 12 }

kmScnSensorOutputResolFeedDir OBJECT-TYPE
     SYNTAX     INTEGER
     ACCESS     read-only
     STATUS     mandatory
     DESCRIPTION
          "The number of addressable output image positions in the feed
          direction per 10000 units of measure specified by
          Resolution Unit. A value of (-1) implies 'other' or 'infinite'
          while a value of (-2) implies 'unknown'."
     ::= { kmScnSensorEntry 13 }

kmScnSensorOutputResolXFeedDir OBJECT-TYPE
     SYNTAX     INTEGER
     ACCESS     read-only
     STATUS     mandatory
     DESCRIPTION
          "The number of addressable output image positions in the cross
          feed direction in 10000 units of measure specified by
          Resolution Unit. A value of (-1) implies 'other' or 'infinite'
          while a value of (-2) implies 'unknown'."
     ::= { kmScnSensorEntry 14 }

kmScnSensorOpticalBitsPerPixel OBJECT-TYPE
     SYNTAX     INTEGER
     ACCESS     read-only
     STATUS     mandatory
     DESCRIPTION
          "The number of bits used to describe a single pixel, as
          generated by the sensor in a single frequency range sample."
     ::= { kmScnSensorEntry 15 }


kmScnSensorOutputBitsPerPixel OBJECT-TYPE
     SYNTAX     INTEGER
     ACCESS     read-only
     STATUS     mandatory
     DESCRIPTION
          "The number of bits used to describe a single pixel, as output
          by the scanner for a single frequency range sample."
     ::= { kmScnSensorEntry 16 }


-- Scanner Capability Group


kmScnCapabilityTable OBJECT-TYPE
     SYNTAX     SEQUENCE OF KmScnCapabilityEntry
     ACCESS     not-accessible
     STATUS     mandatory
     DESCRIPTION
          "
           This table shows the capability of scanner function.
          "
     ::= { kmScnCapability 1 }

kmScnCapabilityEntry OBJECT-TYPE
     SYNTAX     KmScnCapabilityEntry
     ACCESS     not-accessible
     STATUS     mandatory
     DESCRIPTION
          "
           The information of scanner capability. 
          " 
     INDEX  {  hrDeviceIndex, kmScnCapabilityIndex }
     ::= { kmScnCapabilityTable 1 }

    KmScnCapabilityEntry ::= SEQUENCE {
            kmScnCapabilityIndex    INTEGER,
            kmScnCapSupportMask     INTEGER,
            kmScnCapResolution      INTEGER,
            kmScnCapColorMode       INTEGER,
            kmScnCapCompressionForm INTEGER,
            kmScnCapFileFormat      INTEGER,
            kmScnCapProtocol        INTEGER,
            kmScnCapScalingMin      INTEGER,
            kmScnCapScalingMax      INTEGER,
            kmScnCapBitDepth        INTEGER,
            kmScnCapDensityMin      INTEGER,
            kmScnCapDensityMax      INTEGER,
            kmScnCapImageEnhance    INTEGER,
            kmScnCapSpecialOriginal INTEGER,
            kmScnCapBookCopyMode    INTEGER,
            kmScnCapImageFeature    INTEGER,
            kmScnCapEraseMin        INTEGER,
            kmScnCapEraseMax        INTEGER,
            kmScnCapFoldEraseMin    INTEGER,
            kmScnCapFoldEraseMax    INTEGER
         }

kmScnCapabilityIndex OBJECT-TYPE
     SYNTAX     INTEGER (1..65535)
     ACCESS     read-only
     STATUS     mandatory
     DESCRIPTION
          "
          Index for scanner capability.
          Normally, this value should be 1.
          "
     ::= { kmScnCapabilityEntry 1 }

kmScnCapSupportMask  OBJECT-TYPE
    SYNTAX    INTEGER
    ACCESS    read-only
    STATUS    mandatory
    DESCRIPTION
        "
         Supported function of scanner is expressed
         with Bitmap.

           Bit  Value    Function
           ---   -----  ---------------
            0       1   scaling -- Zoom
            1       2   density
            2       4   duplex  -- Double sides
            3       8   rotate
            4      16   originalDirection
            5      32   splitDocument
        "
    ::= { kmScnCapabilityEntry 2 }

kmScnCapResolution  OBJECT-TYPE
    SYNTAX    INTEGER
    ACCESS    read-only
    STATUS    mandatory
    DESCRIPTION
        "
         Supported resolution of scanner is expressed
         with Bitmap.

           Bit  Value   Resolution
           ---   -----  ------------
            0       1   200dpi
            1       2   300dpi
            2       4   400dpi
            3       8   600dpi
            4      16   200x100dpi

        "
    ::= { kmScnCapabilityEntry 3 }

kmScnCapColorMode  OBJECT-TYPE
    SYNTAX    INTEGER
    ACCESS    read-only
    STATUS    mandatory
    DESCRIPTION
        "
         Supported color mode of scanner is expressed
         with Bitmap.

           Bit  Value   Resolution
           ---   -----  ------------
            0       1   black
            1       2   grayscale
            2       4   color
            3       8   Auto

        "
    ::= { kmScnCapabilityEntry 4 }


kmScnCapCompressionForm  OBJECT-TYPE
    SYNTAX    INTEGER
    ACCESS    read-only
    STATUS    mandatory
    DESCRIPTION
        "
         Supported compression form of scanner is expressed
         with Bitmap.

           Bit  Value   Compression Form
           ---   -----  ------------
            0       1   MH
            1       2   MR
            2       4   MMR
            3       8   JPEG
            4      16   JPEG-HighQuality
            5      32   JPEG-Standard
            6      64   JPEG-LowQuality

        "
    ::= { kmScnCapabilityEntry 5 }

kmScnCapFileFormat  OBJECT-TYPE
    SYNTAX    INTEGER
    ACCESS    read-only
    STATUS    mandatory
    DESCRIPTION
        "
         Supported file format of scanner is expressed
         with Bitmap.

           Bit  Value   Compression Form
           ---   -----  ------------
            0       1   TIFF
            1       2   PDF
            2       4   JPEG
            3       8   CompactPDF

        "
    ::= { kmScnCapabilityEntry 6 }

kmScnCapProtocol  OBJECT-TYPE
    SYNTAX    INTEGER
    ACCESS    read-only
    STATUS    mandatory
    DESCRIPTION
        "
         Supported protocol of scanner is expressed
         with Bitmap.

           Bit  Value   Protocol 
           ---   -----  ------------
            0       1   PullTWAIN
            1       2   ISIS （need not support）
            2       4   FTP
            3       8   Email
            4      16   SMB
            5      32   StoreHDD

        "
    ::= { kmScnCapabilityEntry 7 }


kmScnCapScalingMin  OBJECT-TYPE
    SYNTAX    INTEGER
    ACCESS    read-only
    STATUS    mandatory
    DESCRIPTION
        "
         The minimum value of scaling selection.
        "
    ::= { kmScnCapabilityEntry 8 }

kmScnCapScalingMax  OBJECT-TYPE
    SYNTAX    INTEGER
    ACCESS    read-only
    STATUS    mandatory
    DESCRIPTION
        "
         The maximum value of scaling selection.
        "
    ::= { kmScnCapabilityEntry 9 }

kmScnCapBitDepth  OBJECT-TYPE
    SYNTAX    INTEGER
    ACCESS    read-only
    STATUS    mandatory
    DESCRIPTION
        "
         The value of supported BitPerPixel.
        "
    ::= { kmScnCapabilityEntry 10 }

kmScnCapDensityMin  OBJECT-TYPE
    SYNTAX    INTEGER
    ACCESS    read-only
    STATUS    mandatory
    DESCRIPTION
        "
         The minimum value of density selection.
        "
    ::= { kmScnCapabilityEntry 11 }

kmScnCapDensityMax  OBJECT-TYPE
    SYNTAX    INTEGER
    ACCESS    read-only
    STATUS    mandatory
    DESCRIPTION
        "
         The maximum value of density selection.
        "
    ::= { kmScnCapabilityEntry 12 }

kmScnCapImageEnhance  OBJECT-TYPE
    SYNTAX    INTEGER
    ACCESS    read-only
    STATUS    mandatory
    DESCRIPTION
        "
         Supported image enhance is expressed
         with Bitmap.

           Bit  Value   Image
           ---   -----  ------------
            0       1   Auto
            1       2   Photo
            2       4   Text
            3       8   lowContrastOriginal
            4      16   TextAndPhoto

        "
    ::= { kmScnCapabilityEntry 13 }

kmScnCapSpecialOriginal  OBJECT-TYPE
    SYNTAX    INTEGER
    ACCESS    read-only
    STATUS    mandatory
    DESCRIPTION
        "
         Supported special original is expressed
         with Bitmap.

           Bit  Value   Original
           ---   -----  ------------
            0       1   normal
            1       2   zFoldOriginal
            2       4   mixedOriginal
            3       8   sdf(Single Document Feed)
            4      16   bookCopy
            5      32   memoryScan

        "
    ::= { kmScnCapabilityEntry 14 }

kmScnCapBookCopyMode  OBJECT-TYPE
    SYNTAX    INTEGER
    ACCESS    read-only
    STATUS    mandatory
    DESCRIPTION
        "
         Supported  book copy mode is expressed
         with Bitmap.

           Bit  Value   Mode
           ---   -----  ------------
            0       1   bookCopy
            1       2   leftBinding 
            2       4   rightBinding
            3       8   chapter
            4      16   frontCoverFacingPages
            5      32   frontAndBackCoverFacingPages

        "
    ::= { kmScnCapabilityEntry 15 }

kmScnCapImageFeature  OBJECT-TYPE
    SYNTAX    INTEGER
    ACCESS    read-only
    STATUS    mandatory
    DESCRIPTION
        "
         Supported image feature is expressed
         with Bitmap.

           Bit  Value   Mode
           ---   -----  ------------
            0       1   nonImageAreaErase
            1       2   negaPosReverse
            2       4   fullImagingArea
            3       8   BackGroundRemove

        "
    ::= { kmScnCapabilityEntry 16 }

kmScnCapEraseMin  OBJECT-TYPE
    SYNTAX    INTEGER
    ACCESS    read-only
    STATUS    mandatory
    DESCRIPTION
        "
         The minimum value of erase selection.
         If device has no erase function,
         this value should be 0.
        "
    ::= { kmScnCapabilityEntry 17 }

kmScnCapEraseMax  OBJECT-TYPE
    SYNTAX    INTEGER
    ACCESS    read-only
    STATUS    mandatory
    DESCRIPTION
        "
         The maximum value of erase selection.
         If device has no erase function,
         this value should be 0.
        "
    ::= { kmScnCapabilityEntry 18 }


kmScnCapFoldEraseMin  OBJECT-TYPE
    SYNTAX    INTEGER
    ACCESS    read-only
    STATUS    mandatory
    DESCRIPTION
        "
         The minimum value of fold erase selection.
         If device has no erase function,
         this value should be 0.
        "
    ::= { kmScnCapabilityEntry 19 }

kmScnCapFoldEraseMax  OBJECT-TYPE
    SYNTAX    INTEGER
    ACCESS    read-only
    STATUS    mandatory
    DESCRIPTION
        "
         The maximum value of fold erase selection.
         If device has no erase function,
         this value should be 0.
        "
    ::= { kmScnCapabilityEntry 20 }


-- Scanner Alert Group
-- This group shows alert message of scanner.
-- If the device has the printer engine(include FAX),
-- the kmScnAlertGroup's alert must be included in the prtAlert Group
-- of Printer MIB.(The device must not have the kmScnAlertGroup). 
-- If the device does not have the printer engine,
-- the kmScnAlertGroup's alert must be as it is
-- (Because the device does not have the PrinterMIB.).

kmScnAlertTable OBJECT-TYPE
    SYNTAX     SEQUENCE OF KmScnAlertEntry
    ACCESS     not-accessible
    STATUS     optional
    DESCRIPTION
        "
        "
    ::= { kmScnAlert 1 }

kmScnAlertEntry OBJECT-TYPE
    SYNTAX     KmScnAlertEntry
    ACCESS     not-accessible
    STATUS     optional
    DESCRIPTION
        "
        Entries may exist in the table for each device
        index with a device type of 'scanner'.
        "
    INDEX  { hrDeviceIndex, kmScnAlertIndex }
    ::= { kmScnAlertTable 1 }

KmScnAlertEntry ::= SEQUENCE {
    kmScnAlertIndex               INTEGER,
    kmScnAlertSeverityLevel       INTEGER,
    kmScnAlertTrainingLevel       INTEGER,
    kmScnAlertGroup               INTEGER,
    kmScnAlertLocation            INTEGER,
    kmScnAlertDescription         OCTET STRING,
    kmScnAlertTime                TimeTicks
    }

kmScnAlertIndex OBJECT-TYPE
    SYNTAX     INTEGER (1..65535)
    ACCESS      read-only
    STATUS     optional
    DESCRIPTION
         "
         The index value used to determine which alerts have
         been added or removed from the alert table. This is an
         incrementing INTEGER starting from zero every time the
         scanner is reset.  When the scanner adds an alert to the
         table, that alert is assigned the next higher INTEGER
         value from the last item entered into the table.  If the
         index value reaches its maximum value, the next item
         entered will cause the index value to roll over and
         start at zero again.  The first event placed in the
         alert table after a reset of the printer shall have an
         index value of 1. 
         "
    ::= { kmScnAlertEntry 1 }

kmScnAlertSeverityLevel OBJECT-TYPE
    -- This value is a type 1 enumeration
    SYNTAX    INTEGER {
                   other(1),
                   criticalBinaryChangeEvent(3),
                   warningUnaryChangeEvent(4),
                   warningBinaryChangeEvent(5)
               }
    ACCESS read-only
    STATUS     optional
    DESCRIPTION
         "
         The level of severity of this alert table entry.  The
         scanner determines the severity level assigned to each
         entry into the table.
         "
    ::= { kmScnAlertEntry 2 }

kmScnAlertTrainingLevel OBJECT-TYPE
    -- This value is a type 2 enumeration
    SYNTAX     INTEGER {
                   other(1),
                   unknown(2),
                   untrained(3),
                   trained(4),
                   fieldService(5),
                   management(6),
                   noInterventionRequired(7)
               }
    ACCESS read-only
    STATUS     optional
    DESCRIPTION
         "
         The level of training of this alert table entry.  The
         scanner determines the training level assigned to each
         entry into the table.
         "
    ::= { kmScnAlertEntry 3 }

kmScnAlertGroup OBJECT-TYPE
    -- This value is a type 1 enumeration
    SYNTAX     INTEGER {
                      other(1),
                      hostResourcesMIBStorageTable(3),
                      hostResourcesMIBDeviceTable(4),
                   -- Values of Konica-Minolta Private Scanner MIB
                      generalScanner (51),
                      originalDocumentHnadler (52),
                      sensor (53)
                     }
    ACCESS read-only
    STATUS     optional
    DESCRIPTION
         "
         The type of sub-unit within the scanner model that this
         alert is related. 
         "
    ::= { kmScnAlertEntry 4 }

kmScnAlertLocation OBJECT-TYPE
    SYNTAX     INTEGER
    ACCESS     read-only
    STATUS     optional
    DESCRIPTION
         "
         The codes to further refine the alert information.
         "
    ::= { kmScnAlertEntry 5 }

kmScnAlertDescription OBJECT-TYPE
    SYNTAX     OCTET STRING (SIZE(0..255))
    ACCESS     read-only
    STATUS     optional
    DESCRIPTION
         "
         A description of this alert entry in the localization
         specified by prtGeneralCurrentLocalization.
         "
    ::= { kmScnAlertEntry 6 }

kmScnAlertTime OBJECT-TYPE
    SYNTAX     TimeTicks
    ACCESS     read-only
    STATUS     optional
    DESCRIPTION
         "
         The value of sysUpTime at the time that this alert was
         generated.

         If device cannot detect the time of error occurred,
         this value should be (0).
         "
    ::= { kmScnAlertEntry 7 }


-- Private Network MIB

    kmNetworkMib     OBJECT IDENTIFIER ::= { kmNetwork 5 }


    kmNetMibVersion  OBJECT-TYPE
    SYNTAX     DisplayString (SIZE(0..7))
    ACCESS     read-only
    STATUS     mandatory
    DESCRIPTION
        "
         The version information of Konica-Minolta Standard MIB specification.

         This indicates the version of the Konica-Minolta Private Network MIB 
         which is implemented. 

         It is written as AA.BC.
         AA is indicating major revision, and B and C is 
         minor revision. Decimal point is ASCII-coded period.

         This definition file is corresponded to '1.50'.
        "
    ::= { kmNetworkMib 1 }


    kmNetGeneral       OBJECT IDENTIFIER ::= { kmNetworkMib 2 }
    kmNetProtocol      OBJECT IDENTIFIER ::= { kmNetworkMib 3 }

    kmNetCommand       OBJECT IDENTIFIER ::= { kmNetworkMib 5 }
    kmNetSnmp          OBJECT IDENTIFIER ::= { kmNetworkMib 6 }
    kmNetTcpip         OBJECT IDENTIFIER ::= { kmNetworkMib 7 }
    kmNetNetWare       OBJECT IDENTIFIER ::= { kmNetworkMib 8 }
    kmNetAppleTalk     OBJECT IDENTIFIER ::= { kmNetworkMib 9 }
    kmNetSmb           OBJECT IDENTIFIER ::= { kmNetworkMib 10 }

-- kmNetGeneral Group

-- The general information that Network has is included.
-- It shall have the followings as general information.
-- 1.   Version information of NetworkInterface
-- 2.   Hardware address
-- 3.   Cable related information


kmNetGeneralTable  OBJECT-TYPE
    SYNTAX    SEQUENCE OF KmNetGeneralEntry
    ACCESS    not-accessible
    STATUS    mandatory
    DESCRIPTION
        "
        Table for showing the general information of
        Network Interface. 
        "
    ::= { kmNetGeneral 1 }

kmNetGeneralEntry OBJECT-TYPE
    SYNTAX    KmNetGeneralEntry
    ACCESS    not-accessible
    STATUS    mandatory
    DESCRIPTION
        "
        General information of network interface.
        "
    INDEX  { kmNetGeneralIndex }
    ::= { kmNetGeneralTable 1 }

    KmNetGeneralEntry ::= SEQUENCE {
        kmNetGeneralIndex       INTEGER,
        kmNetFirmVersion        OCTET STRING,
        kmNetHardwareAddress    PhysAddress,
        kmNetSerialNumber       OCTET STRING,
        kmNetSpeedConfig        INTEGER,
        kmNetTimeout            INTEGER
        }

kmNetGeneralIndex  OBJECT-TYPE
    SYNTAX     INTEGER
    ACCESS     read-only
    STATUS     mandatory
    DESCRIPTION
           "
            Index for showing NetworkInterface installed to a device. 
            Basically, it shall take the same value with ifIndex. 
           "
       ::= { kmNetGeneralEntry 1 }

kmNetFirmVersion  OBJECT-TYPE
    SYNTAX    OCTET STRING(SIZE(0..7))
    ACCESS    read-only
    STATUS    mandatory
    DESCRIPTION
        "
         Shows the FW version of NetworkInterface. 
         Write it as ##.xx.
         ## shall be a major version and xx shall
         be a minor version.
         If there is no original FW of NetworkInterface, 
         implement character strings of '-' (hyphen).
        "
    ::= { kmNetGeneralEntry 2 }

kmNetHardwareAddress  OBJECT-TYPE
    SYNTAX    PhysAddress
    ACCESS    read-write
    STATUS    mandatory
    DESCRIPTION
        "
         MAC address of NetworkInterface. (Hardware address)
         In the device of our company, it was made into RW since 
         MAC address needs to be written at the time of shipment.
         Implement as RO when the writing of MAC address is unnecessary.
         Moreover, in a management tool side, be sure to handle it as RO.
        "
    ::= { kmNetGeneralEntry 3 }

kmNetSerialNumber  OBJECT-TYPE
    SYNTAX    OCTET STRING(SIZE(0..15))
    ACCESS    read-write
    STATUS    mandatory
    DESCRIPTION
        "
         The serial number of NetworkInterface.
         Implement '-' (hyphen) in the device without a serial number.
         In the device of our company, it was made into RW since serial 
         number may need to be written at the time of shipment.
         Implement as RO when the writing of serial number is unnecessary.
         Moreover, in a management tool side, be sure to handle it as RO.
        "
    ::= { kmNetGeneralEntry 4 }

kmNetSpeedConfig  OBJECT-TYPE
    SYNTAX    INTEGER {
                 other (0),
                 autoDetectEther (1),
                 et10MbpsHalfDuplex (2),
                 et10MbpsFullDuplex (3),
                 et100MbpsHalfDuplex (4),
                 et100MbpsFullDuplex (5),
                 etGbpsHalfDuplex (6),
                 etGbpsFullDuplex (7),

                 autoDetectToken (10),
                 tr4Mbps (11),
                 tr16Mbps (12),
                 tr32Mbps (13),

                 autoDetectWireless (20),
                 wireless1Mbps (21),
                 wireless2Mbps (22),
                 wireless5-5Mbps (23),
                 wireless11Mbps (24),
                 wireless54Mbps (25)
              }
    ACCESS    read-write
    STATUS    mandatory
    DESCRIPTION
        "
         Sets up the speed of NetworkInterface. 
         Refer to ifSpeed for checking the present speed of operation.

         If this setting can not be set from Network access, a device
         should implement a current set value with RO access.
        "
    ::= { kmNetGeneralEntry 7 }

kmNetTimeout  OBJECT-TYPE
    SYNTAX    INTEGER
    ACCESS    read-write
    STATUS    optional
    DESCRIPTION
        "
        The setting of network interface time out.
        Setting range depends device specification.
        Unit is seconds.

        In unified specification, range is 10 to 300, 
        default value is 15.

        If a device cannot support this function,
        This value must be -1 as RO.
        "
    ::= { kmNetGeneralEntry 8 }


-- kmNetProtocol Group

-- The information of Network Protocol that 
-- NetworkInterface has is included.

kmNetProtocolTable  OBJECT-TYPE
    SYNTAX    SEQUENCE OF KmNetProtocolEntry
    ACCESS    not-accessible
    STATUS    mandatory
    DESCRIPTION
        "
         The table for showing the protocol information 
         which NetworkInterface supports. 
        "
    ::= { kmNetProtocol 1 }

kmNetProtocolEntry OBJECT-TYPE
    SYNTAX    KmNetProtocolEntry
    ACCESS    not-accessible
    STATUS    mandatory
    DESCRIPTION
        "
         The information of protocol.
        "
    INDEX  { kmNetProtocolIfIndex, kmNetProtocolIndex }
    ::= { kmNetProtocolTable 1 }

    KmNetProtocolEntry ::= SEQUENCE {
        kmNetProtocolIfIndex   INTEGER,
        kmNetProtocolIndex     INTEGER,
        kmNetProtocolType      INTEGER,
        kmNetProtocolDescr     OCTET STRING,
        kmNetProtocolVer       OCTET STRING,
        kmNetProtocolOnOff     INTEGER
        }

kmNetProtocolIfIndex  OBJECT-TYPE
    SYNTAX     INTEGER
    ACCESS     read-only
    STATUS     mandatory
    DESCRIPTION
           "
            Index for showing NetworkInterface that a system has. 
            The value of index shall be the same value with 
            kmNetGeneralIndex (ifIndex).
           "
       ::= { kmNetProtocolEntry 1 }

kmNetProtocolIndex  OBJECT-TYPE
    SYNTAX     INTEGER
    ACCESS     read-only
    STATUS     mandatory
    DESCRIPTION
           "
            Index for uniquely showing the protocol which
            a system supports. Index shall be assigned in 
            the following order is recommended.

            No. Protocol
            --------------------
            1   TCP/IP
            2   NetWare(IPX/SPX)
            3   AppleTalk
            4   SMB

           "
       ::= { kmNetProtocolEntry 2 }

kmNetProtocolType  OBJECT-TYPE
    SYNTAX    INTEGER {
                unknown (0),
                tcp-ip  (1),
                netWare (2),
                appleTalk (3),
                smb     (4),
                other   (7)
              }
    ACCESS    read-only
    STATUS    mandatory
    DESCRIPTION
        "
         Shows the type of supporting protocol. 
        "
    ::= { kmNetProtocolEntry 3 }

kmNetProtocolDescr  OBJECT-TYPE
    SYNTAX   OCTET STRING (SIZE(0..15))
    ACCESS   read-only
    STATUS     mandatory
    DESCRIPTION
        "
         Description that shows a protocol. 
         Although the value to indicate shall depend on 
         an implementation, the general protocol name, 
         such as 'TCP/IP', 'NetWare', etc., shall be indicated 
         in principle. Implementation of Null is not accepted.
        "
    ::= { kmNetProtocolEntry 4 }

kmNetProtocolVer  OBJECT-TYPE
    SYNTAX  OCTET STRING (SIZE(0..15))
    ACCESS  read-only
    STATUS  mandatory
    DESCRIPTION
        "
         The version of the implemented protocol stack. 
         Implement '-' (hyphen) when there is no version notation. 
         Implementation of Null is not accepted.
        "
    ::= { kmNetProtocolEntry 5 }

kmNetProtocolOnOff  OBJECT-TYPE
    SYNTAX  INTEGER {
            notSupported (0),
            enable (1),
            disable (2)
            }  
    ACCESS  read-write
    STATUS  mandatory
    DESCRIPTION
        "
         Sets up a states display of On and Off of 
         the function of each protocol. 
         If this setting can not be set from Network access, 
         a device should implement a current set value with RO access.
        "
    ::= { kmNetProtocolEntry 6 }


-- kmNetCommand Group

-- The various command information which 
-- NetworkInterface has is included.

kmNetCommandTable  OBJECT-TYPE
    SYNTAX    SEQUENCE OF KmNetCommandEntry
    ACCESS    not-accessible
    STATUS    mandatory
    DESCRIPTION
        "
         The table for showing the command information 
         which NetworkInterface supports. 
        "
    ::= { kmNetCommand 1 }

kmNetCommandEntry OBJECT-TYPE
    SYNTAX    KmNetCommandEntry
    ACCESS    not-accessible
    STATUS    mandatory
    DESCRIPTION
        "
         The information of command for network interface.
        "
    INDEX  { kmNetCommandIfIndex }
    ::= { kmNetCommandTable  1 }

    KmNetCommandEntry ::= SEQUENCE {
        kmNetCommandIfIndex        INTEGER,
        kmNetCommandReset          INTEGER,
        kmNetCommandDefault        INTEGER
        }

kmNetCommandIfIndex  OBJECT-TYPE
    SYNTAX     INTEGER
    ACCESS     read-only
    STATUS     mandatory
    DESCRIPTION
        "
         Index for uniquely showing the destination of command. 
         The value of index shall be the same value with 
         kmNetGeneralIndex (ifIndex).
        "
    ::= { kmNetCommandEntry 1 }

kmNetCommandReset  OBJECT-TYPE
    SYNTAX    INTEGER {
                notSupported (0),
                supported (1),
                reset (2)
               }
    ACCESS    read-write
    STATUS    mandatory
    DESCRIPTION
        "
         The command that performs independent reset of 
         NetworkInterface. 

         When reset(2) is set, an agent side shall surely 
         return Reply. Implementation that performs Reset 
         immediately without returning Reply is not accepted. 
         Return Reply of an error, when Reset command is invalid.
         After reset(2) is set, about the timing which is 
         actually performing Reset depends on an implementation, 
         and it shall not be defined in MIB.
        "
    ::= { kmNetCommandEntry 2 }

kmNetCommandDefault  OBJECT-TYPE
    SYNTAX    INTEGER {
                notSupported (0),
                supported (1),
                resetToDefault (2)
              }
    ACCESS    read-write
    STATUS    mandatory
    DESCRIPTION
        "
         The command for returning a setup about 
         NetworkInterface to FactoryDefault. 

         When resetToDefault(2) is set, an agent side 
         shall surely return Reply.
         In principle, when resetToDefault(2) is set, 
         about the timing in which the setup returns to 
         default depends on an implementation and it does 
         not define in MIB.
        "
    ::= { kmNetCommandEntry 3 }

--  kmNetSnmp Group

-- SNMP related information that NetworkInterface has is included.

kmNetSnmpCommTable  OBJECT-TYPE
    SYNTAX    SEQUENCE OF KmNetSnmpCommEntry
    ACCESS    not-accessible
    STATUS    mandatory
    DESCRIPTION
        "
         The table for showing the information of Community 
         of SNMP which a system has. 
        
         In addition, Community name shall be the common to 
         the whole system on the premise, and shall not have 
         independent Community for every NetworkInterface.
         In having Community independently by Intelligent NIC etc., 
         it shall have NetworkMIB independently to each and is not 
         managed by unified agent.
        "
    ::= { kmNetSnmp 1 }

kmNetSnmpCommEntry OBJECT-TYPE
    SYNTAX    KmNetSnmpCommEntry
    ACCESS    not-accessible
    STATUS    mandatory
    DESCRIPTION
        "
        "
    INDEX  { kmNetSnmpCommIndex }
    ::= { kmNetSnmpCommTable 1 }

    KmNetSnmpCommEntry ::= SEQUENCE {
        kmNetSnmpCommIndex         INTEGER,
        kmNetSnmpCommName          DisplayString,
        kmNetSnmpCommAccessRight   INTEGER
    }

kmNetSnmpCommIndex  OBJECT-TYPE
    SYNTAX     INTEGER
    ACCESS     read-only
    STATUS     mandatory
    DESCRIPTION
       "
        Index for identifying each SNMP community.
        Although about Community number to support, 
        Community name, and each access rights are 
        dependent on an implementation.
        In default, following three Communities is recommended.
        
        public (RO)
        private (RW)
        admin (RW)

        It shall be indispensable at least to have 
        public (RW) or to have the two of public (RO) 
        and private (RW).
       "
       ::= { kmNetSnmpCommEntry 1 }

kmNetSnmpCommName  OBJECT-TYPE
    SYNTAX    DisplayString(SIZE(1..15))
    ACCESS    read-write
    STATUS    mandatory
    DESCRIPTION
        "
         Community name of SNMP. Having the above-mentioned 
         name as default is recommended. This item does not 
         accept the implementation of RO. Community name has 
         to be changeable.

         But if Community name can not be changeable, 
         'public' or 'private' is recommended to be implemented 
         as Community name with RO access.
        "
    ::= { kmNetSnmpCommEntry 2 }

kmNetSnmpCommAccessRight  OBJECT-TYPE
    SYNTAX    INTEGER {
                none (0),
                readOnly (1),
                writeOnly (2),
                readWrite (3)
              }
    ACCESS    read-write
    STATUS    mandatory
    DESCRIPTION
        "
        Shows the access rights of SNMP community. 
        If this setting can not be set from Network access, 
        a device should implement a current set value with RO access.
        "
    ::= { kmNetSnmpCommEntry 3 }


-- SNMP Trap Group

kmNetSnmpTrapGroup    OBJECT IDENTIFIER ::= { kmNetSnmp 2 }


kmNetSnmpTrapOnOff  OBJECT-TYPE
    SYNTAX  INTEGER {
            notSupported (0), -- This value is not used.
            enable (1),
            disable (2)
            }  
    ACCESS  read-write
    STATUS  optional
    DESCRIPTION
        "
         Sets up a SNMP trap function On and Off. 
        "
    ::= { kmNetSnmpTrapGroup 1 }

kmNetSnmpAuthFailureOnOff  OBJECT-TYPE
    SYNTAX  INTEGER {
            notSupported (0), -- This value is not used.
            enable (1),
            disable (2)
            }  
    ACCESS  read-write
    STATUS  optional
    DESCRIPTION
        "
         Sets up a SNMP authentication failure trap function On and Off. 
        "
    ::= { kmNetSnmpTrapGroup 2 }

kmNetSnmpTrapUdpDestTable  OBJECT-TYPE
    SYNTAX    SEQUENCE OF KmNetSnmpTrapUdpDestEntry
    ACCESS    not-accessible
    STATUS    optional
    DESCRIPTION
        "
         The table for showing the information of Trap destination
         by UDP. 
        "
    ::= { kmNetSnmpTrapGroup 3 }

kmNetSnmpTrapUdpDestEntry OBJECT-TYPE
    SYNTAX    KmNetSnmpTrapUdpDestEntry
    ACCESS    not-accessible
    STATUS    optional
    DESCRIPTION
        "
        "
    INDEX  { kmNetSnmpTrapUdpIfIndex, kmNetSnmpTrapUdpIndex }
    ::= { kmNetSnmpTrapUdpDestTable 1 }

    KmNetSnmpTrapUdpDestEntry ::= SEQUENCE {
      kmNetSnmpTrapUdpIfIndex    INTEGER,
      kmNetSnmpTrapUdpIndex      INTEGER,
      kmNetSnmpTrapUdpCommunity  DisplayString,
      kmNetSnmpTrapUdpAddress    DisplayString,
      kmNetSnmpTrapUdpPort       INTEGER
      }

kmNetSnmpTrapUdpIfIndex  OBJECT-TYPE
    SYNTAX     INTEGER
    ACCESS     read-only
    STATUS     optional
    DESCRIPTION
       "
        Index for uniquely showing NetworkInterface which SNMP Trap
        destination by UDP is set up.
        The value of index shall be the same value with 
         kmNetGeneralIndex (ifIndex).
       "
       ::= { kmNetSnmpTrapUdpDestEntry 1 }

kmNetSnmpTrapUdpIndex  OBJECT-TYPE
    SYNTAX     INTEGER
    ACCESS     read-only
    STATUS     optional
    DESCRIPTION
       "
        Index for identifying each SNMP destination 
        by UDP.
       "
       ::= { kmNetSnmpTrapUdpDestEntry 2 }

kmNetSnmpTrapUdpCommunity  OBJECT-TYPE
    SYNTAX    DisplayString(SIZE(0..15))
    ACCESS    read-write
    STATUS    optional
    DESCRIPTION
        "
         Community name of SNMP Trap by UDP. 
         Default value is dependent on implementation.
         When this value is not configured, 'Null' is aceptable.
         In case of 'Null', Trap should not be send.
        "
    ::= { kmNetSnmpTrapUdpDestEntry 3 }

kmNetSnmpTrapUdpAddress  OBJECT-TYPE
    SYNTAX    DisplayString(SIZE(0..255))
    ACCESS    read-write
    STATUS    optional
    DESCRIPTION
        "
         IP address or Host name of Trap Destination.

         Default should be null.
        "
    ::= { kmNetSnmpTrapUdpDestEntry 4 }

kmNetSnmpTrapUdpPort  OBJECT-TYPE
    SYNTAX     INTEGER
    ACCESS     read-write
    STATUS     optional
    DESCRIPTION
        "
        Port number of Trap destination.
        Default value is 162.
        "
       ::= { kmNetSnmpTrapUdpDestEntry 5 }


kmNetSnmpTrapIpxDestTable  OBJECT-TYPE
    SYNTAX    SEQUENCE OF KmNetSnmpTrapIpxDestEntry
    ACCESS    not-accessible
    STATUS    optional
    DESCRIPTION
        "
         The table for showing the information of Trap destination
         by IPX. 
        "
    ::= { kmNetSnmpTrapGroup 4 }

kmNetSnmpTrapIpxDestEntry OBJECT-TYPE
    SYNTAX    KmNetSnmpTrapIpxDestEntry
    ACCESS    not-accessible
    STATUS    optional
    DESCRIPTION
        "
        "
    INDEX  { kmNetSnmpTrapIpxIfIndex, kmNetSnmpTrapIpxIndex }
    ::= { kmNetSnmpTrapIpxDestTable 1 }

    KmNetSnmpTrapIpxDestEntry ::= SEQUENCE {
      kmNetSnmpTrapIpxIfIndex      INTEGER,
      kmNetSnmpTrapIpxIndex        INTEGER,
      kmNetSnmpTrapIpxCommunity    DisplayString,
      kmNetSnmpTrapIpxNetAddress   OCTET STRING,
      kmNetSnmpTrapIpxNodeAddress  PhysAddress
      }


kmNetSnmpTrapIpxIfIndex  OBJECT-TYPE
    SYNTAX     INTEGER
    ACCESS     read-only
    STATUS     optional
    DESCRIPTION
       "
        Index for uniquely showing NetworkInterface which SNMP Trap
        destination by IPX is set up.
        The value of index shall be the same value with 
         kmNetGeneralIndex (ifIndex).
       "
       ::= { kmNetSnmpTrapIpxDestEntry 1 }

kmNetSnmpTrapIpxIndex  OBJECT-TYPE
    SYNTAX     INTEGER
    ACCESS     read-only
    STATUS     optional
    DESCRIPTION
       "
        Index for identifying each SNMP destination 
        by IPX.
       "
       ::= { kmNetSnmpTrapIpxDestEntry 2 }

kmNetSnmpTrapIpxCommunity  OBJECT-TYPE
    SYNTAX    DisplayString(SIZE(0..15))
    ACCESS    read-write
    STATUS    optional
    DESCRIPTION
        "
         Community name of SNMP Trap by IPX. 
         Default value is dependent on implementation.
         When this value is not configured, 'Null' is aceptable.
         In case of 'Null', Trap should not be send.
        "
    ::= { kmNetSnmpTrapIpxDestEntry 3 }

kmNetSnmpTrapIpxNetAddress  OBJECT-TYPE
    SYNTAX    OCTET STRING(SIZE(0..4))
    ACCESS    read-write
    STATUS    optional
    DESCRIPTION
        "
         IPX Network address of Trap Destination.
         Default should be '00 00 00 00'.
        "
    ::= { kmNetSnmpTrapIpxDestEntry 4 }

kmNetSnmpTrapIpxNodeAddress  OBJECT-TYPE
    SYNTAX     PhysAddress
    ACCESS     read-write
    STATUS     optional
    DESCRIPTION
        "
        IPX node address of Trap destination.
        Default value is '00:00:00:00:00:00'.
        "
       ::= { kmNetSnmpTrapIpxDestEntry 5 }

-- kmNetSnmpv3 Group

kmNetSnmpMode  OBJECT-TYPE
    SYNTAX    INTEGER
    ACCESS    read-write
    STATUS    optional --Conditionally Mandatory
    DESCRIPTION
        "
        Set up mode of snmp operation is expressed
        with Bitmap.

         Bit    Value     Mode
         ---    -----    --------------- 
           0       1      SNMPv1/v2 Enable
           1       2        SNMPv1v2 ReadOnly Enable
           2       4        SNMPv1v2 ReadWrite Enable
           3       8      Reserved
           4      16      SNMPv3 Enable
           5      32        DiscoveryAccess Enable
           6      64      Reserved
           7     128      Reserved

        "
    ::= { kmNetSnmp 3 }


kmNetSnmpV3   OBJECT IDENTIFIER ::= { kmNetSnmp 4 }


kmNetSnmpV3DiscoveryUser  OBJECT-TYPE
    SYNTAX    DisplayString(SIZE(1..32))
    ACCESS    read-write
    STATUS    optional --Conditionally Mandatory
    DESCRIPTION
        "
         User name for discovery.
        "
       ::= { kmNetSnmpV3 1 }

kmNetSnmpV3UserTable  OBJECT-TYPE
    SYNTAX    SEQUENCE OF KmNetSnmpV3UserEntry
    ACCESS    not-accessible
    STATUS    optional --Conditionally Mandatory
    DESCRIPTION
        "
         This table shows SNMPv3 user information.
        "
       ::= { kmNetSnmpV3 2 }

kmNetSnmpV3UserEntry OBJECT-TYPE
    SYNTAX    KmNetSnmpV3UserEntry
    ACCESS    not-accessible
    STATUS    optional --Conditionally Mandatory
    DESCRIPTION
        "
        "
    INDEX { kmNetSnmpV3UserIndex }
       ::= { kmNetSnmpV3UserTable 1 }

    KmNetSnmpV3UserEntry ::= SEQUENCE {
        kmNetSnmpV3UserIndex           INTEGER,
        kmNetSnmpV3UserName            DisplayString,
        kmNetSnmpV3UserAuthPasswd      DisplayString,
        kmNetSnmpV3UserPrivPasswd      DisplayString,
        kmNetSnmpV3UserSecurityLevel   INTEGER,
        kmNetSnmpV3UserAccessRight     INTEGER
    }

kmNetSnmpV3UserIndex  OBJECT-TYPE
    SYNTAX    INTEGER
    ACCESS    read-only
    STATUS    optional --Conditionally Mandatory
    DESCRIPTION
        "
        Index for SNMPv3 user.
        "
       ::= { kmNetSnmpV3UserEntry 1 }

kmNetSnmpV3UserName  OBJECT-TYPE
    SYNTAX    DisplayString(SIZE(0..32))
    ACCESS    read-write
    STATUS    optional --Conditionally Mandatory
    DESCRIPTION
        "
          User name of SNMPv3.
        "
       ::= { kmNetSnmpV3UserEntry 2 }

kmNetSnmpV3UserAuthPasswd  OBJECT-TYPE
    SYNTAX    DisplayString(SIZE(0..32))
    ACCESS    read-write
    STATUS    optional --Conditionally Mandatory
    DESCRIPTION
        "
         Though a ture size is 0, 8..32.
         Because the Error of Compiler is generated,
         it is assumed of 0..32.
         Authentication password of SNMPv3.

         This object is defined as ReadWrite,
         but GetResponse should return null string or 
         implementation as WriteOnly.
        "
       ::= { kmNetSnmpV3UserEntry 3 }

kmNetSnmpV3UserPrivPasswd  OBJECT-TYPE
    SYNTAX    DisplayString(SIZE(0..32))
    ACCESS    read-write
    STATUS    optional --Conditionally Mandatory
    DESCRIPTION
        "
         Though a ture size is 0, 8..32.
         Because the Error of Compiler is generated,
         it is assumed of 0..32.
         Privacy password of SNMPv3.
         This object is defined as ReadWrite,
         but GetResponse should return null string or 
         implementation as WriteOnly.
        "
       ::= { kmNetSnmpV3UserEntry 4 }

kmNetSnmpV3UserSecurityLevel OBJECT-TYPE
    SYNTAX    INTEGER {
                 noAuthNoPriv (1),
                 authNoPriv (2),
                 authPriv (3)
                 }
    ACCESS    read-write
    STATUS    optional --Conditionally Mandatory
    DESCRIPTION
        "
         Security level of SNMPv3.
        "
       ::= { kmNetSnmpV3UserEntry 5 }

kmNetSnmpV3UserAccessRight  OBJECT-TYPE
    SYNTAX    INTEGER {
                none (0),
                readOnly (1),
                writeOnly (2),
                readWrite (3)
              }
    ACCESS    read-write
    STATUS    mandatory
    DESCRIPTION
        "
         Access right of SNMPv3.
        "
    ::= { kmNetSnmpV3UserEntry 6 }


kmNetSnmpIpxMode  OBJECT-TYPE
    SYNTAX    INTEGER
    ACCESS    read-write
    STATUS    optional
    DESCRIPTION
        "
        SNMP versions over IPX.

         Bit    Value     Mode
         ---    -----    --------------- 
           0       1      SNMPv1 over IPX Enable
           1       2      SNMPv2 over IPX Enable
           2       4      SNMPv3 over IPX Enable
           3       8      Reserved


        "
    ::= { kmNetSnmp 5 }


-- kmNetTcpip Group

   kmNetTcpipGeneral   OBJECT IDENTIFIER ::= { kmNetTcpip 1 }
   kmNetLpd            OBJECT IDENTIFIER ::= { kmNetTcpip 2 }

   kmNetFtpd           OBJECT IDENTIFIER ::= { kmNetTcpip 6 }
   kmNetFtpClient      OBJECT IDENTIFIER ::= { kmNetTcpip 7 }
   kmNetHttpd          OBJECT IDENTIFIER ::= { kmNetTcpip 8 }

   kmNetPopClient      OBJECT IDENTIFIER ::= { kmNetTcpip 11 }
   kmNetSmtpd          OBJECT IDENTIFIER ::= { kmNetTcpip 12 }
   kmNetSmtpClient     OBJECT IDENTIFIER ::= { kmNetTcpip 13 }
   kmNetIpp            OBJECT IDENTIFIER ::= { kmNetTcpip 14 }

   kmNetSlp            OBJECT IDENTIFIER ::= { kmNetTcpip 17 }

   kmNetImap           OBJECT IDENTIFIER ::= { kmNetTcpip 19 }


-- kmNetTcpipGeneral Group

-- The general information of TCP/IP.
-- The following items shall be defined.
-- About IPv6, it shall not take into consideration by definition of MIB of 
-- this version. It shall be examined when the necessity for IPv6 support 
-- comes out.

kmNetTcpipGeneralTable  OBJECT-TYPE
    SYNTAX    SEQUENCE OF KmNetTcpipGeneralEntry
    ACCESS    not-accessible
    STATUS    mandatory
    DESCRIPTION
        "
         Table with the basic information of TCP/IP relation which
         NetworkInterface has. 
        "
    ::= { kmNetTcpipGeneral 1 }

kmNetTcpipGeneralEntry OBJECT-TYPE
    SYNTAX    KmNetTcpipGeneralEntry
    ACCESS    not-accessible
    STATUS    mandatory
    DESCRIPTION
        "
        "
    INDEX  { kmNetTcpipIfIndex }
    ::= { kmNetTcpipGeneralTable 1 }

    KmNetTcpipGeneralEntry ::= SEQUENCE {
        kmNetTcpipIfIndex              INTEGER,
        kmNetTcpipDefault              INTEGER,
        kmNetTcpipAddress              IpAddress,
        kmNetTcpipSubnet               IpAddress,
        kmNetTcpipGateway              IpAddress,
        kmNetTcpipUseBootProtocol      INTEGER,
        kmNetTcpipBootProtocolEnable   INTEGER,
        kmNetTcpipAddressServer        IpAddress,
        kmNetTcpipRawPortNumber        INTEGER,
        kmNetTcpipDnsSupport           INTEGER,
        kmNetTcpipDnsHostName          OCTET STRING,
        kmNetTcpipDnsDomainName        OCTET STRING
         }

kmNetTcpipIfIndex  OBJECT-TYPE
    SYNTAX     INTEGER
    ACCESS     read-only
    STATUS     mandatory
    DESCRIPTION
        "
         Index for uniquely showing NetworkInterface which IP address 
         is set up. The value of index shall be the same value with 
         kmNetGeneralIndex (ifIndex).
        "
       ::= { kmNetTcpipGeneralEntry 1 }

kmNetTcpipDefault  OBJECT-TYPE
    SYNTAX  INTEGER {
            notSupported (0),
            supported (1),
            resetToDefault (2)
            }  
    ACCESS  read-write
    STATUS  mandatory
    DESCRIPTION
        "
         The command that returns all setup about TCP/IP to FactoryDefault. 

         When resetToDefault(2) is set, an agent side shall surely 
         return Reply. In principle, when resetToDefault(2) is set, 
         about the timing in which the setup returns to default 
         depends on an implementation and it does not define in MIB.
        "
    ::= { kmNetTcpipGeneralEntry 2 }

kmNetTcpipAddress  OBJECT-TYPE
    SYNTAX    IpAddress
    ACCESS    read-write
    STATUS    mandatory
    DESCRIPTION
        "
         IP address of NetworkInterface.

         If this setting can not be set from Network access, 
         a device should implement this value with RO access.
        "
    ::= { kmNetTcpipGeneralEntry 3 }

kmNetTcpipSubnet  OBJECT-TYPE
    SYNTAX    IpAddress
    ACCESS    read-write
    STATUS    mandatory
    DESCRIPTION
        "
         Subnet mask of NetworkInterface.

         If this setting can not be set from Network access, 
         a device should implement this value with RO access.
        "
    ::= { kmNetTcpipGeneralEntry 4 }

kmNetTcpipGateway  OBJECT-TYPE
    SYNTAX    IpAddress
    ACCESS    read-write
    STATUS    mandatory
    DESCRIPTION
        "
         DefaultGateway of NetworkInterface.

         If this setting can not be set from Network access, 
         a device should implement this value with RO access.
        "
    ::= { kmNetTcpipGeneralEntry 5 }

kmNetTcpipUseBootProtocol  OBJECT-TYPE
    SYNTAX  INTEGER {
            neverUse (0),
            useWhenNoAddress (1),
            useEveryTime (2)
            }  
    ACCESS  read-write
    STATUS  mandatory
    DESCRIPTION
        "
         Specifies the IP address acquisition method of 
         NetworkInterface. 
         The value taken by default depends on the implementation 
         of a model.

         If this setting can not be set from Network access, 
         a device should implement this value with RO access.
        "
    ::= { kmNetTcpipGeneralEntry 6 }

kmNetTcpipBootProtocolEnable  OBJECT-TYPE
    SYNTAX     INTEGER
    ACCESS     read-write
    STATUS     mandatory
    DESCRIPTION
        "
         Bitmap for specifying BootProtocol used in order to determine 
         the IP address of NetworkInterface. The value that should have 
         by Default depends on the implementation of a model.
        
         An integer bitmap value specifying bootProtocols. 
         Each bit in the integer is defined as follows.

           bit   Value     Type
           ---   -----     ---------
            0       1      Arp & Ping
            1       2      RARP
            2       4      BootP
            3       8      DHCP
            4      16      AutoIP
        
         If this setting can not be set from Network access, 
         a device should implement this value with RO access.
        "
    ::= { kmNetTcpipGeneralEntry 7 }

kmNetTcpipAddressServer  OBJECT-TYPE
    SYNTAX    IpAddress
    ACCESS    read-only
    STATUS    mandatory
    DESCRIPTION
        "
        IP address of Server which offered IP address when 
        IP address was acquired by bootProtocol.
        When it is manually inputted or Address in NVRAM is used, 
        '0.0.0.0' shall be inputted for this value. 
        When IP address is offered with AutoIP configuration,
        this value should be same as kmNetTcpipAddress.
        This value shall be held even if turning a power supply off.
        "
    ::= { kmNetTcpipGeneralEntry 8}

kmNetTcpipRawPortNumber  OBJECT-TYPE
    SYNTAX     INTEGER
    ACCESS     read-write
    STATUS     mandatory
    DESCRIPTION
        "
        Port number for RAW socket printing.
        Default shall be '9100'.
        In addition, two or more RAW Port printings shall not be supported.

        If this setting can not be set from Network access, 
        a device should implement this value with RO access.
        "
       ::= { kmNetTcpipGeneralEntry 9 }

kmNetTcpipDnsSupport  OBJECT-TYPE
    SYNTAX  INTEGER {
            notSupported (0),
            use (1),
            noUse (2)
            }  
    ACCESS  read-write
    STATUS  mandatory
    DESCRIPTION
        "
        Sets up the availability of use of DNS. 
        The following value shall be used.
        When DNS is not being supported, always takes 0.
        When supporting, Default shall be noUse(2).

        If this setting can not be set from Network access, 
        a device should implement this value with RO access.
        "
    ::= { kmNetTcpipGeneralEntry 11 }

kmNetTcpipDnsHostName  OBJECT-TYPE
    SYNTAX    OCTET STRING(SIZE(1..63))
    ACCESS    read-write
    STATUS    mandatory
    DESCRIPTION
        "
        The host name of NetworkInterface used by DNS. 
        Default in the case of supporting DNS is implementation
        dependence.
        When DNS is not being supported, implement '-' (hyphen)
        and shall be RO.

        If this setting can not be set from Network access, 
        a device should implement this value with RO access.
        "
    ::= { kmNetTcpipGeneralEntry 12 }

kmNetTcpipDnsDomainName  OBJECT-TYPE
    SYNTAX    OCTET STRING(SIZE(0..253))
    ACCESS    read-write
    STATUS    mandatory
    DESCRIPTION
        "
        Domain name to which NetworkInterface used by DNS belongs. 
        Default in the case of supporting DNS is Null (size =0).
        When DNS is not being supported, implement '-' (hyphen) 
        and shall be RO.

        Although the maximum numbers of characters
        in which Set is possible is dependent on implementation, 
        Set be possible for at least 31 characters.

        If this setting can not be set from Network access, 
        a device should implement this value with RO access.
        "
    ::= { kmNetTcpipGeneralEntry 13 }


kmNetTcpipDnsTable  OBJECT-TYPE
    SYNTAX    SEQUENCE OF KmNetTcpipDnsEntry
    ACCESS    not-accessible
    STATUS    optional --Conditionally Mandatory
    DESCRIPTION
        "
        The table for showing DNS Server. 
        "
    ::= { kmNetTcpipGeneral 2 }

kmNetTcpipDnsEntry OBJECT-TYPE
    SYNTAX    KmNetTcpipDnsEntry
    ACCESS    not-accessible
    STATUS    optional --Conditionally Mandatory
    DESCRIPTION
        "
        "
    INDEX  { kmNetTcpipDnsIfIndex, kmNetTcpipDnsServerIndex }
    ::= { kmNetTcpipDnsTable 1 }

   KmNetTcpipDnsEntry ::= SEQUENCE {
        kmNetTcpipDnsIfIndex       INTEGER,
        kmNetTcpipDnsServerIndex   INTEGER,
        kmNetTcpipDnsServerAddress IpAddress
        }

kmNetTcpipDnsIfIndex  OBJECT-TYPE
    SYNTAX     INTEGER
    ACCESS     read-only
    STATUS     optional --Conditionally Mandatory
    DESCRIPTION
        "
        The index for uniquely showing NetworkInterface to which 
        IP address is set. The value of index shall be the same 
        value with kmNetGeneralIndex (ifIndex).
        "
       ::= { kmNetTcpipDnsEntry 1 }

kmNetTcpipDnsServerIndex  OBJECT-TYPE
    SYNTAX     INTEGER
    ACCESS     read-only
    STATUS     optional --Conditionally Mandatory
    DESCRIPTION
        "
        The index for uniquely showing each DNS Server. 
        It shall have at least one or more Indexes as Default. 
        The number of Indexes depends on an implementation.
        "
       ::= { kmNetTcpipDnsEntry 2 }

kmNetTcpipDnsServerAddress  OBJECT-TYPE
    SYNTAX    IpAddress
    ACCESS    read-write
    STATUS    optional --Conditionally Mandatory
    DESCRIPTION
        "
        IP address of DNS Server.

        If this setting can not be set from Network access, 
        a device should implement this value with RO access.
        "
       ::= { kmNetTcpipDnsEntry 3 }



kmNetIpVersion  OBJECT-TYPE
    SYNTAX   INTEGER
    ACCESS   read-write
    STATUS   optional --Conditionally Mandatory
    DESCRIPTION
        "
         This object shows supported ip version.
         Supported function is shown by following  Bitmap.
         
         Bit    Value     Function
         ---    -----    ---------------
          0        1      IPv4
          1        2      IPv6
          2        4      Reserved
          3        8      Reserved
        "
    ::= { kmNetTcpipGeneral 3 }



kmNetIpv6ConfigTable  OBJECT-TYPE
    SYNTAX    SEQUENCE OF KmNetIpv6ConfigEntry
    ACCESS    not-accessible
    STATUS    optional --Conditionally Mandatory
    DESCRIPTION
        "
        The table for showing IPv6.
        "
    ::= { kmNetTcpipGeneral 4 }

kmNetIpv6ConfigEntry OBJECT-TYPE
    SYNTAX    KmNetIpv6ConfigEntry
    ACCESS    not-accessible
    STATUS    optional --Conditionally Mandatory
    DESCRIPTION
        "
        "
    INDEX  { kmNetIpv6ConfigIfIndex }
    ::= { kmNetIpv6ConfigTable 1 }

   KmNetIpv6ConfigEntry ::= SEQUENCE {
        kmNetIpv6ConfigIfIndex    INTEGER,
        kmNetIpv6AutoConfig       INTEGER,
        kmNetIpv6GrobalAddress    Ipv6Address,
        kmNetIpv6LinkLocalAddress Ipv6Address,
        kmNetIpv6RouterAddress    Ipv6Address
        }

kmNetIpv6ConfigIfIndex  OBJECT-TYPE
    SYNTAX     INTEGER
    ACCESS     read-only
    STATUS     optional --Conditionally Mandatory
    DESCRIPTION
        "
        The index for uniquely showing NetworkInterface to which 
        IPv6 address is set. The value of index shall be the same 
        value with kmNetGeneralIndex (ifIndex).
        "
       ::= { kmNetIpv6ConfigEntry 1 }

kmNetIpv6AutoConfig  OBJECT-TYPE
    SYNTAX     INTEGER {
                notSupported (0),
                enable(1),
                disable(2)
               }
    ACCESS     read-write
    STATUS     optional --Conditionally Mandatory
    DESCRIPTION
        "
        Sets up the availability of auto setting of IPv6.
        
        If this setting can not be set from Network access, a device
         should implement a current set value with RO access.
        "
       ::= { kmNetIpv6ConfigEntry 2 }

kmNetIpv6GrobalAddress  OBJECT-TYPE
    SYNTAX    Ipv6Address
    ACCESS    read-write
    STATUS    optional --Conditionally Mandatory
    DESCRIPTION
        "
        Grobal Address of Interface in IPv6 is shown. 
        
        If kmNetIpv6AutoConfig is disable(2), device is possible to set this.
        however if kmNetIpv6AutoConfig is enable(1), device is return 
        the Error when this is set.

        If this setting can not be set from Network access, 
        a device should implement this value with RO access.
        "
       ::= { kmNetIpv6ConfigEntry 3 }

kmNetIpv6LinkLocalAddress  OBJECT-TYPE
    SYNTAX    Ipv6Address
    ACCESS    read-only
    STATUS    optional --Conditionally Mandatory
    DESCRIPTION
        "
        LinkLocal Address of Interface in IPv6 is shown. 
        "
       ::= { kmNetIpv6ConfigEntry 4 }

kmNetIpv6RouterAddress  OBJECT-TYPE
    SYNTAX    Ipv6Address
    ACCESS    read-write
    STATUS    optional --Conditionally Mandatory
    DESCRIPTION
        "
        Router Address of Interface in IPv6 is shown. 
        
        If kmNetIpv6AutoConfig is disable(2), device is possible to set this.
        however if kmNetIpv6AutoConfig is enable(1), device is return 
        the Error when this is set.

        If this setting can not be set from Network access, 
        a device should implement this value with RO access.
        "
       ::= { kmNetIpv6ConfigEntry 5 }


-- kmNetLpd Group

-- The information of LPD relation which NetworkInterface has is included. 
-- The following items shall be defined. 
-- When it does not have the function of LPD, 
-- it is not necessary to implement this Group.

kmNetLpdGeneralTable  OBJECT-TYPE
    SYNTAX    SEQUENCE OF KmNetLpdGeneralEntry
    ACCESS    not-accessible
    STATUS    optional --Conditionally Mandatory
    DESCRIPTION
        "
        The table for showing the general information of lpd. 
        "
    ::= { kmNetLpd 1 }
        
kmNetLpdGeneralEntry OBJECT-TYPE
    SYNTAX    KmNetLpdGeneralEntry
    ACCESS    not-accessible
    STATUS    optional --Conditionally Mandatory
    DESCRIPTION
        "
        "
    INDEX  { kmNetLpdIfIndex }
    ::= { kmNetLpdGeneralTable 1 }

   KmNetLpdGeneralEntry ::= SEQUENCE {
        kmNetLpdIfIndex    INTEGER,
        kmNetLpdEnable     INTEGER,
        kmNetLpdPort       INTEGER
        }

kmNetLpdIfIndex  OBJECT-TYPE
    SYNTAX     INTEGER
    ACCESS     read-only
    STATUS     optional --Conditionally Mandatory
    DESCRIPTION
        "
        The index for uniquely specifying NetworkInterface to 
        which lpd is set. 
        The value of index shall be the same value with 
        kmNetGeneralIndex (ifIndex).
        "
       ::= { kmNetLpdGeneralEntry 1 }

kmNetLpdEnable  OBJECT-TYPE
    SYNTAX  INTEGER {
            enable (1),
            disable (2)
            }  
    ACCESS  read-write
    STATUS  optional --Conditionally Mandatory
    DESCRIPTION
        "
        Sets up Enable/Disable of service of lpd.
        "
       ::= { kmNetLpdGeneralEntry 2 }

kmNetLpdPort  OBJECT-TYPE
    SYNTAX     INTEGER
    ACCESS     read-write
    STATUS     optional --Conditionally Mandatory
    DESCRIPTION
        "
        Specifies Port number which lpd uses. Default is 515.
        "
       ::= { kmNetLpdGeneralEntry 3 }

kmNetLpdQueueTable  OBJECT-TYPE
    SYNTAX    SEQUENCE OF KmNetLpdQueueEntry
    ACCESS    not-accessible
    STATUS    optional --Conditionally Mandatory
    DESCRIPTION
        "
        The table for showing the information of Queue of lpd. 
        "
    ::= { kmNetLpd 2 }

kmNetLpdQueueEntry OBJECT-TYPE
    SYNTAX    KmNetLpdQueueEntry
    ACCESS    not-accessible
    STATUS    optional --Conditionally Mandatory
    DESCRIPTION
        "
        "
    INDEX  { kmNetLpdQueueIfIndex, kmNetLpdQueueIndex }
    ::= { kmNetLpdQueueTable 1 }

   KmNetLpdQueueEntry ::= SEQUENCE {
        kmNetLpdQueueIfIndex   INTEGER,
        kmNetLpdQueueIndex     INTEGER,
        kmNetLpdQueueName      OCTET STRING,
        kmNetLpdQueueDescr     OCTET STRING,
        kmNetLpdQueueFilter    INTEGER,
        kmNetLpdQueueBanner    INTEGER,
        kmNetLpdQueueEnable    INTEGER
        }

kmNetLpdQueueIfIndex  OBJECT-TYPE
    SYNTAX     INTEGER
    ACCESS     read-only
    STATUS     optional --Conditionally Mandatory
    DESCRIPTION
        "
        The index for uniquely specifying NetworkInterface to 
        which each Queue is set. 
        The value of index shall be the same value with 
        kmNetGeneralIndex (ifIndex).
        "
       ::= { kmNetLpdQueueEntry 1 }

kmNetLpdQueueIndex  OBJECT-TYPE
    SYNTAX     INTEGER
    ACCESS     read-only
    STATUS     optional --Conditionally Mandatory
    DESCRIPTION
        "
        The index for uniquely showing Queue set up for 
        every NetworkInterface. 
        The number of Indexes depends on an implementation.
        "
       ::= { kmNetLpdQueueEntry 2 }

kmNetLpdQueueName  OBJECT-TYPE
    SYNTAX    OCTET STRING(SIZE(1..31))
    ACCESS    read-write
    STATUS    optional --Conditionally Mandatory
    DESCRIPTION
        "
        The name of Queue used at the time of printing by lpd. 
        The value of Default depends on a model. 
        Default shall be '-' (hyphen) when printing function 
        has no relation to the name of Queue.
        "
    ::= { kmNetLpdQueueEntry 3 }

kmNetLpdQueueDescr  OBJECT-TYPE
    SYNTAX    OCTET STRING(SIZE(0..31))
    ACCESS    read-write
    STATUS    optional --Conditionally Mandatory
    DESCRIPTION
        "
        It recommends describing the information which serves 
        as help when a user performs a setup for lpr printing.
        "
    ::= { kmNetLpdQueueEntry 4 }

kmNetLpdQueueFilter  OBJECT-TYPE
    SYNTAX     INTEGER
    ACCESS     read-write
    STATUS     optional --Conditionally Mandatory
    DESCRIPTION
        "
        Selects Filter function set as Queue by Bitmap. 
        When there is no Filter function in Queue, shall always be 0.
        
        Each bit in the integer is defined as follows.

            bit   Value     Filter
            ---   -----     ---------
             0       1      FF (Form Feed)
             1       2      LF (Line Feed)
             2       4      CR (Carriage Return)
             3       8      PS (Add PostScript Header)
             4      16        reserved
             5      32      rejectPS
             6      64      rejectPCL
             7     128      rejectASCII

        "
     ::= { kmNetLpdQueueEntry 5 }

kmNetLpdQueueBanner  OBJECT-TYPE
    SYNTAX  INTEGER {
            noBanner (0),
            ascii (1),
            pcl (2),
            ps (3)
            }  
    ACCESS  read-write
    STATUS  optional --Conditionally Mandatory
    DESCRIPTION
        "
        A setup of BannerPage set in Queue. 
        "
    ::= { kmNetLpdQueueEntry 6 }

kmNetLpdQueueEnable  OBJECT-TYPE
    SYNTAX  INTEGER {
            enable (1),
            disable (2)
            }  
    ACCESS  read-write
    STATUS  optional --Conditionally Mandatory
    DESCRIPTION
        "
        Sets up Enable/Disable of each Queue.
        "
       ::= { kmNetLpdQueueEntry 7 }


-- kmNetFtpd Group

-- The information on FTP Server relation which NetworkInterface has 
-- is included. The following items shall be defined. 
-- In the system without FTP Server function, 
-- it is not necessary to implement this Group.

kmNetFtpdGeneralTable  OBJECT-TYPE
    SYNTAX    SEQUENCE OF KmNetFtpdGeneralEntry
    ACCESS    not-accessible
    STATUS    optional --Conditionally Mandatory
    DESCRIPTION
        "
        The table for showing the general information of FTP Server. 
        "
    ::= { kmNetFtpd 1 }

kmNetFtpdGeneralEntry OBJECT-TYPE
    SYNTAX    KmNetFtpdGeneralEntry
    ACCESS    not-accessible
    STATUS    optional --Conditionally Mandatory
    DESCRIPTION
        "
        "
    INDEX  { kmNetFtpdIfIndex }
    ::= { kmNetFtpdGeneralTable 1 }

   KmNetFtpdGeneralEntry ::= SEQUENCE {
        kmNetFtpdIfIndex   INTEGER,
        kmNetFtpdEnable    INTEGER,
        kmNetFtpdPort      INTEGER
        }

kmNetFtpdIfIndex  OBJECT-TYPE
    SYNTAX     INTEGER
    ACCESS     read-only
    STATUS     optional --Conditionally Mandatory
    DESCRIPTION
        "
        The index for uniquely specifying NetworkInterface to 
        which FTP server is set up. The value of index shall 
        be the same value with kmNetGeneralIndex (ifIndex).
        "
       ::= { kmNetFtpdGeneralEntry 1 }

kmNetFtpdEnable  OBJECT-TYPE
    SYNTAX  INTEGER {
            enable (1),
            disable (2)
            }  
    ACCESS  read-write
    STATUS  optional --Conditionally Mandatory
    DESCRIPTION
        "
        Sets up Enable/Disable of service of FTP. 
        "
       ::= { kmNetFtpdGeneralEntry 2 }

kmNetFtpdPort  OBJECT-TYPE
    SYNTAX     INTEGER
    ACCESS     read-write
    STATUS     optional --Conditionally Mandatory
    DESCRIPTION
        "
        Specifies Port number which FTP Server uses. Default is 21.
        "
       ::= { kmNetFtpdGeneralEntry 3 }


-- kmNetFtpClient Group

-- The information of FTP Client relation which NetworkInterface 
-- has is included. 
-- The following items shall be defined. 
-- In the system without FTP Client function, 
-- it is not necessary to implement this Group.
-- About destination information, it shall not be the object of this MIB.


kmNetFtpClientGeneralTable  OBJECT-TYPE
    SYNTAX    SEQUENCE OF KmNetFtpClientGeneralEntry
    ACCESS    not-accessible
    STATUS    optional --Conditionally Mandatory
    DESCRIPTION
        "
        The table for showing the general information about FTP Client. 
        "
    ::= { kmNetFtpClient 1 }

kmNetFtpClientGeneralEntry OBJECT-TYPE
    SYNTAX    KmNetFtpClientGeneralEntry
    ACCESS    not-accessible
    STATUS    optional --Conditionally Mandatory
    DESCRIPTION
        "
        "
    INDEX  { kmNetFtpClientIfIndex }
    ::= { kmNetFtpClientGeneralTable 1 }

   KmNetFtpClientGeneralEntry ::= SEQUENCE {
        kmNetFtpClientIfIndex  INTEGER,
        kmNetFtpClientEnable   INTEGER,
        kmNetFtpProxyAddress   OCTET STRING,
        kmNetFtpProxyPort      INTEGER,
        kmNetFtpConnTimeout    INTEGER
       }

kmNetFtpClientIfIndex  OBJECT-TYPE
    SYNTAX     INTEGER
    ACCESS     read-only
    STATUS     optional --Conditionally Mandatory
    DESCRIPTION
        "
        Index for uniquely specifying NetworkInterface to 
        which FTP Client is set. 
        The value of index shall be the same value with 
        kmNetGeneralIndex (ifIndex).
        "
       ::= { kmNetFtpClientGeneralEntry 1 }

kmNetFtpClientEnable  OBJECT-TYPE
    SYNTAX  INTEGER {
            enable (1),
            disable (2)
            }  
    ACCESS  read-write
    STATUS  optional --Conditionally Mandatory
    DESCRIPTION
        "
        Enable/Disable of service of FTP Client is set up. 
        "
       ::= { kmNetFtpClientGeneralEntry 2 }

kmNetFtpProxyAddress  OBJECT-TYPE
    SYNTAX     OCTET STRING(SIZE(0..255))
    ACCESS     read-write
    STATUS     optional --Conditionally Mandatory
    DESCRIPTION
        "
        The address of Proxy Server which FTP Client uses. 
        For domain name assignment, syntax of this object is 
        string.
        The availability of use of Proxy is dependent on an address setup.
        Default is '0.0.0.0'.
        "
       ::= { kmNetFtpClientGeneralEntry 3 }

kmNetFtpProxyPort  OBJECT-TYPE
    SYNTAX     INTEGER
    ACCESS     read-write
    STATUS     optional --Conditionally Mandatory
    DESCRIPTION
        "
        The port number of Proxy which FTP Client uses. Default is 21.
        "
       ::= { kmNetFtpClientGeneralEntry 4 }

kmNetFtpConnTimeout  OBJECT-TYPE
    SYNTAX     INTEGER
    ACCESS     read-write
    STATUS     optional --Conditionally Mandatory
    DESCRIPTION
        "
        Timeout setup at the time of connection by FTP Client. 
        A unit is second. Default shall be 60 (seconds). 
        (It complies with a system standard specification)
        "
       ::= { kmNetFtpClientGeneralEntry 5 }


-- kmNetHttpd Group

-- The information of HTTP Server relation which 
-- NetworkInterface has is included. 
-- The following items shall be defined. 
-- In addition, in this item, the item of IPP 
-- relation shall not be the object.

kmNetHttpdGeneralTable  OBJECT-TYPE
    SYNTAX    SEQUENCE OF KmNetHttpdGeneralEntry
    ACCESS    not-accessible
    STATUS    mandatory
    DESCRIPTION
        "
        The table for showing the general information about HTTP Server. 
        "
    ::= { kmNetHttpd 1 }

kmNetHttpdGeneralEntry OBJECT-TYPE
    SYNTAX    KmNetHttpdGeneralEntry
    ACCESS    not-accessible
    STATUS    mandatory
    DESCRIPTION
        "
        "
    INDEX  { kmNetHttpdIfIndex }
    ::= { kmNetHttpdGeneralTable 1 }

   KmNetHttpdGeneralEntry ::= SEQUENCE {
        kmNetHttpdIfIndex       INTEGER,
        kmNetHttpdEnable        INTEGER,
        kmNetHttpdPort          INTEGER,
        kmNetHttpdDescr         OCTET STRING,
        kmNetHttpdOpenApiUri    OCTET STRING,
        kmNetHttpdOpenApiSslUri OCTET STRING
        }

kmNetHttpdIfIndex  OBJECT-TYPE
    SYNTAX     INTEGER
    ACCESS     read-only
    STATUS     mandatory
    DESCRIPTION
        "
        Index for uniquely showing NetworkInterface to 
        which HTTP Server is set up. 
        The value of index shall be the same value with 
        kmNetGeneralIndex (ifIndex).
        "
       ::= { kmNetHttpdGeneralEntry 1 }

kmNetHttpdEnable  OBJECT-TYPE
    SYNTAX  INTEGER {
            enable (1),
            disable (2)
            }  
    ACCESS  read-write
    STATUS  mandatory
    DESCRIPTION
        "
        Sets up Enable/Disable of service of HTTP Server. 
        "
       ::= { kmNetHttpdGeneralEntry 2 }

kmNetHttpdPort  OBJECT-TYPE
    SYNTAX     INTEGER
    ACCESS     read-write
    STATUS     mandatory
    DESCRIPTION
        "
        The port number which HTTP Server uses. Default is 80.
        "
       ::= { kmNetHttpdGeneralEntry 3 }

kmNetHttpdDescr  OBJECT-TYPE
    SYNTAX    OCTET STRING(SIZE(0..31))
    ACCESS    read-write
    STATUS    mandatory
    DESCRIPTION
        "
        Indicates the information, such as a version of HTTP Server.
        "
    ::= { kmNetHttpdGeneralEntry 4 }

kmNetHttpdOpenApiUri  OBJECT-TYPE
    SYNTAX    OCTET STRING(SIZE(0..63))
    ACCESS    read-only
    STATUS    mandatory
    DESCRIPTION
        "
        The information of IsOpenAPI URI.
        "
    ::= { kmNetHttpdGeneralEntry 5 }


kmNetHttpdOpenApiSslUri  OBJECT-TYPE
    SYNTAX    OCTET STRING(SIZE(0..63))
    ACCESS    read-only
    STATUS    mandatory
    DESCRIPTION
        "
        The information of IsOpenAPI URI for SSL connection.
        "
    ::= { kmNetHttpdGeneralEntry 6 }



-- kmNetPopClient Group

-- The information on POP3 relation which NetworkInterface 
-- has is included. 
-- In the system without a mail receiving function, 
-- it is not necessary to implement this Group.
-- In a definition of this MIB, it shall not take into 
-- consideration about the handling of the mail on the 
-- server after Download. About a detailed setup, 
-- it depends on an implementation.


kmNetPopGeneralTable  OBJECT-TYPE
    SYNTAX    SEQUENCE OF KmNetPopGeneralEntry
    ACCESS    not-accessible
    STATUS    optional --Conditionally Mandatory
    DESCRIPTION
        "
        The table for showing the general information of POP3. 
        "
    ::= { kmNetPopClient 1 }

kmNetPopGeneralEntry OBJECT-TYPE
    SYNTAX    KmNetPopGeneralEntry
    ACCESS    not-accessible
    STATUS    optional --Conditionally Mandatory
    DESCRIPTION
        "
        "
    INDEX  { kmNetPopIfIndex }
    ::= { kmNetPopGeneralTable 1 }


   KmNetPopGeneralEntry ::= SEQUENCE {
        kmNetPopIfIndex        INTEGER,
        kmNetPopEnable         INTEGER,
        kmNetPopServerAddress  OCTET STRING,
        kmNetPopPort           INTEGER,
        kmNetPopSslEnable      INTEGER,
        kmNetPopSslPort        INTEGER
         }

kmNetPopIfIndex  OBJECT-TYPE
    SYNTAX     INTEGER
    ACCESS     read-only
    STATUS     optional --Conditionally Mandatory
    DESCRIPTION
        "
        The index for uniquely specifying NetworkInterface to 
        which POP is set. 
        The value of Index shall be the same value with 
        kmNetGeneralIndex (ifIndex).
        "
       ::= { kmNetPopGeneralEntry 1 }

kmNetPopEnable  OBJECT-TYPE
    SYNTAX  INTEGER {
            enable (1),
            disable (2)
            }  
    ACCESS  read-write
    STATUS  optional --Conditionally Mandatory
    DESCRIPTION
        "
        Sets up Enable/Disable of service of POP.
        "
       ::= { kmNetPopGeneralEntry 2 }

kmNetPopServerAddress  OBJECT-TYPE
    SYNTAX    OCTET STRING(SIZE(0..255))
    ACCESS    read-write
    STATUS    optional --Conditionally Mandatory
    DESCRIPTION
        "
        Shows the address of POP Server. 
        Considering about specification by Domain name, 
        it is made into OCTET STRING.
        In the case of specifying by the IP address, 
        it shall be handled as a character string of maximum 
        15 characters of 'xxx.xxx.xxx.xxx'.
        Whether to accept a setup by Domain name is dependent 
        on an implementation of a model.
        "
       ::= { kmNetPopGeneralEntry 3 }

kmNetPopPort  OBJECT-TYPE
    SYNTAX     INTEGER
    ACCESS     read-write
    STATUS     optional --Conditionally Mandatory
    DESCRIPTION
        "
        Specifies Port number which POP uses. Default is 110.
        "
       ::= { kmNetPopGeneralEntry 4 }


kmNetPopSslEnable  OBJECT-TYPE
    SYNTAX  INTEGER {
            enable (1),
            disable (2)
            }  
    ACCESS  read-write
    STATUS  optional --Conditionally Mandatory
    DESCRIPTION
        "
        Sets up Enable/Disable of service of POP over SSL.
        Default value is disabel(2).

        If device has not this function (POP over SSL),
        this object must not be implemented.
        "
       ::= { kmNetPopGeneralEntry 5 }

kmNetPopSslPort  OBJECT-TYPE
    SYNTAX     INTEGER
    ACCESS     read-write
    STATUS     optional --Conditionally Mandatory
    DESCRIPTION
        "
        Specifies Port number which POP over SSL uses. Default is 995.

        If device has not this function (POP over SSL),
        this object must not be implemented.
        "
       ::= { kmNetPopGeneralEntry 6 }


-- kmNetSmtpd Group

-- The information of SMTP Server relation which NetworkInterface 
-- has is included. 
-- The following items shall be defined. 
-- This group is optional.
-- It is only supported when it is necessary in the system with 
-- the SMTP Server function. 
-- In this group, the setting of the user count in the SMTP Server function 
-- is not supported. 


kmNetSmtpdGeneralTable  OBJECT-TYPE
    SYNTAX    SEQUENCE OF KmNetSmtpdGeneralEntry
    ACCESS    not-accessible
    STATUS    optional
    DESCRIPTION
        "
        The table for showing the general information of SMTP Server. 
        "
    ::= { kmNetSmtpd 1 }

kmNetSmtpdGeneralEntry OBJECT-TYPE
    SYNTAX    KmNetSmtpdGeneralEntry
    ACCESS    not-accessible
    STATUS    optional
    DESCRIPTION
        "
        "
    INDEX  { kmNetSmtpdIfIndex }
    ::= { kmNetSmtpdGeneralTable 1 }

   KmNetSmtpdGeneralEntry ::= SEQUENCE {
        kmNetSmtpdIfIndex       INTEGER,
        kmNetSmtpdEnable        INTEGER,
        kmNetSmtpdPort          INTEGER,
        kmNetSmtpdTimeout       INTEGER,
        kmNetSmtpdMaxMailSize   INTEGER,
        kmNetSmtpdMaxSpoolSize  INTEGER
        }

kmNetSmtpdIfIndex  OBJECT-TYPE
    SYNTAX     INTEGER
    ACCESS     read-only
    STATUS     optional
    DESCRIPTION
        "
        The index for uniquely specifying NetworkInterface to 
        which SMTP Server is set. 
        The value of Index shall be the same value with 
        kmNetGeneralIndex (ifIndex).
        "
       ::= { kmNetSmtpdGeneralEntry 1 }

kmNetSmtpdEnable  OBJECT-TYPE
    SYNTAX     INTEGER{
                enable (1),
                disable (2)
               }
    ACCESS     read-write
    STATUS     optional
    DESCRIPTION
        "
        Sets up Enable/Disable of service of SMTP Server. 
        "
       ::= { kmNetSmtpdGeneralEntry 2 }

kmNetSmtpdPort  OBJECT-TYPE
    SYNTAX     INTEGER
    ACCESS     read-write
    STATUS     optional
    DESCRIPTION
        "
        Specifies Port number which SMTP Server uses. Default is 25.
        "
       ::= { kmNetSmtpdGeneralEntry 3 }

kmNetSmtpdTimeout  OBJECT-TYPE
    SYNTAX     INTEGER
    ACCESS     read-write
    STATUS     optional
    DESCRIPTION
        "
        Shows the setting of timeout in SMTP Server when connecting the client.
        This timeout has the following two meanings.
         1. Standby time until the next command after response to client.
         2. Timeout of transmission and reception.
        Unit is seconds.
        This setting range is 5 to 1000.
        Default value is 300(seconds).
        If this setting can not set, a device should implement this value 
        with RO access.
        "
       ::= { kmNetSmtpdGeneralEntry 4 }


kmNetSmtpdMaxMailSize  OBJECT-TYPE
    SYNTAX     INTEGER
    ACCESS     read-write
    STATUS     optional
    DESCRIPTION
        "
        Show the maximum size of the message that can be received 
        in SMTP Server.
        The maximum size shows the size after it encodes with BASE64.
        Unit is MB.
        This setting range and default value depend on a device.
        "
       ::= { kmNetSmtpdGeneralEntry 5 }

kmNetSmtpdMaxSpoolSize  OBJECT-TYPE
    SYNTAX     INTEGER
    ACCESS     read-write
    STATUS     optional
    DESCRIPTION
        "
        Show the maximum size of spool capacity that can be received 
        in SMTP Server.
        Unit is MB.
        This setting range and default value depend on a device.
        "
       ::= { kmNetSmtpdGeneralEntry 6 }



-- kmNetSmtpClient Group

-- The information of SMTP relation which NetworkInterface has is included. 
-- The following items shall be defined. 
-- In the system without a mail transmitting function, 
-- it is not necessary to implement this Group.
-- In a definition of this MIB, it considers as the outside of an object 
-- about address information


kmNetSmtpGeneralTable  OBJECT-TYPE
    SYNTAX    SEQUENCE OF KmNetSmtpGeneralEntry
    ACCESS    not-accessible
    STATUS    optional --Conditionally Mandatory
    DESCRIPTION
        "
        The table for showing the general information of SMTP. 
        "
    ::= { kmNetSmtpClient 1 }

kmNetSmtpGeneralEntry OBJECT-TYPE
    SYNTAX    KmNetSmtpGeneralEntry
    ACCESS    not-accessible
    STATUS    optional --Conditionally Mandatory
    DESCRIPTION
        "
        "
    INDEX  { kmNetSmtpIfIndex }
    ::= { kmNetSmtpGeneralTable 1 }

   KmNetSmtpGeneralEntry ::= SEQUENCE {
        kmNetSmtpIfIndex       INTEGER,
        kmNetSmtpEnable        INTEGER,
        kmNetSmtpServerAddress OCTET STRING,
        kmNetSmtpPort          INTEGER,
        kmNetSmtpSslEnable     INTEGER,
        kmNetSmtpSslPort       INTEGER
        }

kmNetSmtpIfIndex  OBJECT-TYPE
    SYNTAX     INTEGER
    ACCESS     read-only
    STATUS     optional --Conditionally Mandatory
    DESCRIPTION
        "
        The index for uniquely specifying NetworkInterface to 
        which SMTP is set. 
        The value of Index shall be the same value with 
        kmNetGeneralIndex (ifIndex).
        "
       ::= { kmNetSmtpGeneralEntry 1 }

kmNetSmtpEnable  OBJECT-TYPE
    SYNTAX     INTEGER{
            enable (1),
            disable (2)
            }  
    ACCESS     read-write
    STATUS     optional --Conditionally Mandatory
    DESCRIPTION
        "
        Sets up Enable/Disable of service of SMTP. 
        "
       ::= { kmNetSmtpGeneralEntry 2 }

kmNetSmtpServerAddress  OBJECT-TYPE
    SYNTAX     OCTET STRING(SIZE(0..63))
    ACCESS     read-only
    STATUS     optional --Conditionally Mandatory
    DESCRIPTION
        "
        Shows the IP address of SMTP Server. 
        Considering about specification by Domain name, 
        it is made into OCTET STRING.
        In the case of specifying by the IP address, 
        it shall be handled as a character string of maximum 15 
        characters of 'xxx.xxx.xxx.xxx'.
        Whether to accept a setup by Domain name is dependent 
        on an implementation of a model.
        "
       ::= { kmNetSmtpGeneralEntry 3 }

kmNetSmtpPort  OBJECT-TYPE
    SYNTAX     INTEGER
    ACCESS     read-only
    STATUS     optional --Conditionally Mandatory
    DESCRIPTION
        "
        Specifies Port number which SMTP uses. Default is 25.
        "
       ::= { kmNetSmtpGeneralEntry 4 }

kmNetSmtpSslEnable  OBJECT-TYPE
    SYNTAX     INTEGER{
            enable (1),
            disable (2)
            }  
    ACCESS     read-write
    STATUS     optional --Conditionally Mandatory
    DESCRIPTION
        "
        Sets up Enable/Disable of service of SMTP over SSL. 

        If device has not this function (POP over SSL),
        this object must not be implemented.
        "
       ::= { kmNetSmtpGeneralEntry 5 }


kmNetSmtpSslPort  OBJECT-TYPE
    SYNTAX     INTEGER
    ACCESS     read-only
    STATUS     optional --Conditionally Mandatory
    DESCRIPTION
        "
        Specifies Port number which SMTP over SSL uses. Default is 465.

        If device has not this function (POP over SSL),
        this object must not be implemented.
        "
       ::= { kmNetSmtpGeneralEntry 6 }



-- kmNetIpp Group

-- The information of IPP relation which NetworkInterface has is included. 
-- In the system without IPP function, it is not necessary to implement 
-- this Group.


kmNetIppGeneral   OBJECT IDENTIFIER ::= { kmNetIpp 1 }   


-- kmNetIppGeneral Group

kmNetIppGeneralTable  OBJECT-TYPE
    SYNTAX    SEQUENCE OF KmNetIppGeneralEntry
    ACCESS    not-accessible
    STATUS    optional --Conditionally Mandatory
    DESCRIPTION
        "
        The table for showing the general information of IPP. 
        "
    ::= { kmNetIppGeneral 1 }


kmNetIppGeneralEntry  OBJECT-TYPE
    SYNTAX    KmNetIppGeneralEntry
    ACCESS    not-accessible
    STATUS    optional --Conditionally Mandatory
    DESCRIPTION
        "
        "
    INDEX  { kmNetIppGeneralIfIndex }
    ::= { kmNetIppGeneralTable 1 }

   KmNetIppGeneralEntry ::= SEQUENCE {
        kmNetIppGeneralIfIndex     INTEGER,
        kmNetIppServiceEnable      INTEGER,
        kmNetIppDefaultPortIndex   INTEGER
        }

kmNetIppGeneralIfIndex  OBJECT-TYPE
    SYNTAX     INTEGER
    ACCESS     read-only
    STATUS     optional --Conditionally Mandatory
    DESCRIPTION
        "
        The index for uniquely specifying NetworkInterface to 
        which IPP is set.   
        The value of Index shall be the same value with 
        kmNetGeneralIndex (ifIndex).
        "
       ::= { kmNetIppGeneralEntry 1 }

kmNetIppServiceEnable  OBJECT-TYPE
    SYNTAX     INTEGER{
            enable (1),
            disable (2)
            }  
    ACCESS     read-write
    STATUS     optional --Conditionally Mandatory
    DESCRIPTION
        "
        Sets up Enable/Disable of service of IPP
        "
       ::= { kmNetIppGeneralEntry 2 }

kmNetIppDefaultPortIndex  OBJECT-TYPE
    SYNTAX     INTEGER
    ACCESS     read-write
    STATUS     optional --Conditionally Mandatory
    DESCRIPTION
        "
        kmNetIppPortIndex which shows Default Port number used by IPP.
        "
       ::= { kmNetIppGeneralEntry 3 }


kmNetIppPortTable OBJECT-TYPE
    SYNTAX    SEQUENCE OF KmNetIppPortEntry
    ACCESS    not-accessible
    STATUS    optional --Conditionally Mandatory
    DESCRIPTION
        "
        The table for showing Port information of IPP. 
        "
    ::= { kmNetIppGeneral 2 }

kmNetIppPortEntry  OBJECT-TYPE
    SYNTAX    KmNetIppPortEntry
    ACCESS    not-accessible
    STATUS    optional --Conditionally Mandatory
    DESCRIPTION
        "
        "
    INDEX  { kmNetIppPortIfIndex, kmNetIppPortIndex }
    ::= { kmNetIppPortTable 1 }

   KmNetIppPortEntry ::= SEQUENCE {
        kmNetIppPortIfIndex    INTEGER,
        kmNetIppPortIndex      INTEGER,
        kmNetIppPortNumber     INTEGER
        }

kmNetIppPortIfIndex  OBJECT-TYPE
    SYNTAX     INTEGER
    ACCESS     read-only
    STATUS     optional --Conditionally Mandatory
    DESCRIPTION
        "
        The index for uniquely specifying NetworkInterface to 
        which IPP is set. 
        The value of Index shall be the same value with 
        kmNetGeneralIndex (ifIndex).
        "
       ::= { kmNetIppPortEntry 1 }

kmNetIppPortIndex  OBJECT-TYPE
    SYNTAX     INTEGER
    ACCESS     read-only
    STATUS     optional --Conditionally Mandatory
    DESCRIPTION
        "
        The index for uniquely showing Port.
        "
       ::= { kmNetIppPortEntry 2 }

kmNetIppPortNumber  OBJECT-TYPE
    SYNTAX     INTEGER
    ACCESS     read-only
    STATUS     optional --Conditionally Mandatory
    DESCRIPTION
        "
        Port number. '631' is supported at least.
        "
       ::= { kmNetIppPortEntry 3 }


-- kmNetSlp Group

-- The information of SLP relation which NetworkInterface has is included.
-- The following items shall be defined. In the system without SLP function,
-- it is not necessary to implement this Group.

kmNetSlpGeneralTable  OBJECT-TYPE
    SYNTAX    SEQUENCE OF KmNetSlpGeneralEntry
    ACCESS    not-accessible
    STATUS    optional --Conditionally Mandatory
    DESCRIPTION
        "
        Table for showing the general information of SLP. 
        "
    ::= { kmNetSlp 1 }

kmNetSlpGeneralEntry OBJECT-TYPE
    SYNTAX    KmNetSlpGeneralEntry
    ACCESS    not-accessible
    STATUS    optional --Conditionally Mandatory
    DESCRIPTION
        "
        "
    INDEX  { kmNetSlpIfIndex }
    ::= { kmNetSlpGeneralTable 1 }

   KmNetSlpGeneralEntry ::= SEQUENCE {
       kmNetSlpIfIndex            INTEGER,
       kmNetSlpEnable             INTEGER,
       kmNetSlpPortNumber         INTEGER,
       kmNetSlpMTU                INTEGER,
       kmNetSlpTTL                INTEGER,
       kmNetSlpBroadcastSupport   INTEGER
       }

kmNetSlpIfIndex  OBJECT-TYPE
    SYNTAX     INTEGER
    ACCESS     read-only
    STATUS     optional --Conditionally Mandatory
    DESCRIPTION
        "
        The index for uniquely specifying NetworkInterface to 
        which SLP is set.
         The value of index shall be the same value 
         with kmNetGeneralIndex(ifIndex).
        "
       ::= { kmNetSlpGeneralEntry 1 }

kmNetSlpEnable  OBJECT-TYPE
    SYNTAX     INTEGER{
                enable (1),
                disable (2)
                }
    ACCESS     read-write
    STATUS     optional --Conditionally Mandatory
    DESCRIPTION
        "Enable/Disable of service of SLP is set up. 
        "
       ::= { kmNetSlpGeneralEntry 2 }

kmNetSlpPortNumber  OBJECT-TYPE
    SYNTAX     INTEGER
    ACCESS     read-write
    STATUS     optional --Conditionally Mandatory
    DESCRIPTION
        "Port number of SLP is shown. 
         Default is 427.
        "
       ::= { kmNetSlpGeneralEntry 3 }

kmNetSlpMTU  OBJECT-TYPE
    SYNTAX     INTEGER
    ACCESS     read-write
    STATUS     optional --Conditionally Mandatory
    DESCRIPTION
        "MTU value of LP gas is shown.
         Default shall be 1400.
        "
       ::= { kmNetSlpGeneralEntry 4 }

kmNetSlpTTL  OBJECT-TYPE
    SYNTAX     INTEGER
    ACCESS     read-write
    STATUS     optional --Conditionally Mandatory
    DESCRIPTION
        "TTL value of SLP is shown.
         Default shall be 255.
        "
       ::= { kmNetSlpGeneralEntry 5 }

kmNetSlpBroadcastSupport  OBJECT-TYPE
    SYNTAX     INTEGER{
                broadcastOnly (1),
                multicastOnly (2),
                both (3)
                }
    ACCESS     read-write
    STATUS     optional --Conditionally Mandatory
    DESCRIPTION
        "Support of multicasting and broadcasting is shown.
        "
       ::= { kmNetSlpGeneralEntry 6 }


kmNetSlpConfigTable  OBJECT-TYPE
    SYNTAX    SEQUENCE OF KmNetSlpConfigEntry
    ACCESS    not-accessible
    STATUS    optional --Conditionally Mandatory
    DESCRIPTION
        "
        The table for showing the setup information of SLP.  
        "
    ::= { kmNetSlp 2 }

kmNetSlpConfigEntry OBJECT-TYPE
    SYNTAX    KmNetSlpConfigEntry
    ACCESS    not-accessible
    STATUS    optional --Conditionally Mandatory
    DESCRIPTION
        "
        "
    INDEX  { kmNetSlpConfigIfIndex, kmNetSlpIndex }
    ::= { kmNetSlpConfigTable 1 }

   KmNetSlpConfigEntry ::= SEQUENCE {
    kmNetSlpConfigIfIndex  INTEGER,
    kmNetSlpIndex          INTEGER,
    kmNetSlpService        OCTET STRING,
    kmNetSlpScope          OCTET STRING,
    kmNetSlpLifetime       INTEGER
         }

kmNetSlpConfigIfIndex  OBJECT-TYPE
    SYNTAX     INTEGER
    ACCESS     read-only
    STATUS     optional --Conditionally Mandatory
    DESCRIPTION
        "
        The index for uniquely specifying NetworkInterface to 
        which SLP is set.
         The value of index shall be the same value 
         with kmNetGeneralIndex (ifIndex).
        "
       ::= { kmNetSlpConfigEntry 1 }

kmNetSlpIndex  OBJECT-TYPE
    SYNTAX     INTEGER
    ACCESS     read-only
    STATUS     optional --Conditionally Mandatory
    DESCRIPTION
        "Index for showing a specific entry.
         Default is 1.
        "
       ::= { kmNetSlpConfigEntry 2 }

kmNetSlpService  OBJECT-TYPE
    SYNTAX     OCTET STRING(SIZE(0..31))
    ACCESS     read-only
    STATUS     optional --Conditionally Mandatory
    DESCRIPTION
        "The character string which shows the service registered into DA.
         Example: 'service:printer:help'

        "
       ::= { kmNetSlpConfigEntry 3 }

kmNetSlpScope  OBJECT-TYPE
    SYNTAX     OCTET STRING(SIZE(1..31))
    ACCESS     read-write
    STATUS     optional --Conditionally Mandatory
    DESCRIPTION
        "The character string which shows the scope of SLP.
         Default character string is 'default'.
        "
       ::= { kmNetSlpConfigEntry 4 }

kmNetSlpLifetime  OBJECT-TYPE
    SYNTAX     INTEGER
    ACCESS     read-write
    STATUS     optional --Conditionally Mandatory
    DESCRIPTION
        "The value which shows Lifetime of a registration.
         A unit is second. Default is 10800 (3 hours).
        "
       ::= { kmNetSlpConfigEntry 5 }


-- kmNetImap Group

-- The information of IMAP4 relation which NetworkInterface has is included.
-- The following items shall be defined. In the system which does not have
-- a mail receiving function or does not support IMAP4,
-- it is not necessary to implement this Group.


kmNetImapGeneralTable  OBJECT-TYPE
    SYNTAX    SEQUENCE OF KmNetImapGeneralEntry
    ACCESS    not-accessible
    STATUS    optional --Conditionally Mandatory
    DESCRIPTION
        "
        The table for showing the general information of IMAP4. 
        "
    ::= { kmNetImap 1 }

kmNetImapGeneralEntry OBJECT-TYPE
    SYNTAX    KmNetImapGeneralEntry
    ACCESS    not-accessible
    STATUS    optional --Conditionally Mandatory
    DESCRIPTION
        "
        "
    INDEX  { kmNetImapIfIndex }
    ::= { kmNetImapGeneralTable 1 }

   KmNetImapGeneralEntry ::= SEQUENCE {
       kmNetImapIfIndex       INTEGER,
       kmNetImapEnable        INTEGER,
       kmNetImapServerAddress OCTET STRING,
       kmNetImapPort          INTEGER
       }

kmNetImapIfIndex  OBJECT-TYPE
    SYNTAX     INTEGER
    ACCESS     read-only
    STATUS     optional --Conditionally Mandatory
    DESCRIPTION
        "
        The index for uniquely specifying NetworkInterface to 
        which IMAP is set.
         The value of index shall be the same value 
         with kmNetGeneralIndex (ifIndex).
        "
       ::= { kmNetImapGeneralEntry 1 }

kmNetImapEnable  OBJECT-TYPE
    SYNTAX     INTEGER{
                enable (1),
                disable (2)
                }
    ACCESS     read-write
    STATUS     optional --Conditionally Mandatory
    DESCRIPTION
        "Enable/Disable of service of IMAP is set up. 
        "
       ::= { kmNetImapGeneralEntry 2 }

kmNetImapServerAddress  OBJECT-TYPE
    SYNTAX     OCTET STRING(SIZE(0..255))
    ACCESS     read-write
    STATUS     optional --Conditionally Mandatory
    DESCRIPTION
        "Shows the IP address of IMAP Server.
         Considering about specification by Domain name,
         it is made into OCTET STRING.
         In the case of specifying by the IP address,
         it shall be handled as a character string of
         maximum 15 characters of 'xxx.xxx.xxx.xxx'.
         Whether to accept a setup by Domain name is
         dependent on an implementation of a model.
        "
       ::= { kmNetImapGeneralEntry 3 }

kmNetImapPort  OBJECT-TYPE
    SYNTAX     INTEGER
    ACCESS     read-write
    STATUS     optional --Conditionally Mandatory
    DESCRIPTION
        "Port number which Imap uses is specified.
         Default is 143.
        "
       ::= { kmNetImapGeneralEntry 4 }


-- kmNetNetWareGroup

-- NetWare related information which NetworkInterface has is included.
-- The following items shall be defined as NetWare relation.

-- Notes: About NDPS, since details are unknown at present,
-- it is not defined in this version. About NDPS,
-- a definition shall be added after making it clear that
-- how much items needs to be set up by a user.


kmNetNwGeneralTable  OBJECT-TYPE
    SYNTAX    SEQUENCE OF KmNetNwGeneralEntry
    ACCESS    not-accessible
    STATUS    optional --Conditionally Mandatory
    DESCRIPTION
        "Table with the basic information of NetWare relation
         which NetworkInterface has
        "
    ::= { kmNetNetWare 1 }

kmNetNwGeneralEntry OBJECT-TYPE
    SYNTAX    KmNetNwGeneralEntry
    ACCESS    not-accessible
    STATUS    optional --Conditionally Mandatory
    DESCRIPTION
        "
        "
    INDEX  { kmNetNwIfIndex }
    ::= { kmNetNwGeneralTable 1 }

   KmNetNwGeneralEntry ::= SEQUENCE {
       kmNetNwIfIndex         INTEGER,
       kmNetNwDefault         INTEGER,
       kmNetNwFrameTypeConfig INTEGER,
       kmNetNwPrintMode       INTEGER
       }

kmNetNwIfIndex  OBJECT-TYPE
    SYNTAX     INTEGER
    ACCESS     read-only
    STATUS     optional --Conditionally Mandatory
    DESCRIPTION
        "The index for uniquely showing NetworkInterface.
         The value of index shall be the same value with 
         kmNetGeneralIndex (ifIndex).
        "
       ::= { kmNetNwGeneralEntry 1 }

kmNetNwDefault  OBJECT-TYPE
    SYNTAX     INTEGER{
                notSupported (0),
                supported (1),
                resetToDefault (2)
                }
    ACCESS     read-write
    STATUS     optional --Conditionally Mandatory
    DESCRIPTION
        "The command which restores all setup about NetWare to FactoryDefault. 

         When resetToDefault(2) is set, an agent side shall surely 
         return Reply.
         In principle, when resetToDefault(2) is set, about the timing
         in which the setup returns to default depends on an implementation
         and it does not define in MIB.
        "
       ::= { kmNetNwGeneralEntry 2 }

kmNetNwFrameTypeConfig  OBJECT-TYPE
    SYNTAX     INTEGER
    ACCESS     read-write
    STATUS     optional --Conditionally Mandatory
    DESCRIPTION
        "A setup of FrameType used by NetWare (IPX). 
         It is set by using Bitmap of the following.
         1 (Auto-Sense) is recommended for the Default.
         Although Auto-Sense and other value do not exist together,
         about Binding two or more FrameType simultaneously,
         it is dependent on the implementation of a model.

              Bit  Value      FrameType
              ---- ----       ----------
               0     1        AutoSense
               1     2        802.3
               2     4        EthernetII
               3     8        802.3_SNAP
               4    16        802.2 (4)
               5    32        Reserved
               6    64        802.5_TokenRing
               7   128        TokenRing_SNAP

        "
       ::= { kmNetNwGeneralEntry 3 }

kmNetNwPrintMode  OBJECT-TYPE
    SYNTAX     INTEGER{
                disable (0), -- IPX is working but Pint service is stopped.
                pServerMode (1),
                nPrinterMode (2)
                }
    ACCESS     read-write
    STATUS     optional --Conditionally Mandatory
    DESCRIPTION
        "The mode of NetworkInterface used by NetWare is set up.
        Default shall be pServerMode(1). When not supporting NPrinter,
         it shall be the implementation of RO.
        "
       ::= { kmNetNwGeneralEntry 4 }


kmNetNwFrameTable  OBJECT-TYPE
    SYNTAX    SEQUENCE OF KmNetNwFrameEntry
    ACCESS    not-accessible
    STATUS    optional
    DESCRIPTION
        "The information of FrameType which is working in NetWare is shown.
        "
    ::= { kmNetNetWare 2 }

kmNetNwFrameEntry OBJECT-TYPE
    SYNTAX    KmNetNwFrameEntry
    ACCESS    not-accessible
    STATUS    optional
    DESCRIPTION
        "
        "
    INDEX  { kmNetNwFrameIfIndex, kmNetNwFrameIndex }
    ::= { kmNetNwFrameTable 1 }

   KmNetNwFrameEntry ::= SEQUENCE {
      kmNetNwFrameIfIndex    INTEGER,
      kmNetNwFrameIndex      INTEGER,
      kmNetNwFrameType       INTEGER,
      kmNetNwNetworkNumber   OCTET STRING
      }

kmNetNwFrameIfIndex  OBJECT-TYPE
    SYNTAX     INTEGER
    ACCESS     read-only
    STATUS     optional
    DESCRIPTION
        "The index for uniquely showing NetworkInterface.
         The value of index shall be the same value with 
         kmNetGeneralIndex (ifIndex).
        "
       ::= { kmNetNwFrameEntry 1 }

kmNetNwFrameIndex  OBJECT-TYPE
    SYNTAX     INTEGER
    ACCESS     read-only
    STATUS     optional
    DESCRIPTION
        "Index for showing FrameType which is operating by NetworkInterface.
        "
       ::= { kmNetNwFrameEntry 2 }

kmNetNwFrameType  OBJECT-TYPE
    SYNTAX     INTEGER{
                ethernet8023 (1),
                ethernetII (2),
                ethernetSnap (3),
                ethernet8022 (4),
                tokenRing8025 (6),
                tokenRingSnap (7)
                }
    ACCESS     read-only
    STATUS     optional
    DESCRIPTION
        "FrameType is shown.
        "
       ::= { kmNetNwFrameEntry 3 }

kmNetNwNetworkNumber  OBJECT-TYPE
    SYNTAX     OCTET STRING(SIZE(4))
    ACCESS     read-only
    STATUS     optional
    DESCRIPTION
        "Network number which each FrameType is using is displayed.
         The notation of a number is indicated by Hexadecimal numbers.
         For example, '96 10 c0 02'. 
        "
       ::= { kmNetNwFrameEntry 4 }


kmNetNwPserverTable  OBJECT-TYPE
    SYNTAX    SEQUENCE OF KmNetNwPserverEntry
    ACCESS    not-accessible
    STATUS    optional --Conditionally Mandatory
    DESCRIPTION
        "The table for showing the setup of PrintServer. 
        "
    ::= { kmNetNetWare 3 }

kmNetNwPserverEntry OBJECT-TYPE
    SYNTAX    KmNetNwPserverEntry
    ACCESS    not-accessible
    STATUS    optional --Conditionally Mandatory
    DESCRIPTION
        "
        "
    INDEX  { kmNetNwPsIfIndex, kmNetNwPsIndex }
    ::= { kmNetNwPserverTable 1 }

   KmNetNwPserverEntry ::= SEQUENCE {
      kmNetNwPsIfIndex       INTEGER,
      kmNetNwPsIndex         INTEGER,
      kmNetNwPsName          OCTET STRING,
      kmNetNwPsPasswd        OCTET STRING,
      kmNetNwPsMode          INTEGER,
      kmNetNwPsPrefFServer   OCTET STRING,
      kmNetNwPsPrefTree      OCTET STRING,
      kmNetNwPsPrefContext   OCTET STRING,
      kmNetNwPsPollingRate   INTEGER
      }

kmNetNwPsIfIndex  OBJECT-TYPE
    SYNTAX     INTEGER
    ACCESS     read-only
    STATUS     optional --Conditionally Mandatory
    DESCRIPTION
        "The index for uniquely showing NetworkInterface.
         The value of index shall be the same value with 
         kmNetGeneralIndex (ifIndex).
        "
       ::= { kmNetNwPserverEntry 1 }

kmNetNwPsIndex  OBJECT-TYPE
    SYNTAX     INTEGER
    ACCESS     read-only
    STATUS     optional --Conditionally Mandatory
    DESCRIPTION
        "Index for uniquely showing PrintServer.
         The number of indexes depends on an implementation.
        The number of indexes which can be implemented and
         the number of defaults depends on an implementation.
        "
       ::= { kmNetNwPserverEntry 2 }

kmNetNwPsName  OBJECT-TYPE
    SYNTAX     OCTET STRING(SIZE(1..63))
    ACCESS     read-write
    STATUS     optional --Conditionally Mandatory
    DESCRIPTION
        "The name of PrintServer.
         Default is dependent on an implementation.
         Definition of Max size is 63. But recommended
         size is 47. 
        "
       ::= { kmNetNwPserverEntry 3 }

kmNetNwPsPasswd  OBJECT-TYPE
    SYNTAX     OCTET STRING(SIZE(0..63))
    ACCESS     read-write
    STATUS     optional --Conditionally Mandatory
    DESCRIPTION
        "Password of PrintServer.
         Default is Null.
         When it is gotten, applying scramble to value is not accepted.
         About security, support by the management tool side.
         Definition of Max size is 63. But recommended
         size is 31. 
        "
       ::= { kmNetNwPserverEntry 4 }

kmNetNwPsMode  OBJECT-TYPE
    SYNTAX     INTEGER{
                both (0),
                binderyMode (1),
                ndsMode (2)
                }
    ACCESS     read-write
    STATUS     optional --Conditionally Mandatory
    DESCRIPTION
        "The mode in which PrintServer supports is shown.
        "
       ::= { kmNetNwPserverEntry 5 }

kmNetNwPsPrefFServer  OBJECT-TYPE
    SYNTAX     OCTET STRING(SIZE(0..47))
    ACCESS     read-write
    STATUS     optional --Conditionally Mandatory
    DESCRIPTION
        "Value of Preferred FileServer used in Bindery mode.
         It shall be NullString when set only to NDS mode.
         In the system which does not set up PreferredFileServer,
         implement '-' (hyphen) and shall be RO.
         Definition of Max size is 63. But recommended
         size is 47. 
        "
       ::= { kmNetNwPserverEntry 6 }

kmNetNwPsPrefTree  OBJECT-TYPE
    SYNTAX     OCTET STRING(SIZE(0..63))
    ACCESS     read-write
    STATUS     optional --Conditionally Mandatory
    DESCRIPTION
        "Value of Preferred Tree used in NDS mode.
         It shall be NullString when set only to Bindery mode.
         In the system which does not set up PreferredTree,
         implement 'N/A' and shall be RO.
         Definition of Max size is 63. But recommended
         size is 47. 
        "
       ::= { kmNetNwPserverEntry 7 }

kmNetNwPsPrefContext  OBJECT-TYPE
    SYNTAX     OCTET STRING(SIZE(0..191))
    ACCESS     read-write
    STATUS     optional --Conditionally Mandatory
    DESCRIPTION
        "Value of Preferred Context used in NDS mode.
         It shall be NullString when set only to Bindery mode.
         In the system which does not set up PreferredContext,
         implement 'N/A' and shall be RO.
         Definition of Max size is 255. But recommended
         size is 127. 
        "
       ::= { kmNetNwPserverEntry 8 }

kmNetNwPsPollingRate  OBJECT-TYPE
    SYNTAX     INTEGER
    ACCESS     read-write
    STATUS     optional --Conditionally Mandatory
    DESCRIPTION
        "
        The interval at which PrinteServer scans Queue. Unit is second.
        Range which can be set up shall be 1 - 65535. Default is 1 (second).
        "
       ::= { kmNetNwPserverEntry 9 }


kmNetNwQueueTable  OBJECT-TYPE
    SYNTAX    SEQUENCE OF KmNetNwQueueEntry
    ACCESS    not-accessible
    STATUS    optional --Conditionally Mandatory
    DESCRIPTION
        "
         Table which shows the information of Queue which 
         NetworkInterface has managed. 
        "
    ::= { kmNetNetWare 4 }

kmNetNwQueueEntry OBJECT-TYPE
    SYNTAX    KmNetNwQueueEntry
    ACCESS    not-accessible
    STATUS    optional --Conditionally Mandatory
    DESCRIPTION
        "
        "
    INDEX  { kmNetNwQueueIndex }
    ::= { kmNetNwQueueTable 1 }

   KmNetNwQueueEntry ::= SEQUENCE {
      kmNetNwQueueIndex      INTEGER,
      kmNetNwQueueName       OCTET STRING,
      kmNetNwQueueRefIfIndex INTEGER,
      kmNetNwQueueRefPsIndex INTEGER,
      kmNetNwQueueStatus     INTEGER
      }

kmNetNwQueueIndex  OBJECT-TYPE
    SYNTAX     INTEGER
    ACCESS     read-only
    STATUS     optional --Conditionally Mandatory
    DESCRIPTION
        "
         The index for uniquely showing Queue.
        "
       ::= { kmNetNwQueueEntry 1 }

kmNetNwQueueName  OBJECT-TYPE
    SYNTAX     OCTET STRING(SIZE(0..63))
    ACCESS     read-only
    STATUS     optional --Conditionally Mandatory
    DESCRIPTION
        "
         The name of Queue.
        "
       ::= { kmNetNwQueueEntry 2 }

kmNetNwQueueRefIfIndex  OBJECT-TYPE
    SYNTAX     INTEGER
    ACCESS     read-only
    STATUS     optional --Conditionally Mandatory
    DESCRIPTION
        "
         NetworkInterface which is managing Queue is shown.
         Use the value of kmNetNwPsIfIndex.
        "
       ::= { kmNetNwQueueEntry 3 }

kmNetNwQueueRefPsIndex  OBJECT-TYPE
    SYNTAX     INTEGER
    ACCESS     read-only
    STATUS     optional --Conditionally Mandatory
    DESCRIPTION
        "
         PrintServer which is managing Queue is shown.
         Use the value of kmNetNwPsIndex.
        "
       ::= { kmNetNwQueueEntry 4 }

kmNetNwQueueStatus  OBJECT-TYPE
    SYNTAX     INTEGER{
                unknown (0),
                available(1),
                allocated (2),
                inUse (3)
                }
    ACCESS     read-only
    STATUS     optional --Conditionally Mandatory
    DESCRIPTION
        "
         The state of Queue is shown. 
        "
       ::= { kmNetNwQueueEntry 5 }


kmNetNwNPrinterTable  OBJECT-TYPE
    SYNTAX    SEQUENCE OF KmNetNwNPrinterEntry
    ACCESS    not-accessible
    STATUS    optional --Conditionally Mandatory
    DESCRIPTION
        "Table which shows the information of NPrinter
         which NetworkInterface is managing. 
         In the system without Nprinter function,
         it is not necessary to implement this table.
        "
    ::= { kmNetNetWare 5 }

kmNetNwNPrinterEntry OBJECT-TYPE
    SYNTAX    KmNetNwNPrinterEntry
    ACCESS    not-accessible
    STATUS    optional --Conditionally Mandatory
    DESCRIPTION
        "
        "
    INDEX  { kmNetNwNPrinterIfIndex, kmNetNwNPrinterIndex }
    ::= { kmNetNwNPrinterTable 1 }

   KmNetNwNPrinterEntry ::= SEQUENCE {
      kmNetNwNPrinterIfIndex INTEGER,
      kmNetNwNPrinterIndex   INTEGER,
      kmNetNwNPrinterName    OCTET STRING,
      kmNetNwNPrinterNumber  INTEGER
      }

kmNetNwNPrinterIfIndex  OBJECT-TYPE
    SYNTAX     INTEGER
    ACCESS     read-only
    STATUS     optional --Conditionally Mandatory
    DESCRIPTION
        "
         The index for uniquely showing NetworkInterface.
         The value of index shall be the same value 
         with kmNetGeneralIndex (ifIndex).
        "
       ::= { kmNetNwNPrinterEntry 1 }

kmNetNwNPrinterIndex  OBJECT-TYPE
    SYNTAX     INTEGER
    ACCESS     read-only
    STATUS     optional --Conditionally Mandatory
    DESCRIPTION
        "
         Index for uniquely showing NPrinter.
        "
       ::= { kmNetNwNPrinterEntry 2 }

kmNetNwNPrinterName  OBJECT-TYPE
    SYNTAX     OCTET STRING(SIZE(1..63))
    ACCESS     read-write
    STATUS     optional --Conditionally Mandatory
    DESCRIPTION
        "
         The name of NPrinter.
        "
       ::= { kmNetNwNPrinterEntry 3 }

kmNetNwNPrinterNumber  OBJECT-TYPE
    SYNTAX     INTEGER
    ACCESS     read-only
    STATUS     optional --Conditionally Mandatory
    DESCRIPTION
        "
         Printer number of NPrinter. Default shall be 1.
        "
       ::= { kmNetNwNPrinterEntry 4 }


-- kmNetAppleTalk Group

-- AppleTalk related information which NetworkInterface has is included.

kmNetAppleTalkGeneralTable  OBJECT-TYPE
    SYNTAX    SEQUENCE OF KmNetAppleTalkGeneralEntry
    ACCESS    not-accessible
    STATUS    optional --Conditionally Mandatory
    DESCRIPTION
        "Table with the basic information of AppleTalk relation
         which NetworkInterface has. 
        "
    ::= { kmNetAppleTalk 1 }

kmNetAppleTalkGeneralEntry OBJECT-TYPE
    SYNTAX    KmNetAppleTalkGeneralEntry
    ACCESS    not-accessible
    STATUS    optional --Conditionally Mandatory
    DESCRIPTION
        "
        "
    INDEX  { kmNetAtIfIndex }
    ::= { kmNetAppleTalkGeneralTable 1 }

   KmNetAppleTalkGeneralEntry ::= SEQUENCE {
      kmNetAtIfIndex     INTEGER,
      kmNetAtDefault     INTEGER,
      kmNetAtNetNumber   INTEGER,
      kmNetAtNodeNumber  INTEGER,
      kmNetAtDesiredZone OCTET STRING,
      kmNetAtCurrentZone OCTET STRING
      }

kmNetAtIfIndex  OBJECT-TYPE
    SYNTAX     INTEGER
    ACCESS     read-only
    STATUS     optional --Conditionally Mandatory
    DESCRIPTION
        "The index for uniquely showing NetworkInterface.
         The value of index shall be the same value 
         with kmNetGeneralIndex (ifIndex).
        "
       ::= { kmNetAppleTalkGeneralEntry 1 }

kmNetAtDefault  OBJECT-TYPE
    SYNTAX     INTEGER{
                notSupported (0),
                supported (1),
                resetToDefault (2)
                }
    ACCESS     read-write
    STATUS     optional --Conditionally Mandatory
    DESCRIPTION
        "
         The command which restores all setup about AppleTalk to FactoryDefault.

         When resetToDefault(2) is set, an agent side shall surely return Reply.
         In principle, when resetToDefault(2) is set, about the timing
         in which the setup returns to default depends on an implementation
         and it does not define in MIB.
        "
       ::= { kmNetAppleTalkGeneralEntry 2 }

kmNetAtNetNumber  OBJECT-TYPE
    SYNTAX     INTEGER
    ACCESS     read-only
    STATUS     optional --Conditionally Mandatory
    DESCRIPTION
        "Network Number in Network of AppleTalk.
         Display the value acquired at the time of Apple Talk starting.
         When it is unknown, may be -2 (unknown).
        "
       ::= { kmNetAppleTalkGeneralEntry 3 }

kmNetAtNodeNumber  OBJECT-TYPE
    SYNTAX     INTEGER
    ACCESS     read-only
    STATUS     optional --Conditionally Mandatory
    DESCRIPTION
        "Node Number in Network of AppleTalk.
         Display the value acquired at the time of Apple Talk starting.
         When it is unknown, may be -2 (unknown).
        "
       ::= { kmNetAppleTalkGeneralEntry 4 }

kmNetAtDesiredZone  OBJECT-TYPE
    SYNTAX     OCTET STRING(SIZE(1..31))
    ACCESS     read-write
    STATUS     optional --Conditionally Mandatory
    DESCRIPTION
        "Setting value of Zone name in Apple Talk.
         Default shall be '*'.
        "
       ::= { kmNetAppleTalkGeneralEntry 5 }

kmNetAtCurrentZone  OBJECT-TYPE
    SYNTAX     OCTET STRING(SIZE(0..31))
    ACCESS     read-only
    STATUS     optional --Conditionally Mandatory
    DESCRIPTION
        "
         Zone name to which device is operating.
         In environment of operation, it may differ from 
         the above-mentioned value.
        "
       ::= { kmNetAppleTalkGeneralEntry 6 }


kmNetAtPrinterTable  OBJECT-TYPE
    SYNTAX    SEQUENCE OF KmNetAtPrinterEntry
    ACCESS    not-accessible
    STATUS    optional --Conditionally Mandatory
    DESCRIPTION
        "The table for showing the setup of AppleTalk Printer. 
        "
    ::= { kmNetAppleTalk 2 }

kmNetAtPrinterEntry OBJECT-TYPE
    SYNTAX    KmNetAtPrinterEntry
    ACCESS    not-accessible
    STATUS    optional --Conditionally Mandatory
    DESCRIPTION
        "
        "
    INDEX  { kmNetAtPrinterIfIndex, kmNetAtPrinterIndex }
    ::= { kmNetAtPrinterTable 1 }

   KmNetAtPrinterEntry ::= SEQUENCE {
      kmNetAtPrinterIfIndex  INTEGER,
      kmNetAtPrinterIndex    INTEGER,
      kmNetAtPrinterName     OCTET STRING,
      kmNetAtPrinterType     OCTET STRING
      }

kmNetAtPrinterIfIndex  OBJECT-TYPE
    SYNTAX     INTEGER
    ACCESS     read-only
    STATUS     optional --Conditionally Mandatory
    DESCRIPTION
        "
         The index for uniquely showing NetworkInterface.
         The value of index shall be the same value 
         with kmNetGeneralIndex (ifIndex).
        "
       ::= { kmNetAtPrinterEntry 1 }

kmNetAtPrinterIndex OBJECT-TYPE
    SYNTAX     INTEGER
    ACCESS     read-only
    STATUS     optional --Conditionally Mandatory
    DESCRIPTION
        "The index for uniquely showing AppleTalk Printer.
         The number of indexed depends on an implementation.
        "
       ::= { kmNetAtPrinterEntry 2 }

kmNetAtPrinterName OBJECT-TYPE
    SYNTAX     OCTET STRING(SIZE(1..31))
    ACCESS     read-write
    STATUS     optional --Conditionally Mandatory
    DESCRIPTION
        "The name of AppleTalk Printer.
         When performing the operation, the name in an actual
         operation environment should be shown.
        "
       ::= { kmNetAtPrinterEntry 3 }

kmNetAtPrinterType OBJECT-TYPE
    SYNTAX     OCTET STRING(SIZE(0..31))
    ACCESS     read-only
    STATUS     optional --Conditionally Mandatory
    DESCRIPTION
        "Type of AppleTalk Printer. Default is 'LaserWriter'.
        "
       ::= { kmNetAtPrinterEntry 4 }


-- kmNetSmb Group

-- SMB related information which NetworkInterface has is included.

kmNetSmbGeneralTable  OBJECT-TYPE
    SYNTAX    SEQUENCE OF KmNetSmbGeneralEntry
    ACCESS    not-accessible
    STATUS    optional --Conditionally Mandatory
    DESCRIPTION
        "The table with the basic information of SMB relation
         which NetworkInterface has. 
        "
    ::= { kmNetSmb 1 }

kmNetSmbGeneralEntry OBJECT-TYPE
    SYNTAX    KmNetSmbGeneralEntry
    ACCESS    not-accessible
    STATUS    optional --Conditionally Mandatory
    DESCRIPTION
        "
        "
    INDEX  { kmNetSmbIfIndex }
    ::= { kmNetSmbGeneralTable 1 }

   KmNetSmbGeneralEntry ::= SEQUENCE {
      kmNetSmbIfIndex                INTEGER,
      kmNetSmbDefault                INTEGER,
      kmNetSmbWorkGroupName          OCTET STRING,
      kmNetSmbHostName               OCTET STRING,
      kmNetSmbWinsSupport            INTEGER,
      kmNetSmbWinsPrimaryServer      IpAddress,
      kmNetSmbWinsSecondaryServer    IpAddress
      }

kmNetSmbIfIndex  OBJECT-TYPE
    SYNTAX     INTEGER
    ACCESS     read-only
    STATUS     optional --Conditionally Mandatory
    DESCRIPTION
        "
         The index for uniquely showing NetworkInterface.
         The value of index shall be the same value 
         with kmNetGeneralIndex (ifIndex).
        "
       ::= { kmNetSmbGeneralEntry 1 }

kmNetSmbDefault  OBJECT-TYPE
    SYNTAX     INTEGER{
                notSupported (0),
                supported (1),
                resetToDefault (2)
                }
    ACCESS     read-write
    STATUS     optional --Conditionally Mandatory
    DESCRIPTION
        "
        The command which restores all setup about SMB to FactoryDefault. 

        When resetToDefault(2) is set, an agent side shall surely return Reply.
        In principle, when resetToDefault(2) is set, about the timing
        in which the setup returns to default depends on an implementation
        and it does not define in MIB.
        "
       ::= { kmNetSmbGeneralEntry 2 }

kmNetSmbWorkGroupName  OBJECT-TYPE
    SYNTAX     OCTET STRING(SIZE(1..31))
    ACCESS     read-write
    STATUS     optional --Conditionally Mandatory
    DESCRIPTION
        "
         Workgroup name in Windows Network. Default shall be 'WORKGROUP'.
         Only the implementation of capital letters is accepted 
         about this item.
        "
       ::= { kmNetSmbGeneralEntry 3 }

kmNetSmbHostName  OBJECT-TYPE
    SYNTAX     OCTET STRING(SIZE(1..31))
    ACCESS     read-write
    STATUS     optional --Conditionally Mandatory
    DESCRIPTION
        "
         Host name in Windows Network. Default is dependent on 
         an implementation.
         Only the implementation of capital letters is accepted 
         about this item
        "
       ::= { kmNetSmbGeneralEntry 4 }

kmNetSmbWinsSupport  OBJECT-TYPE
    SYNTAX     INTEGER{
                notSupported (0),
                enable (1),
                disable (2)
                }
    ACCESS     read-write
    STATUS     optional --Conditionally Mandatory
    DESCRIPTION
        "Sets up the availability of use of WINS.
         Default is disable(2).
        "
       ::= { kmNetSmbGeneralEntry 5 }

kmNetSmbWinsPrimaryServer  OBJECT-TYPE
    SYNTAX     IpAddress
    ACCESS     read-write
    STATUS     optional --Conditionally Mandatory
    DESCRIPTION
        "Sets up Primary Server of Wins. Default is 0.0.0.0
        "
       ::= { kmNetSmbGeneralEntry 6 }

kmNetSmbWinsSecondaryServer  OBJECT-TYPE
    SYNTAX     IpAddress
    ACCESS     read-write
    STATUS     optional --Conditionally Mandatory
    DESCRIPTION
        "Sets up Secondary Server of Wins. Default is 0.0.0.0.
        "
       ::= { kmNetSmbGeneralEntry 7 }


kmNetSmbPrinterTable  OBJECT-TYPE
    SYNTAX    SEQUENCE OF KmNetSmbPrinterEntry
    ACCESS    not-accessible
    STATUS    optional --Conditionally Mandatory
    DESCRIPTION
        "The table which has the information of Printer relation in SMB. 
        "
    ::= { kmNetSmb 2 }

kmNetSmbPrinterEntry OBJECT-TYPE
    SYNTAX    KmNetSmbPrinterEntry
    ACCESS    not-accessible
    STATUS    optional --Conditionally Mandatory
    DESCRIPTION
        "
        "
    INDEX  { kmNetSmbPrinterIfIndex, kmNetSmbPrinterIndex }
    ::= { kmNetSmbPrinterTable 1 }

   KmNetSmbPrinterEntry ::= SEQUENCE {
      kmNetSmbPrinterIfIndex INTEGER,
      kmNetSmbPrinterIndex   INTEGER,
      kmNetSmbPrinterName    OCTET STRING,
      kmNetSmbPrinterDescr   OCTET STRING
      }

kmNetSmbPrinterIfIndex  OBJECT-TYPE
    SYNTAX     INTEGER
    ACCESS     read-only
    STATUS     optional --Conditionally Mandatory
    DESCRIPTION
        "
         The index for uniquely showing NetworkInterface.
         The value of index shall be the same value 
         with kmNetGeneralIndex (ifIndex).
        "
       ::= { kmNetSmbPrinterEntry 1 }

kmNetSmbPrinterIndex OBJECT-TYPE
    SYNTAX     INTEGER
    ACCESS     read-only
    STATUS     optional --Conditionally Mandatory
    DESCRIPTION
        "Index for uniquely showing Printer in SMB.
         The number of indexes depends on an implementation.
        "
       ::= { kmNetSmbPrinterEntry 2 }

kmNetSmbPrinterName OBJECT-TYPE
    SYNTAX     OCTET STRING(SIZE(1..12))
    ACCESS     read-write
    STATUS     optional --Conditionally Mandatory
    DESCRIPTION
        "
         Printer name in SMB. Default is dependent on the implementation of 
         a model.
         About the availability of Printer name change shall also be dependent
         on an implementation.
        "
       ::= { kmNetSmbPrinterEntry 3 }

kmNetSmbPrinterDescr OBJECT-TYPE
    SYNTAX     OCTET STRING(SIZE(0..31))
    ACCESS     read-write
    STATUS     optional --Conditionally Mandatory
    DESCRIPTION
        "
         Explanation of Printer.
         About the written contents is dependent on the implementation of
         a model; however, implementation of NullString is not accepted.
         At least input the character string which is same as 
         Default Printer name.
        "
       ::= { kmNetSmbPrinterEntry 4 }


-- Private Job Management MIB

kmJmMibVersion  OBJECT-TYPE
    SYNTAX    DisplayString (SIZE(0..7))
    ACCESS    read-only
    STATUS    mandatory
    DESCRIPTION
        "
         The version information of Konica-Minolta Standard MIB specification.

         This indicates the version of the 
         Konica-Minolta Private Job Management MIB which is implemented. 

         It is written as AA.BC.
         AA is indicating major revision, and B and C is 
         minor revision. Decimal point is ASCII-coded period.

         This definition file is corresponded to '1.50'.
        "
    ::= { kmJobManagement 1 }

   kmJmGeneral      OBJECT IDENTIFIER ::= { kmJobManagement 2 }
   kmJmJob          OBJECT IDENTIFIER ::= { kmJobManagement 3 }


--  kmJmGeneral Group

kmJmGeneralTable  OBJECT-TYPE
    SYNTAX    SEQUENCE OF KmJmGeneralEntry
    ACCESS    not-accessible
    STATUS    mandatory
    DESCRIPTION
        "
         This table indicates the general information about
         Job Management.
         This table contains the number of active jobs, oldest/newest
         jobs, the number of preservation of a history, and so on. 
        "
    ::= { kmJmGeneral 1 }

kmJmGeneralEntry OBJECT-TYPE
    SYNTAX    KmJmGeneralEntry
    ACCESS    not-accessible
    STATUS    mandatory
    DESCRIPTION
        "
        "
    INDEX  { kmJmGeneralJobSetIndex }
    ::= { kmJmGeneralTable 1 }

    KmJmGeneralEntry ::= SEQUENCE {
        kmJmGeneralJobSetIndex           INTEGER,
        kmJmGeneralNumberOfActiveJobs    INTEGER,
        kmJmGeneralOldestActiveJobIndex  INTEGER,
        kmJmGeneralNewestActiveJobIndex  INTEGER,
        kmJmGeneralJobPersistence        INTEGER,
        kmJmGeneralJobSetType            INTEGER,
        kmJmGeneralJobFinishTimeOfActiveJobs INTEGER
        }

kmJmGeneralJobSetIndex  OBJECT-TYPE
       SYNTAX     INTEGER
       ACCESS     read-only
       STATUS     mandatory
       DESCRIPTION
           "
            A unique value for each job set in this MIB. 
            JobSet shows the system of the serial number used for 
            Job management.

            In managing a serial number to 1 by all the functions of 
            a device, it sets the number of JobSets to 1.
            In managing a serial number for every functional classification,
            only the number of functional classifications shall have JobSet.
           "
       ::= { kmJmGeneralEntry 1 }

kmJmGeneralNumberOfActiveJobs  OBJECT-TYPE
       SYNTAX     INTEGER
       ACCESS     read-only
       STATUS     mandatory
       DESCRIPTION
           "
            The current number of 'active' jobs in the kmJmJobTable.
            when the device has no active jobs, this value should be 0.

            The device that cannot support to count active jobs
            should implement (-2) as fixed value. 
           "
       ::= { kmJmGeneralEntry 2 }

kmJmGeneralOldestActiveJobIndex  OBJECT-TYPE
       SYNTAX     INTEGER
       ACCESS     read-only
       STATUS     mandatory
       DESCRIPTION
           "
            The kmJmJobIndex of the oldest job that is still in 
            one of the 'active' states.
            In other words, the index of the 'active' job that has 
            been in the job tables the longest.

            If there are no active jobs, this value should be 0.

            The device that cannot support to count active jobs
            should implement (-2) as fixed value. 
           "
       ::= { kmJmGeneralEntry 3 }

kmJmGeneralNewestActiveJobIndex  OBJECT-TYPE
       SYNTAX     INTEGER
       ACCESS     read-only
       STATUS     mandatory
       DESCRIPTION
           "
            The kmJmJobIndex of the newest job that is in one of the
            'active' states.
            In other words, the index of the 'active' job that has been
            most recently added to the job tables.

            If there are no active jobs, this value should be 0.

            The device that cannot support to count active jobs
            should implement (-2) as fixed value. 
           "
       ::= { kmJmGeneralEntry 4 }

kmJmGeneralJobPersistence  OBJECT-TYPE
       SYNTAX     INTEGER
       ACCESS     read-only
       STATUS     mandatory
       DESCRIPTION
           "The number holding the information (Index) on Job
            is specified after an end of Job.
            About the number which should hold the history information
            on Job, it shall be dependent on implementation of a model.
            recommended value is 50.

            If a device can not support this, '-2'(Not Support) should
            be implemented.
           "
       ::= { kmJmGeneralEntry 5 }

kmJmGeneralJobSetType  OBJECT-TYPE
       SYNTAX    INTEGER {
                 mfpAll (0),
                 copy (1),
                 print (2),
                 receiveJob (3),
                 sendJob (4),
                 faxReceive (5),
                 faxSend (6),
                 other (7)
                 }
       ACCESS     read-only
       STATUS     mandatory
       DESCRIPTION
           "
            The type of JobSet.
           "
       ::= { kmJmGeneralEntry 6 }

kmJmGeneralJobFinishTimeOfActiveJobs OBJECT-TYPE
       SYNTAX    INTEGER 
       ACCESS     read-only
       STATUS     mandatory
       DESCRIPTION
           "
            The projected finishing time of active jobs.
            Unit is minutes.

            If there are no active jobs, this value should be 0.

            The device that cannot support to estimate finishing time,
            should implement (-2) as fixed value. 
           "
       ::= { kmJmGeneralEntry 7 }

--  kmJmJob Group

-- This group shows the detailed information of jobs.

kmJmJobTable  OBJECT-TYPE
       SYNTAX    SEQUENCE OF KmJmJobEntry
       ACCESS    not-accessible
       STATUS    mandatory
       DESCRIPTION
           "
            The table indicates the detailed information of jobs.

           "
       ::= { kmJmJob 1 }

kmJmJobEntry OBJECT-TYPE
    SYNTAX    KmJmJobEntry
    ACCESS    not-accessible
    STATUS    mandatory
    DESCRIPTION
        "
        "
    INDEX  { kmJmJobJobSetIndex, kmJmJobIndex }
    ::= { kmJmJobTable 1 }

    KmJmJobEntry ::= SEQUENCE {
       kmJmJobJobSetIndex    INTEGER,
       kmJmJobIndex          Integer32,
       kmJmJobFunction       INTEGER,
       kmJmJobStatus         INTEGER,
       kmJmJobStatusDetails  OCTET STRING,
       kmJmJobReceivedTime   DateAndTime,
       kmJmJobCompleteTime   DateAndTime,
       kmJmJobPriority       INTEGER,
       kmJmJobDivNumber      OCTET STRING,
       kmJmJobOwner          OCTET STRING,
       kmJmJobType           INTEGER,
       kmJmJobName           OCTET STRING,
       kmJmJobDocPageNumbers    Integer32,
       kmJmJobDocCopyNumbers    Integer32,
       kmJmJobPageSize       INTEGER,
       kmJmJobDestination    OCTET STRING,
       kmJmJobDriverJobID    OCTET STRING,
       kmJmJobOutputMode     INTEGER,
       kmJmJobDataSize       Integer32,
       kmJmJobColorMode      INTEGER,
       kmJmJobFormat         INTEGER,
       kmJmJobXResolution    INTEGER,
       kmJmJobYResolution    INTEGER,
       kmJmJobDuplex         INTEGER,
       kmJmJobFinishing      OCTET STRING,
       kmJmJobOutputPages    Integer32,
       kmJmJobOutputSheets   Integer32,
       kmJmJobMediaType      INTEGER,
       kmJmJobPaperAttribute INTEGER
       }

kmJmJobJobSetIndex  OBJECT-TYPE
    SYNTAX    INTEGER
    ACCESS    read-only
    STATUS    mandatory
    DESCRIPTION
        "
        A unique value for each job set in this MIB. 
        JobSet shows the system of the serial number used for Job management.

        This index is the same as kmJmGeneralJobSetIndex.
        "
    ::= { kmJmJobEntry 1 }

kmJmJobIndex  OBJECT-TYPE
    SYNTAX    Integer32
    ACCESS    read-only
    STATUS    mandatory
    DESCRIPTION
        "
        The sequential, monotonously increasing identifier index for
        the job generated by the device when that device accepted the job. 

        This Index shall hold also in power supply On./Off.
        "
    ::= { kmJmJobEntry 2 }

kmJmJobFunction  OBJECT-TYPE
    SYNTAX    INTEGER {
                 unknown (0),
                 copy (1),
                 print (2),
                 receiveJob (3),
                 sendJob (4),
                 faxReceive (5),
                 faxSend (6),
                 other (7),
                 multi (10)
                 }
    ACCESS    read-only
    STATUS    mandatory
    DESCRIPTION
        "
        This value indicates the function of job sender.

        receiveJob(3) may include FAX and iFAX jobs.
        "
    ::= { kmJmJobEntry 3 }

kmJmJobStatus  OBJECT-TYPE
    SYNTAX    INTEGER {
                unknown (0),
                other (1),
                cancelRequest (2),
                pauseRequest (3),
                restartRequest (4),

                pending (10),
                pendingHeld (11),
                pendingPaused (12),

                processing (20),
                sending (21),
                receiving (22),
                printing (23),
                scanning (24),
                processingStopped (25),

                completed (30),
                caution (31),
                aborted (32),
                canceled (33)
                }
    ACCESS    read-write
    STATUS    mandatory
    DESCRIPTION
        "
        This value indicates the status of job.
        "
    ::= { kmJmJobEntry 4 }

   kmJmJobStatusDetails  OBJECT-TYPE
    SYNTAX    OCTET STRING(SIZE(0..63))
    ACCESS    read-only
    STATUS    mandatory
    DESCRIPTION
        "
        The detailed status of job.
        It is used as information added to kmJmJobStatus.

        In Alert conditions, this string should be same as
        prtAlertLocation code.
        If no appropriate code, this string should be device
       depended string. 

        If the device cannot recognize the detailed status of job,
        this value should be null (Zero-Length).
        "
    ::= { kmJmJobEntry 5 }

kmJmJobReceivedTime  OBJECT-TYPE
    SYNTAX     DateAndTime
    ACCESS     read-only
    STATUS     mandatory
    DESCRIPTION
        "
        Registration time of Job.
        UTC is recommended. (in this case time zone is omissible).

        When you cannot perform acquisition of time information, 
        be referred to as Null (Zero-Length).
        "
    ::= { kmJmJobEntry 6 }

kmJmJobCompleteTime  OBJECT-TYPE
    SYNTAX     DateAndTime
    ACCESS     read-only
    STATUS     mandatory
    DESCRIPTION
        "
         Completion time of Job.
         UTC is recommended. (in this case time zone is omissible).

         When you await and completion time cannot be 
         written by Job etc., be referred to as Null (Zero-Length).
        "
    ::= { kmJmJobEntry 7 }


kmJmJobPriority  OBJECT-TYPE
    SYNTAX    INTEGER {
                 notSupported (0),
                 lowestPriority (1),
                 lowPriority (2),
                 normalPriority (3),
                 highPriority (4),
                 highestPriority (5)
              }
    ACCESS    read-write
    STATUS    mandatory
    DESCRIPTION
        "
        It is used when controlling the priority of Job.
        
        When device cannot support to  change of a priority,
        this value should be notSupported (0) as RO.

        When device support to change of a priority, 
        it uses the value of 1 to 5. In this case, 
        implementation as RW is mandatory.
        "
    ::= { kmJmJobEntry 8 }

kmJmJobDivNumber  OBJECT-TYPE
    SYNTAX    OCTET STRING(SIZE(0..8))
    ACCESS    read-only
    STATUS    mandatory
    DESCRIPTION
        "
        The division number of job.

        When the device does not perform division control,
        this value should be null.
        "
    ::= { kmJmJobEntry 9 }

kmJmJobOwner  OBJECT-TYPE
    SYNTAX    OCTET STRING(SIZE(0..63))
    ACCESS    read-only
    STATUS    mandatory
    DESCRIPTION
        "
        The owner of job.
        If device cannot detect the name of owner ,
        this value should be null.
        
        When the display character string is done for the language,
        the encode key must be UTF-8.
        "
    ::= { kmJmJobEntry 10 }

kmJmJobType  OBJECT-TYPE
    SYNTAX    INTEGER {
                 other (0),
                 scanSend (10),
                 eMail (11),
                 iFaxSend (12),
                 scanToServer (13),
                 scanToPC (14),
                 scanToHDD (15),
                 twain (16),
                 faxSend (17),
                 pcFaxSend (18),
                 batchSend (19),
                 normalPrint (20),
                 ippPrint (21),
                 securePrint (22),
                 timerPrint (23),
                 printToHDD (24),
                 proofAndPrint (25),
                 proofAndRestoreSend (26),
                 bindPrint (27),
                 bulletinPrint (28),
                 reportPrint (29),

                 iFaxReceive (31),
                 faxReceive (32),
                 faxPollingReceive (33),
                 
                 faxForwardingReceive (35),
                 faxRelayReceive (36),
                 faxForwardingSend (37),
                 faxRelaySend (38),
                 faxRestoreSend (39),

                 copy (40),
                 
                 boxPrint (51),
                 
                 boxStore (60),
                 
                 pollingSend (71),
                 pollingSendPrint (72),
                 pollingSendBulletin (73),
                 pollingSendStore (74)
              }
    ACCESS    read-only
    STATUS    mandatory
    DESCRIPTION
        "
        The type of job.
        When the job type is not detected, 
        this value should be other(0).
        "
    ::= { kmJmJobEntry 11 }

kmJmJobName  OBJECT-TYPE
    SYNTAX    OCTET STRING(SIZE(0..255))
    ACCESS    read-only
    STATUS    mandatory
    DESCRIPTION
        "
        The name of job.
        In case of print job, this value should be
        file name or file name of PJL.

        In case of copy job, this value should be null.

        When the display character string is done for the language,
        the encode key must be UTF-8.
        "
    ::= { kmJmJobEntry 12 }

kmJmJobDocPageNumbers  OBJECT-TYPE
    SYNTAX    Integer32
    ACCESS    read-only
    STATUS    mandatory
    DESCRIPTION
        "
        The page numbers of job.
        When device cannot detect page numbers
        this value should be (-2).
        "
    ::= { kmJmJobEntry 13 }

kmJmJobDocCopyNumbers  OBJECT-TYPE
    SYNTAX    Integer32
    ACCESS    read-only
    STATUS    mandatory
    DESCRIPTION
        "
        Number of copies of Job.
        When device cannot detect the number of copies,
        this value should be (-2).
        "
    ::= { kmJmJobEntry 14 }

kmJmJobPageSize  OBJECT-TYPE
    SYNTAX    INTEGER {
        other(1),
        unknown(2),
        a3(259),
        a4(260),
        a5(261),
        a6(262),
        b4(516),
        b5(517),
        b6(518),
        isoB4(772),
        isoB5(773),
        isoB6(774),
        c5(1029),
        metric220x330(1285),
        na13x19(1539),
        na12x18(1540),
        na11x17(1541),
        na11x15(1542),
        na11x14(1543),  -- Printer Only
        na10x14(1545),
        na8Halfx14(1547), -- 8 1/2 x 14
        na8Halfx13Half(1548), -- 8 1/2 x 13 1/2
        na8Halfx13(1549), -- 8 1/2 x 13
        na8Halfx11(1551), -- 8 1/2 x 11
        na8Quarterx13(1553), -- 8 1/4 x 13
        na8Eighthx13Quarterx(1554), -- 8 1/8 x 13
        na8x13(1556),
        na8x10Half(1557), -- 8x10 1/2
        na8x10(1558),
        na7Quarterx10Half(1559), -- 7 1/4 x 10 1/2
        na5Halfx8Half(1560), -- 5 1/2 x 8 1/2
        letterPlus(1808),  -- 8.5x12/69 inch
        kai8(2051),  -- for MFP
        kai16(2052),  -- for MFP
        kai32(2053),  -- for MFP
        kai8P(2055),  -- for Printer
        kai16P(2056),  -- for Printer
        kai32P(2057),  -- for Printer
        ra0(2304),
        ra1(2305),
        ra2(2306),
        ra3(2307),
        ra4(2308),
        sra0(2320),
        sra1(2321),
        sra2(2322),
        sra3(2323),
        sra4(2324),
        choukei3(2562),
        choukei4(2564),
        kakukei2(2578),
        youkei1(2592),
        youkei2(2593),
        youkei4(2594),
        youkei6(2595),
        dl(2826),
        envMonarch(3073),
        envCom10(3074),
        envPersonal(3121),
        japaneseDoublePostCard(3586),
        japanesePostCard(3587),
        postCard4x6(3602),
        a3Wide(8451),
        a4Wide(8452),
        a5Wide(8453),
        b4Wide(8708),
        b5Wide(8709),
        na11x17Wide(9733),
        na8Halfx14Wide(9739), -- 8 1/2 x 14
        na8Halfx11Wide(9743), -- 8 1/2 x 11
        na5Halfx8HalfWide(9752), --5 1/2 x 8 1/2
        a3Index(16643),
        a4Index(16644),
        b4Index(16900),
        b5Index(16901),
        na8Halfx14Index(17931), -- 8 1/2 x 14
        na8Halfx11Index(17935)  -- 8 1/2 x 11
        }
    ACCESS    read-only
    STATUS    mandatory
    DESCRIPTION
        "
        The paper/picture size of Job.
        In case of output job, this value shows output paper size.
        Incase of scanned job,  this value shows the size of picture.
        In Job of mixed size, the last page or first page should be displayed.
        "
    ::= { kmJmJobEntry 15 }

kmJmJobDestination  OBJECT-TYPE
    SYNTAX    OCTET STRING(SIZE(0..255))
    ACCESS    read-only
    STATUS    mandatory
    DESCRIPTION
        "
        The destination of job.
        When jobs are copying or printing, show Bin Name.
        When jobs are sending, show mail address or FAX number.
        Manage one as another job at multi-sending job of G3FAX.
        Moreover, when jobs are multi-sending, may show all mail address or all FAX number.
        "
    ::= { kmJmJobEntry 16 }

kmJmJobDriverJobID  OBJECT-TYPE
    SYNTAX    OCTET STRING(SIZE(0..31))
    ACCESS    read-only
    STATUS    mandatory
    DESCRIPTION
        "
        DriverJobID is include in data of PC print.
        If job has no Driver Job ID (Copy job etc.)job,
        this value should be null.
        "
    ::= { kmJmJobEntry 17 }

kmJmJobOutputMode  OBJECT-TYPE
    SYNTAX    INTEGER {
            other (0),
            unknown(1),

            pageDivision (11),
            binaryDivision (12),
            urlNotification (13),

            normalPrint (21),
            electricSort (22),
            securePrint (24),

            receivePrint (31),
            store (32),
            forwarding (33)
            }
    ACCESS    read-only
    STATUS    optional
    DESCRIPTION
        "
        The output mode of job.
        "
    ::= { kmJmJobEntry 18 }

kmJmJobDataSize  OBJECT-TYPE
    SYNTAX    Integer32
    ACCESS    read-only
    STATUS    optional
    DESCRIPTION
        "
        The data size of job. A unit is KByte.
        In case of printing job, this value should be the size of 
        printing date.
        In case of send job, this value should be not the size of picture
        but the size of transferred data.

        When the device cannot detect data size, this value should be (-2).
        "
    ::= { kmJmJobEntry 19 }

kmJmJobColorMode  OBJECT-TYPE
    SYNTAX    INTEGER {
                other (0),
                unknown (1),
                color (2),
                grayScale (3),
                blackWhite (4)
              }
    ACCESS    read-only
    STATUS    optional
    DESCRIPTION
        "
        The type of color mode.
        "
    ::= { kmJmJobEntry 20 }

kmJmJobFormat  OBJECT-TYPE
    SYNTAX    INTEGER {
                other (0),
                unknown (1),
                raw (2),
                tiff (3),
                tiff-MH (4),
                tiff-MR (5),
                tiff-MMR (6),
                jpeg (7),
                pdf (8),
                pcl (9),
                postScript (10),
                gdi (11),
                linePrinter (12)
              }
    ACCESS    read-only
    STATUS    optional
    DESCRIPTION
        "
        The data format of job.
        "
    ::= { kmJmJobEntry 21 }

kmJmJobXResolution  OBJECT-TYPE
    SYNTAX    INTEGER
    ACCESS    read-only
    STATUS    optional
    DESCRIPTION
        "
        Resolution of the X direction of Job.
        A unit is dpi.
        "
    ::= { kmJmJobEntry 22 }

kmJmJobYResolution  OBJECT-TYPE
    SYNTAX    INTEGER
    ACCESS    read-only
    STATUS    optional
    DESCRIPTION
        "
        Resolution of the Y direction of Job.
        A unit is dpi.
        "
    ::= { kmJmJobEntry 23 }

kmJmJobDuplex  OBJECT-TYPE
    SYNTAX    INTEGER {
                on (1),
                off (2)
              }
    ACCESS    read-only
    STATUS    optional
    DESCRIPTION
        "
        A duplex setting of job.
        "
    ::= { kmJmJobEntry 24 }


kmJmJobFinishing  OBJECT-TYPE
    SYNTAX    OCTET STRING(SIZE(0..15))
    ACCESS    read-only
    STATUS    optional
    DESCRIPTION
        "
        Finishing processing mode of Job.
        "
    ::= { kmJmJobEntry 25 }

kmJmJobOutputPages  OBJECT-TYPE
    SYNTAX    Integer32
    ACCESS    read-only
    STATUS    optional
    DESCRIPTION
        "
        The page numbers which the output ended in Job.
        If a device can not recognize this information,
        '-2'(Not Support) should be implemented.
        "
    ::= { kmJmJobEntry 26 }

kmJmJobOutputSheets  OBJECT-TYPE
    SYNTAX    Integer32
    ACCESS    read-only
    STATUS    optional
    DESCRIPTION
        "
        The sheets numbers which the output ended in Job.
        If a device can not recognize this information,
        '-2'(Not Support) should be implemented.
        "
    ::= { kmJmJobEntry 27 }

kmJmJobMediaType  OBJECT-TYPE
    SYNTAX    INTEGER {
              other(0),
              normalPaper(1),
              recycledpaper1(17),
              recyclepdaper2(18),
              finePaper1(24),
              finePaper2(25),
              postCard1(33),
              envelope(40),
              ohp(65),
              ohp2(66),
              labelPaper(69),
              tracePaper(70),
              basePaper1(81),
              basePaper2(82),
              coatedPaper1(88),
              coatedPaper2(89),
              bookPaper(97),
              roughPaper(98),
              blankInsertSheet(99),
              userDefined1(113),
              userDefined2(114),
              userDefined3(115),
              glossy(129),
              heavyGlossy(130),
              highGloss(131),
              tabPaper(161),
              letterHead(162),
              formatedPaper(164),
              specialPaper1(177),
              specialPaper2(178),
              printedPaper1(184),
              printedPaper2(185),
              thinPaper1(209),
              thinPaper2(210),
              thinPaper3(211),
              thinPaper4(212),
              thinPaper5(213),
              thickPaper1(225),
              thickPaper2(226),
              thickPaper3(227),
              thickPaper4(228),
              thickPaper5(229),
              userCustom1(241),
              userCustom2(242),
              userCustom3(243),
              userCustom4(244),
              userCustom5(245)
              }
    ACCESS    read-only
    STATUS    optional
    DESCRIPTION
        "
        The media type of job.
        "
    ::= { kmJmJobEntry 28 }

   kmJmJobPaperAttribute  OBJECT-TYPE
    SYNTAX    INTEGER {
                   other (0),
                   unknown(2)
                  }
    ACCESS    read-only
    STATUS    optional
    DESCRIPTION
        "
        The paper attribute of job.
        "
    ::= { kmJmJobEntry 29 }

END
