------------------------------------------------------------------------
-- @(#)$Id $
-- Copyright 1994 by Fore Systems, Inc.

Fore-E3-MIB DEFINITIONS ::= BEGIN

IMPORTS
	Counter, Gauge, IpAddress, TimeTicks	FROM RFC1155-SMI
	OBJECT-TYPE				FROM RFC1212
	asx					FROM Fore-Switch-MIB;
	

------------------------------------------------------------------------
-- The implementation of the foreE3 tables is mandatory
-- for all switches that have E3 port module.

foreE3			OBJECT IDENTIFIER ::= { asx 5 }
e3ConfGroup		OBJECT IDENTIFIER ::= { foreE3 1 }
e3StatsGroup		OBJECT IDENTIFIER ::= { foreE3 2 }


------------------------------------------------------------------------
-- The E3 configuration Group

e3ConfTable OBJECT-TYPE
	SYNTAX	SEQUENCE OF E3ConfEntry
	ACCESS	not-accessible
	STATUS	mandatory
	DESCRIPTION
		"A table of E3 switch port configuration information."
	::= { e3ConfGroup 1 }

e3ConfEntry OBJECT-TYPE
	SYNTAX	E3ConfEntry
	ACCESS	not-accessible
	STATUS	mandatory
	DESCRIPTION
		"A table entry containing E3 configuration information for each port. Not 
		all RFC1407 configuration table variables are included, and some are modified."
	INDEX	{ e3ConfBoard, e3ConfModule, e3ConfPort }
	::= { e3ConfTable 1 }

E3ConfEntry ::=
	SEQUENCE {
		e3ConfBoard		INTEGER,
		e3ConfModule		INTEGER,
		e3ConfPort		INTEGER,
		e3LineType		INTEGER,		
		e3LineCoding		INTEGER,
		e3SendCode		INTEGER,
		e3ReceiveCode		INTEGER,
		e3LoopbackConfig	INTEGER,
		e3TxClockSource	        INTEGER,
		e3RxScrambling		INTEGER,
		e3TxScrambling		INTEGER,
		e3LineStatus		INTEGER,
		e3IdleUnassignedCells   INTEGER
	}		


e3ConfBoard OBJECT-TYPE
	SYNTAX	INTEGER
	ACCESS	read-only
	STATUS	mandatory
	DESCRIPTION
		"The index of this port's switch board."
	::= { e3ConfEntry 1 }

e3ConfModule OBJECT-TYPE
	SYNTAX	INTEGER
	ACCESS	read-only
	STATUS	mandatory
	DESCRIPTION
		"The network module of this port."
	::= { e3ConfEntry 2 }

e3ConfPort OBJECT-TYPE
	SYNTAX	INTEGER
	ACCESS	read-only
	STATUS	mandatory
	DESCRIPTION
		"The number of this port."
	::= { e3ConfEntry 3 }

e3LineType OBJECT-TYPE
	SYNTAX	INTEGER {
                e3OtherLineType (1),
                e3Framed (2),
                e3Plcp (3)
		} 
	ACCESS	read-write
	STATUS	mandatory
	DESCRIPTION
                "This variable indicates the type of cell delineation being used.  
		The e3Plcp(3) value indicates cell delineation according to CCITT 
		G.751 using PLCP (Physical Layer Converhence Protocol) framing, 
		while e3Framed(2) indicates HCS (Header Check Sequence) based framing. 
		This variable is defined in the rfc1407 configuration table as 
		dsx3LineType. According to RFC1407, the different values are:
		e3Framed(2)   specification: CCITT G.751
		e3Plcp(3)     specification: ETSI T/NA(91)18."
	DEFVAL { 2 }
	::= { e3ConfEntry 4 }

e3LineCoding OBJECT-TYPE
	SYNTAX	INTEGER {
                e3OtherLineCoding (1),
		e3HDB3 (2)
		}
	ACCESS	read-only
	STATUS	mandatory
	DESCRIPTION

		"This variable describes the variety of Zero Code suppression used on this 
                interface, which in turn affects a number of its characteristics. e3HDB3 (1) 
                refers to the use of specified pattern of normal bits and bipolar violations 
                which are used to replaced sequences of zero bits of specified length. This 
                variable is defined in the rfc1407 configuration table as dsx3LineCoding."

	DEFVAL { 2 }
	::= { e3ConfEntry 5 }

e3SendCode OBJECT-TYPE
	SYNTAX	INTEGER {
		e3SendNoCode (1),
		e3SendLineCode (2),
		e3SendPayloadCode (3),
		e3SendResetCode (4),
		e3SendDS1LoopCode (5),
		e3SendTestPattern (6)
		}
	ACCESS	read-write
	STATUS	mandatory
	DESCRIPTION
		"This variable indicates what type of code is being sent across the E3/E3 
		interface by the device. 
		The values mean:
		e3SendNoCode		sending looped or normal data
		e3SendLineCode		sending request for a line loopback
		e3SendPayloadCode	sending a request for a payload loopback (i.e. all 
					DS1/E1 in a E3/E3 frame)
		e3SendResetCode         sending a loopback deactivation request
		e3SendDS1LoopCode	requesting to loopback a particular DS1/E1 within a 
					E3/E3 frame
		e3SendTestPattern	sending a test pattern."
	DEFVAL { 1 }
	::= { e3ConfEntry 6 }

e3ReceiveCode OBJECT-TYPE
	SYNTAX	INTEGER {
		e3ReceiveNoCode (1),
		e3ReceiveLineCode (2),
		e3ReceivePayloadCode (3),
		e3ReceiveResetCode (4),
		e3ReceiveDS1LoopCode (5),
		e3ReceiveTestPattern (6)
		}
	ACCESS	read-only
	STATUS	mandatory
	DESCRIPTION
		"This variable indicates the type of code that was received across the E3/E3 
		interface. 
		The values mean:
		e3ReceiveNoCode	receiving looped or normal data
		e3ReceiveLineCode	receiving request for a line loopback
		e3ReceivePayloadCode	receiving a request for a payload loopback (i.e. all  
					DS1/E1 in a E3/E3 frame)
		e3ReceiveResetCode	receiving a loopback deactivation request
		e3ReceiveDS1LoopCode	receiving a request to loopback a particular DS1/E1 
					within a E3/E3 frame
		e3ReceiveTestPattern	receiving a test pattern."
	DEFVAL { 1 }
	::= { e3ConfEntry 7 }

e3LoopbackConfig OBJECT-TYPE
	SYNTAX	INTEGER {
		e3NoLoop (1), 
		e3CellLoop (2),
		e3PayloadLoop (3),
		e3DiagLoop (4),
                e3LineLoop (5),
		e3OtherLoop (6)
		}
	ACCESS	read-write
	STATUS	mandatory
	DESCRIPTION
		"This variable represents the loopback configuration of the E3 interface. This 
		variable is defined in the rfc1407 configuration table as dsx3LoopbackConfig, 
		with slightly different values.
		e3NoLoop (1) means that the interface is not in a loopback state.
		e3CellLoop (2) means that cells that are processed by the receiving component 
		  are not written into the receive FIFO, but into the transmit FIFO for 
		  retransmission.
		e3PayloadLoop (3) means that the receive signal is looped back for retransmission
		  after it has passed through the port's reframing function.	
		e3DiagLoop (4) means that the transmit data stream is looped back to the receiver.
                e3LineLoop (5) means that the received data stream is reflected back to the sender.
		e3OtherLoop (6) means that the interface is in a loopback that is not defined 
		  here."
	DEFVAL { 1 }
	::= { e3ConfEntry 8 }

e3TxClockSource OBJECT-TYPE
	SYNTAX	INTEGER {
		rxTiming (1),
		localTiming (2)
		}
	ACCESS	read-write
	STATUS	mandatory
	DESCRIPTION
		"The source of the transmit clock."
	DEFVAL { 2 }
	::= { e3ConfEntry 9 }

e3RxScrambling OBJECT-TYPE
	SYNTAX	INTEGER {
		descrambling(1),
		noDescrambling(2)
		}
	ACCESS	read-write
	STATUS	mandatory
	DESCRIPTION
		"This variable indicates whether the information is being descrambled 
		on receiving. It should be set the same as the transmitting side." 
	DEFVAL { 2 }
	::= { e3ConfEntry 10 }

e3TxScrambling OBJECT-TYPE
	SYNTAX	INTEGER {
		scrambling(1),
		noScrambling(2)
		}
	ACCESS	read-write
	STATUS	mandatory
	DESCRIPTION
		"This variable indicates whether the information (48 octet payload) is being 
		scrambled before transmitting. It should be set the same as the receiving side."
	DEFVAL { 2 }
	::= { e3ConfEntry 11 }

e3LineStatus OBJECT-TYPE
	SYNTAX	INTEGER (1..2046)
	ACCESS	read-only
	STATUS	mandatory
	DESCRIPTION
		"This variable indicates the Line Status of the interface. A similar object is
		defined in the rfc1407 configuration table as dsx3LineStatus (the e3RxFERF bit 
		is not defined in rfc1407) . The variable contains loopback state information 
		and failure state information. It is a bit map represented as a sum. The 
		e3NoAlarm should be set if and only if no other flag is set.
		The various bit positions are:
		   1  e3NoAlarm
		   2  e3RxAIS		Receiving AIS failure state
		   4  e3TxAIS		Transmitting AIS
		   8  e3PllcpLOF	Receiving LOF failure state (G.751)
		  16  e3LOS		Receiving LOS failure state
		  32  e3LoopbackState	Looping the received signal
                  64  e3HcsLCD          Loss of Cell Delineation (G.832)
		 128  e3RxFERF		Receiving Far End Receive Failure
		 256  e3OtherFailure	any line status not defined here."
	DEFVAL { 1 }
	::= { e3ConfEntry 12 }

e3IdleUnassignedCells OBJECT-TYPE
	SYNTAX	INTEGER {
		unassigned(1),
		idle(2)
		}
	ACCESS	read-write
	STATUS	mandatory
	DESCRIPTION
		"This variable indicates the types of cells that  should be sent 
		in case there is no real data to send. According to the ATM Forum, 
		Unassigned cells should be sent (octet 1-3 are 0's, octet 4 is 
		0000xxx0, where x is 'don't care'). According to the CCITT 
		specifications, Idle cells should be sent (everything is '0' except 
		for the CLP bit which is '1'). By default, unassigned cells are 
		transmitted is case there is no data to send."
	DEFVAL { 1 }
	::= { e3ConfEntry 13 }

------------------------------------------------------------------------
-- The E3 Statistics Group

e3FramingTable OBJECT-TYPE
	SYNTAX	SEQUENCE OF E3FramingEntry
	ACCESS	not-accessible
	STATUS	mandatory
	DESCRIPTION
		"A table of E3 framing statistics information."
	::= { e3StatsGroup 1 }

e3FramingEntry OBJECT-TYPE
	SYNTAX	E3FramingEntry
	ACCESS	not-accessible
	STATUS	mandatory
	DESCRIPTION
		"A table entry containing E3 framing statistics information."
	INDEX	{ e3FramingBoard, e3FramingModule, e3FramingPort }
	::= { e3FramingTable 1 }

E3FramingEntry ::=
	SEQUENCE {
		e3FramingBoard		INTEGER,
		e3FramingModule         INTEGER,
		e3FramingPort		INTEGER,

		e3FramingLOSs		Counter,
		e3FramingLCVs		Counter,
		e3FramingFERRs		Counter,
		e3FramingOOFs		Counter,
		e3FramingFERFs		Counter,
		e3FramingAISs		Counter,
		e3FramingBIP8s  	Counter,

		e3FramingFEBEs		Counter
	}

e3FramingBoard OBJECT-TYPE
	SYNTAX	INTEGER
	ACCESS	read-only
	STATUS	mandatory
	DESCRIPTION
		"The index of this port's switch board."
	::= { e3FramingEntry 1 }

e3FramingModule OBJECT-TYPE
	SYNTAX	INTEGER
	ACCESS	read-only
	STATUS	mandatory
	DESCRIPTION
		"The network module of this port."
	::= { e3FramingEntry 2 }

e3FramingPort OBJECT-TYPE
	SYNTAX	INTEGER
	ACCESS	read-only
	STATUS	mandatory
	DESCRIPTION
		"The number of this port."
	::= { e3FramingEntry 3 }

e3FramingLOSs OBJECT-TYPE
	SYNTAX	Counter
	ACCESS	read-only
	STATUS	mandatory
	DESCRIPTION
		"The number of seconds in which Loss Of Signal (LOS) errors were detected 
		by the E3 Receive Framer block."
	::= { e3FramingEntry 4 }

e3FramingLCVs OBJECT-TYPE
	SYNTAX	Counter
	ACCESS	read-only
	STATUS	mandatory
	DESCRIPTION
		"The number of Line Code Violations (LCV) that were detected by the E3 
		Receive Framer block."
	::= { e3FramingEntry 5 }

e3FramingFERRs OBJECT-TYPE
	SYNTAX	Counter
	ACCESS	read-only
	STATUS	mandatory
	DESCRIPTION
		"Number of E3 framing error (FERR) events."
	::= { e3FramingEntry 6 }

e3FramingOOFs OBJECT-TYPE
	SYNTAX	Counter
	ACCESS	read-only
	STATUS	mandatory
	DESCRIPTION
		"Number of seconds when E3 Out Of Frame (OOF) error events."
	::= { e3FramingEntry 7 }

e3FramingFERFs OBJECT-TYPE
	SYNTAX	Counter
	ACCESS	read-only
	STATUS	mandatory
	DESCRIPTION
                "In a G.832 (e3LineType == e3Framed) configured port, this variable relects 
                the number of seconds when Far End Receive Failures were experienced.  
                In G.751 (e3LineType == e3Plcp) it is the number of  Remote Alarm Indications."
	::= { e3FramingEntry 8 }

e3FramingAISs OBJECT-TYPE
	SYNTAX	Counter
	ACCESS	read-only
	STATUS	mandatory
	DESCRIPTION
		"The number of seconds in which Alarm Indication Signals (AIS) were 
		detected by the E3 Receive Framer block. AIS indicates that an upstream 
		failure has been detected by the far end."
	::= { e3FramingEntry 9 }

e3FramingBIP8s OBJECT-TYPE
	SYNTAX	Counter
	ACCESS	read-only
	STATUS	mandatory
	DESCRIPTION
		"The number of E3 G.832 BIP-8 errors.  This counter is
only valid in G.832."
	::= { e3FramingEntry 10 }


e3FramingFEBEs OBJECT-TYPE
	SYNTAX	Counter
	ACCESS	read-only
	STATUS	mandatory
	DESCRIPTION
		"Number of E3 far end block error (FEBE) events."
	::= { e3FramingEntry 11 }

------------------------------------------------------------------------

e3PlcpTable OBJECT-TYPE
	SYNTAX	SEQUENCE OF E3PlcpEntry
	ACCESS	not-accessible
	STATUS	mandatory
	DESCRIPTION
		"A table of E3 Physical Layer Convergence Protocol (PLCP) statistics 
                information.  These statistics are only valid when the G.751 (PLCP) based 
                framing is being used by the E3.  They are not meaningful when G.832 HCS-based 
                framing is being used.  Check e3LineType for the current framing option."
	::= { e3StatsGroup 2 }

e3PlcpEntry OBJECT-TYPE
	SYNTAX	E3PlcpEntry
	ACCESS	not-accessible
	STATUS	mandatory
	DESCRIPTION
		"A table entry containing E3 PLCP statistics information."
	INDEX	{ e3PlcpBoard, e3PlcpModule, e3PlcpPort }
	::= { e3PlcpTable 1 }

E3PlcpEntry ::=
	SEQUENCE {
		e3PlcpBoard		INTEGER,
		e3PlcpModule		INTEGER,
		e3PlcpPort		INTEGER,

		e3PlcpFERRs		Counter,
		e3PlcpLOFs		Counter,
		e3PlcpBIP8s		Counter,
		e3PlcpFEBEs		Counter,
		e3PlcpYellows		Counter
	}

e3PlcpBoard OBJECT-TYPE
	SYNTAX	INTEGER
	ACCESS	read-only
	STATUS	mandatory
	DESCRIPTION
		"The index of this port's switch board."
	::= { e3PlcpEntry 1 }

e3PlcpModule OBJECT-TYPE
	SYNTAX	INTEGER
	ACCESS	read-only
	STATUS	mandatory
	DESCRIPTION
		"The network module of this port."
	::= { e3PlcpEntry 2 }

e3PlcpPort OBJECT-TYPE
	SYNTAX	INTEGER
	ACCESS	read-only
	STATUS	mandatory
	DESCRIPTION
		"The number of this port."
	::= { e3PlcpEntry 3 }

e3PlcpFERRs OBJECT-TYPE
	SYNTAX	Counter
	ACCESS	read-only
	STATUS	mandatory
	DESCRIPTION
		"Number of Physical Layer Convergence Protocol (PLCP) octet error events."
	::= { e3PlcpEntry 4 }

e3PlcpLOFs OBJECT-TYPE
	SYNTAX	Counter
	ACCESS	read-only
	STATUS	mandatory
	DESCRIPTION
		"The number of seconds in which Loss Of Frame (LOF) errors were detected 
		by the PLCP (Physical Layer Convergence Protocol) receiver. LOF is declared 
		when an Out-Of-Frame state persists for more than 1ms. LOF is removed when 
		in-frame state persists for more than 12ms."
	::= { e3PlcpEntry 5 }

e3PlcpBIP8s OBJECT-TYPE
	SYNTAX	Counter
	ACCESS	read-only
	STATUS	mandatory
	DESCRIPTION
		"Number of BIP-8 (Bit Interleaved Parity - 8) error events. The BIP-8 is 
		calculated over the Path Overhead field and the associated ATM cell of the 
		previous frame. A BIP-N is a method of error monitoring. An N bit code is 
		generated by the transmitting equipment in such a manner that the first bit 
		of the code provides even parity over the first bit of all N-bit sequences 
		in the previous VT SPE, the second bit provides even parity over the second 
		bits of all N-bit sequences within the specified portion, etc."
	::= { e3PlcpEntry 6 }

e3PlcpFEBEs OBJECT-TYPE
	SYNTAX	Counter
	ACCESS	read-only
	STATUS	mandatory
	DESCRIPTION
		"Number of ATM Far End Block Error (FEBE) events."
	::= { e3PlcpEntry 7 }

e3PlcpYellows OBJECT-TYPE
	SYNTAX	Counter
	ACCESS	read-only
	STATUS	mandatory
	DESCRIPTION
		"The number of seconds in which Yellow alarm errors were detected by the 
		PLCP (Physical Layer Convergence Protocol) receiver. Yellow alarm is asserted 
		when 10 consecutive yellow signal bits are set to logical 1. Yellow signals 
		are used to alert upstream terminals of a downstream failure in order to 
		initiate trunk conditioning on the failure circuit."
	::= { e3PlcpEntry 8 }

------------------------------------------------------------------------

e3AtmTable OBJECT-TYPE
	SYNTAX	SEQUENCE OF E3AtmEntry
	ACCESS	not-accessible
	STATUS	mandatory
	DESCRIPTION
		"A table of E3 ATM statistics information."
	::= { e3StatsGroup 3 }

e3AtmEntry OBJECT-TYPE
	SYNTAX	E3AtmEntry
	ACCESS	not-accessible
	STATUS	mandatory
	DESCRIPTION
		"A table entry containing E3 ATM statistics information."
	INDEX	{ e3AtmBoard, e3AtmModule, e3AtmPort }
	::= { e3AtmTable 1 }

E3AtmEntry ::=
	SEQUENCE {
		e3AtmBoard		INTEGER,
		e3AtmModule		INTEGER,
		e3AtmPort		INTEGER,

		e3AtmHCSs		Counter,
		e3AtmRxCells		Counter,
		e3AtmTxCells		Counter
	}

e3AtmBoard OBJECT-TYPE
	SYNTAX	INTEGER
	ACCESS	read-only
	STATUS	mandatory
	DESCRIPTION
		"The index of this port's switch board."
	::= { e3AtmEntry 1 }

e3AtmModule OBJECT-TYPE
	SYNTAX	INTEGER
	ACCESS	read-only
	STATUS	mandatory
	DESCRIPTION
		"The network module of this port."
	::= { e3AtmEntry 2 }

e3AtmPort OBJECT-TYPE
	SYNTAX	INTEGER
	ACCESS	read-only
	STATUS	mandatory
	DESCRIPTION
		"The number of this port."
	::= { e3AtmEntry 3 }

e3AtmHCSs OBJECT-TYPE
	SYNTAX	Counter
	ACCESS	read-only
	STATUS	mandatory
	DESCRIPTION
		"Number of header check sequence (HCS) error events. The HCS is a CRC-8 
		calculation over the first 4 octets of the ATM cell header."
	::= { e3AtmEntry 4 }

e3AtmRxCells OBJECT-TYPE
	SYNTAX	Counter
	ACCESS	read-only
	STATUS	mandatory
	DESCRIPTION
		"Number of ATM cells that were received."
	::= { e3AtmEntry 5 }

e3AtmTxCells OBJECT-TYPE
	SYNTAX	Counter
	ACCESS	read-only
	STATUS	mandatory
	DESCRIPTION
		"Number of non-null ATM cells that were transmitted."
	::= { e3AtmEntry 6 }

END
