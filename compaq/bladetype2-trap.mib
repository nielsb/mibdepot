-- COPYRIGHT NOTICE
-- Copyright (c) Hewlett Packard Company, 2003
-- All rights reserved
--
--
-- HISTORY
-- $Log: bladetype2-trap.mib,v $
-- Revision 1.4  2005/06/15 14:09:51  kallio
-- Updated mibs for Gbe2.2.0
--
-- Revision 1.3  06/14/2005  AlpoK
-- Changes from Bruce Guertler
-- Revision 1.17.6.1  2005/05/23 21:10:23  bruceg
-- GbE2 2.2.0
--
-- Revision submit_zoe_1563/1 2005/03/24 13:36:55 coman
-- Adding changes for failover
-- 
-- Revision 1.2  2005/02/10 15:55:35  aminchew
-- Changes from Bruce Guertler.
-- Revision submit_zoe_500/1 2003/07/07 23:50:57 tolin
-- Fixes Defect #702393: Add Severity level for Bert generated traps.
--
-- Revision submit_zoe_496/1 2003/07/07 23:10:16 tolin
-- Fixes Defect #706213: Correctly use the name bt2SwFanFailureFixed as
-- the trap description name.
--
-- Revision submit_zoe_464/1 2003/06/23 23:40:36 smiao
-- Fixed Q00695674. Dispalyed trap OID correctly.
--
-- Revision submit_zoe_442/1 2003/06/13 03:14:45 tolin
-- Fixes Defect #650736: Correct the description of Rack Location change trap
-- description to reference rac-loc instead of DefGwUp
--
-- Revision submit_zoe_428/1 2003/06/10 18:05:49 smiao
-- Fixed the compiler error.
--
-- Revision submit_zoe_427/1 2003/06/09 23:59:55 smiao
-- Checked in for enviromental trap definitions.
--
-- Revision submit_zoe_423/1 2003/06/06 21:06:27 smiao
-- Fixed Q00673523. Added trap and syslog for firmware download.
--
-- Revision submit_zoe_419/1 2003/06/05 22:35:42 smiao
-- Fixed Q00673526. Added traps for configuration changes.
--
-- Revision submit_zoe_397/1 2003/05/29 01:12:07 smiao
-- Fixed Q00650736. Put correct description for bt2SwitchRackLoactionChange.
--
-- Revision submit_zoe_186/1 2003/02/18 22:22:13 smiao
-- Added rack location change trap.
--
-- Revision submit_zoe_181/1 2003/02/14 18:18:00 smiao
-- Adjusted MIB nodes for HP MIB tree.
--
-- Revision submit_zoe_165/1 2003/02/04 23:05:49 smiao
-- Created MIB files for HP BERT project.
--
-- $EndLog$

BLADETYPE2-TRAP-MIB DEFINITIONS ::= BEGIN

IMPORTS
    TRAP-TYPE
        FROM RFC-1215
    sysName, sysLocation, sysContact, DisplayString
        FROM RFC1213-MIB
    hpSwitchBladeType2-Mgmt
        FROM HP-SWITCH-PL-MIB
    agSlotNumber, agRackId, agChassis
        FROM BLADETYPE2-SWITCH-MIB
    ipCurCfgGwIndex, ipCurCfgGwAddr,
    vrrpCurCfgVirtRtrIndx, vrrpCurCfgVirtRtrAddr,
    vrrpCurCfgIfIndx, vrrpCurCfgIfPasswd
        FROM BLADETYPE2-NETWORK-MIB;

bt2Traps OBJECT IDENTIFIER ::= { hpSwitchBladeType2-Mgmt 7 }

-- SECTION 2:  Temporary Object Definitions Used In Traps

bt2SwTrapDisplayString OBJECT-TYPE
        SYNTAX  DisplayString (SIZE(0..255))
        ACCESS  read-only
        STATUS  mandatory
        DESCRIPTION
                "Temporary string object used to store information being sent
                 in an Bladetype2 Switch trap."
        ::= { bt2Traps 1000 }

bt2SwTrapRate OBJECT-TYPE
    SYNTAX  INTEGER
    ACCESS  read-only
    STATUS  mandatory
    DESCRIPTION
        "Temporary integer object used to store information being sent
         in an Bladetype2 Switch trap."
    ::= { bt2Traps 1001 }

-- SECTION 3:  Trap Definitions

bt2SwPrimaryPowerSupplyFailure TRAP-TYPE
        ENTERPRISE      bt2Traps
        DESCRIPTION
                "A bt2SwPrimaryPowerSupplyFailure trap signifies that the
       primary power supply failed."

      --#SEVERITY CRITICAL

        ::= 1   -- 0x01

bt2SwDefGwUp TRAP-TYPE
        ENTERPRISE      bt2Traps
        VARIABLES       { ipCurCfgGwIndex,
                          ipCurCfgGwAddr,
                          sysName, sysLocation, sysContact }
        DESCRIPTION
                "A bt2SwDefGwUp trap signifies that the default
                 gateway is alive."

      --#SEVERITY INFORMATIONAL

        ::= 2   -- 0x02

bt2SwDefGwDown TRAP-TYPE
        ENTERPRISE      bt2Traps
        VARIABLES       { ipCurCfgGwIndex,
                          ipCurCfgGwAddr,
                          sysName, sysLocation, sysContact }
        DESCRIPTION
                "A bt2SwDefGwDown trap signifies that the default
                 gateway is down."

      --#SEVERITY INFORMATIONAL

        ::= 3   -- 0x03

bt2SwDefGwInService TRAP-TYPE
        ENTERPRISE      bt2Traps
        VARIABLES       { ipCurCfgGwIndex,
                          ipCurCfgGwAddr,
                          sysName, sysLocation, sysContact }
        DESCRIPTION
                "A bt2SwDefGwEnabled trap signifies that the default
                 gateway is up and in service."

      --#SEVERITY INFORMATIONAL

        ::= 4   -- 0x04

bt2SwDefGwNotInService TRAP-TYPE
        ENTERPRISE      bt2Traps
        VARIABLES       { ipCurCfgGwIndex,
                          ipCurCfgGwAddr,
                          sysName, sysLocation, sysContact }
        DESCRIPTION
                "A bt2SwDefGwDisabled trap signifies that the default
                 gateway is alive but not in service."

      --#SEVERITY INFORMATIONAL

        ::= 5   -- 0x05


bt2SwVrrpNewMaster TRAP-TYPE
        ENTERPRISE      bt2Traps
        VARIABLES       { vrrpCurCfgVirtRtrIndx,
                          vrrpCurCfgVirtRtrAddr,
                          sysName, sysLocation, sysContact }
        DESCRIPTION
                "The bt2SwVrrpNewMaster trap indicates that the sending agent
       has transitioned to 'Master' state."

      --#SEVERITY INFORMATIONAL

        ::= 16 -- 0x10

bt2SwVrrpNewBackup TRAP-TYPE
        ENTERPRISE      bt2Traps
        VARIABLES       { vrrpCurCfgVirtRtrIndx,
                          vrrpCurCfgVirtRtrAddr,
                          sysName, sysLocation, sysContact }
        DESCRIPTION
                "The bt2SwVrrpNewBackup trap indicates that the sending agent
       has transitioned to 'Backup' state."

      --#SEVERITY INFORMATIONAL

        ::= 17 -- 0x11

bt2SwVrrpAuthFailure TRAP-TYPE
        ENTERPRISE      bt2Traps
        VARIABLES       { vrrpCurCfgIfIndx,
                          vrrpCurCfgIfPasswd,
                          sysName, sysLocation, sysContact }
        DESCRIPTION
                "A bt2SwVrrpAuthFailure trap signifies that a packet has
       been received from a router whose authentication key
       or authentication type conflicts with this router's
       authentication key or authentication type. Implementation
       of this trap is optional."

      --#SEVERITY MAJOR

        ::= 18 -- 0x12

bt2SwLoginFailure TRAP-TYPE
        ENTERPRISE      bt2Traps
        VARIABLES       { bt2SwTrapDisplayString,
                          sysName, sysLocation, sysContact }
        DESCRIPTION
                "A bt2SwLoginFailure trap signifies that someone failed to
                 enter a valid username/password combination."

      --#SEVERITY MAJOR

        ::= 19 -- 0x13

bt2SwTempExceedThreshold TRAP-TYPE
        ENTERPRISE      bt2Traps
        VARIABLES       { bt2SwTrapDisplayString,
                          sysName, sysLocation, sysContact }
        DESCRIPTION
              "A bt2SwTempExceedThreshold trap signifies that the
               switch temperature has exceeded maximum safety limits."

      --#SEVERITY CRITICAL

        ::= 22   -- 0x16

bt2SwRackLocationChange TRAP-TYPE
        ENTERPRISE      bt2Traps
        VARIABLES       { agRackId,
                          agChassis,
           agSlotNumber,
                          sysName, sysLocation, sysContact }
        DESCRIPTION
                "A bt2SwRackLocationChange trap signifies that the rack
            location has been changed."

      --#SEVERITY INFORMATIONAL

        ::= 26   -- 0x1A

bt2SwApplyComplete TRAP-TYPE
        ENTERPRISE      bt2Traps
        VARIABLES       { bt2SwTrapDisplayString,
                          sysName, sysLocation, sysContact }
        DESCRIPTION
                "A bt2SwApplyComplete signifies that new configuration
       has been applied."

      --#SEVERITY INFORMATIONAL

        ::= 27 -- 0x1B

bt2SwSaveComplete TRAP-TYPE
        ENTERPRISE      bt2Traps
        VARIABLES       { bt2SwTrapDisplayString,
                          sysName, sysLocation, sysContact }
        DESCRIPTION
                "A bt2SwApplyComplete signifies that new configuration
       has been saved."

      --#SEVERITY INFORMATIONAL

        ::= 28 -- 0x1C

bt2SwFwDownloadSucess TRAP-TYPE
        ENTERPRISE      bt2Traps
        VARIABLES       { bt2SwTrapDisplayString,
                          sysName, sysLocation, sysContact }
        DESCRIPTION
                "A bt2SwFwDownloadSuccess signifies that firmware
       has been downloaded to [image1|image2|boot image]."

      --#SEVERITY INFORMATIONAL

        ::= 29 -- 0x1D

bt2SwFwDownloadFailure TRAP-TYPE
        ENTERPRISE      bt2Traps
        VARIABLES       { bt2SwTrapDisplayString,
                          sysName, sysLocation, sysContact }
        DESCRIPTION
                "A bt2SwFwDownloadFailure signifies that firmware
       downloaded failed to [image1|image2|boot image]."

      --#SEVERITY MINOR

        ::= 30 -- 0x1E

bt2SwTempReturnThreshold TRAP-TYPE
        ENTERPRISE      bt2Traps
        VARIABLES       { bt2SwTrapDisplayString,
                          sysName, sysLocation, sysContact }
        DESCRIPTION
              "A bt2SwTempReturnThreshold trap signifies that the
               switch temperature has returned below maximum safety limits."

      --#SEVERITY INFORMATIONAL

        ::= 31   -- 0x1F

bt2SwFanFailure TRAP-TYPE
        ENTERPRISE      bt2Traps
        VARIABLES       { bt2SwTrapDisplayString,
                          sysName, sysLocation, sysContact }
        DESCRIPTION
              "A bt2SwFanFailure trap signifies that the
               fan failure has been detected."

      --#SEVERITY MAJOR

        ::= 32   -- 0x20

bt2SwFanFailureFixed TRAP-TYPE
        ENTERPRISE      bt2Traps
        VARIABLES       { bt2SwTrapDisplayString,
                          sysName, sysLocation, sysContact }
        DESCRIPTION
              "A bt2SwFanFailureFixed trap signifies that the
               fan failure has been fixed."

      --#SEVERITY INFORMATIONAL

        ::= 33   -- 0x21

bt2SwUfdfoLtMFailure TRAP-TYPE
        ENTERPRISE      bt2Traps
        VARIABLES       { bt2SwTrapDisplayString,
                          sysName, sysLocation, sysContact }
        DESCRIPTION
                "A bt2SwUfdfoLtMFailure trap signifies that a LtM link is down."

                --#SEVERITY MAJOR

        ::= 34 -- 0x22

bt2SwUfdfoLtMUP TRAP-TYPE
        ENTERPRISE      bt2Traps
        VARIABLES       { bt2SwTrapDisplayString,
                          sysName, sysLocation, sysContact }
        DESCRIPTION
                "A bt2SwUfdfoLtMUP trap signifies that a LtM link is up."

                --#SEVERITY INFORMATIONAL

        ::= 35 -- 0x23

END
