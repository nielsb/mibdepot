-- *********************************************************************
-- CISCO-FIREPOWER-AP-VNIC-MIB.my
-- 
-- MIB representation of the Cisco Firepower
-- VNIC management information model package
-- 
-- Created July 2022 by Charles Bullis
-- 
-- Copyright (c) 2005-2022 Cisco Systems, Inc. All rights reserved.
-- 
-- *********************************************************************

CISCO-FIREPOWER-AP-VNIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApDpsecForgedTransmit,
    CfprApFabricHostPortId,
    CfprApFabricSSAPortType,
    CfprApFabricVlanSharingType,
    CfprApLsConfigState,
    CfprApNetworkSwitchId,
    CfprApNwctrlAdminState,
    CfprApNwctrlLinkFailAction,
    CfprApNwctrlRegistrationMode,
    CfprApPolicyPolicyOwner,
    CfprApVmMgmtPlane,
    CfprApVnicAEtherIfType,
    CfprApVnicAFcIfType,
    CfprApVnicAIpcIfType,
    CfprApVnicAScsiIfType,
    CfprApVnicAppRole,
    CfprApVnicConfigIssues,
    CfprApVnicConnectionOwner,
    CfprApVnicConnectionType,
    CfprApVnicDefBehType,
    CfprApVnicDefaultAction,
    CfprApVnicDynamicConReqProtection,
    CfprApVnicEtherBaseSwitchId,
    CfprApVnicEtherType,
    CfprApVnicExternalMgmtIPMode,
    CfprApVnicFcBasePersBind,
    CfprApVnicFcBaseType,
    CfprApVnicHostNwIOPerfPref,
    CfprApVnicIPv4DnsPref,
    CfprApVnicIScsiIfDefType,
    CfprApVnicIScsiNodeOwner,
    CfprApVnicIfOperState,
    CfprApVnicInstantiation,
    CfprApVnicIpcType,
    CfprApVnicL2IfSwitchId,
    CfprApVnicLanConnTemplSwitchId,
    CfprApVnicLunId,
    CfprApVnicPortProfileType,
    CfprApVnicProfileConfigQualifier,
    CfprApVnicSanConnTemplTarget,
    CfprApVnicScsiType,
    CfprApVnicTemplateTarget,
    CfprApVnicTemplateType,
    CfprApVnicVhbaBehPolicyType,
    CfprApVnicVirtualizationPreferenceType,
    CfprApVnicVnicBehPolicyType,
    CfprApVnicVnicBootDev,
    CfprApVnicVnicOperHostPort
        FROM CISCO-FIREPOWER-AP-TC-MIB;

cfprApVnicObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        VNIC management information model package"
    ::= { ciscoFirepowerApMIBObjects 83 }

cfprApVnicBootIpPolicyTable OBJECT-TYPE
    SYNTAX           SEQUENCE OF CfprApVnicBootIpPolicyEntry
    MAX-ACCESS       not-accessible
    STATUS           current
    DESCRIPTION
        "Cisco Firepower vnic:BootIpPolicy managed object table"
    ::= { cfprApVnicObjects 1 }

cfprApVnicBootIpPolicyEntry OBJECT-TYPE
    SYNTAX           CfprApVnicBootIpPolicyEntry
    MAX-ACCESS       not-accessible
    STATUS           current
    DESCRIPTION
        "Entry for the cfprApVnicBootIpPolicyTable table."
    INDEX { cfprApVnicBootIpPolicyInstanceId }
    ::= { cfprApVnicBootIpPolicyTable 1 }

CfprApVnicBootIpPolicyEntry ::= SEQUENCE {
    cfprApVnicBootIpPolicyInstanceId                                 CfprApManagedObjectId,
    cfprApVnicBootIpPolicyDn                                         CfprApManagedObjectDn,
    cfprApVnicBootIpPolicyRn                                         SnmpAdminString,
    cfprApVnicBootIpPolicyDescr                                      SnmpAdminString,
    cfprApVnicBootIpPolicyIntId                                      SnmpAdminString,
    cfprApVnicBootIpPolicyName                                       SnmpAdminString,
    cfprApVnicBootIpPolicyPolicyLevel                                Gauge32,
    cfprApVnicBootIpPolicyPolicyOwner                                CfprApPolicyPolicyOwner,
    cfprApVnicBootIpPolicyPoolName                                   SnmpAdminString
}

cfprApVnicBootIpPolicyInstanceId OBJECT-TYPE
    SYNTAX       CfprApManagedObjectId
    MAX-ACCESS   not-accessible
    STATUS       current
    DESCRIPTION
        "Instance identifier of the managed object."
    ::= { cfprApVnicBootIpPolicyEntry 1 }

cfprApVnicBootIpPolicyDn OBJECT-TYPE
    SYNTAX       CfprApManagedObjectDn
    MAX-ACCESS   read-only
    STATUS       current
    DESCRIPTION
        "Cisco Firepower vnic:BootIpPolicy:dn managed object property"
    ::= { cfprApVnicBootIpPolicyEntry 2 }

cfprApVnicBootIpPolicyRn OBJECT-TYPE
    SYNTAX       SnmpAdminString
    MAX-ACCESS   read-only
    STATUS       current
    DESCRIPTION
        "Cisco Firepower vnic:BootIpPolicy:rn managed object property"
    ::= { cfprApVnicBootIpPolicyEntry 3 }

cfprApVnicBootIpPolicyDescr OBJECT-TYPE
    SYNTAX       SnmpAdminString
    MAX-ACCESS   read-only
    STATUS       current
    DESCRIPTION
        "Cisco Firepower vnic:BootIpPolicy:descr managed object property"
    ::= { cfprApVnicBootIpPolicyEntry 4 }

cfprApVnicBootIpPolicyIntId OBJECT-TYPE
    SYNTAX       SnmpAdminString
    MAX-ACCESS   read-only
    STATUS       current
    DESCRIPTION
        "Cisco Firepower vnic:BootIpPolicy:intId managed object property"
    ::= { cfprApVnicBootIpPolicyEntry 5 }

cfprApVnicBootIpPolicyName OBJECT-TYPE
    SYNTAX       SnmpAdminString
    MAX-ACCESS   read-only
    STATUS       current
    DESCRIPTION
        "Cisco Firepower vnic:BootIpPolicy:name managed object property"
    ::= { cfprApVnicBootIpPolicyEntry 6 }

cfprApVnicBootIpPolicyPolicyLevel OBJECT-TYPE
    SYNTAX       Gauge32
    MAX-ACCESS   read-only
    STATUS       current
    DESCRIPTION
        "Cisco Firepower vnic:BootIpPolicy:policyLevel
        managed object property"
    ::= { cfprApVnicBootIpPolicyEntry 7 }

cfprApVnicBootIpPolicyPolicyOwner OBJECT-TYPE
    SYNTAX       CfprApPolicyPolicyOwner
    MAX-ACCESS   read-only
    STATUS       current
    DESCRIPTION
        "Cisco Firepower vnic:BootIpPolicy:policyOwner
        managed object property"
    ::= { cfprApVnicBootIpPolicyEntry 8 }

cfprApVnicBootIpPolicyPoolName OBJECT-TYPE
    SYNTAX       SnmpAdminString
    MAX-ACCESS   read-only
    STATUS       current
    DESCRIPTION
        "Cisco Firepower vnic:BootIpPolicy:poolName managed
        object property"
    ::= { cfprApVnicBootIpPolicyEntry 9 }

cfprApVnicBootTargetTable OBJECT-TYPE
    SYNTAX           SEQUENCE OF CfprApVnicBootTargetEntry
    MAX-ACCESS       not-accessible
    STATUS           current
    DESCRIPTION
        "Cisco Firepower vnic:BootTarget managed object table"
    ::= { cfprApVnicObjects 2 }

cfprApVnicBootTargetEntry OBJECT-TYPE
    SYNTAX           CfprApVnicBootTargetEntry
    MAX-ACCESS       not-accessible
    STATUS           current
    DESCRIPTION
        "Entry for the cfprApVnicBootTargetTable table."
    INDEX { cfprApVnicBootTargetInstanceId }
    ::= { cfprApVnicBootTargetTable 1 }

CfprApVnicBootTargetEntry ::= SEQUENCE {
    cfprApVnicBootTargetInstanceId                                   CfprApManagedObjectId,
    cfprApVnicBootTargetDn                                           CfprApManagedObjectDn,
    cfprApVnicBootTargetRn                                           SnmpAdminString,
    cfprApVnicBootTargetLun                                          SnmpAdminString,
    cfprApVnicBootTargetWwn                                          Unsigned64
}

cfprApVnicBootTargetInstanceId OBJECT-TYPE
    SYNTAX       CfprApManagedObjectId
    MAX-ACCESS   not-accessible
    STATUS       current
    DESCRIPTION
        "Instance identifier of the managed object."
    ::= { cfprApVnicBootTargetEntry 1 }

cfprApVnicBootTargetDn OBJECT-TYPE
    SYNTAX       CfprApManagedObjectDn
    MAX-ACCESS   read-only
    STATUS       current
    DESCRIPTION
        "Cisco Firepower vnic:BootTarget:dn managed object property"
    ::= { cfprApVnicBootTargetEntry 2 }

cfprApVnicBootTargetRn OBJECT-TYPE
    SYNTAX       SnmpAdminString
    MAX-ACCESS   read-only
    STATUS       current
    DESCRIPTION
        "Cisco Firepower vnic:BootTarget:rn managed object property"
    ::= { cfprApVnicBootTargetEntry 3 }

cfprApVnicBootTargetLun OBJECT-TYPE
    SYNTAX       SnmpAdminString
    MAX-ACCESS   read-only
    STATUS       current
    DESCRIPTION
        "Cisco Firepower vnic:BootTarget:lun managed object property"
    ::= { cfprApVnicBootTargetEntry 4 }

cfprApVnicBootTargetWwn OBJECT-TYPE
    SYNTAX       Unsigned64
    MAX-ACCESS   read-only
    STATUS       current
    DESCRIPTION
        "Cisco Firepower vnic:BootTarget:wwn managed object property"
    ::= { cfprApVnicBootTargetEntry 5 }

cfprApVnicConnDefTable OBJECT-TYPE
    SYNTAX           SEQUENCE OF CfprApVnicConnDefEntry
    MAX-ACCESS       not-accessible
    STATUS           current
    DESCRIPTION
        "Cisco Firepower vnic:ConnDef managed object table"
    ::= { cfprApVnicObjects 3 }

cfprApVnicConnDefEntry OBJECT-TYPE
    SYNTAX           CfprApVnicConnDefEntry
    MAX-ACCESS       not-accessible
    STATUS           current
    DESCRIPTION
        "Entry for the cfprApVnicConnDefTable table."
    INDEX { cfprApVnicConnDefInstanceId }
    ::= { cfprApVnicConnDefTable 1 }

CfprApVnicConnDefEntry ::= SEQUENCE {
    cfprApVnicConnDefInstanceId                                      CfprApManagedObjectId,
    cfprApVnicConnDefDn                                              CfprApManagedObjectDn,
    cfprApVnicConnDefRn                                              SnmpAdminString,
    cfprApVnicConnDefFltAggr                                         Unsigned64,
    cfprApVnicConnDefLanConnPolicyName                               SnmpAdminString,
    cfprApVnicConnDefOperLanConnPolicyName                           SnmpAdminString
}

cfprApVnicConnDefInstanceId OBJECT-TYPE
    SYNTAX       CfprApManagedObjectId
    MAX-ACCESS   not-accessible
    STATUS       current
    DESCRIPTION
        "Instance identifier of the managed object."
    ::= { cfprApVnicConnDefEntry 1 }

cfprApVnicConnDefDn OBJECT-TYPE
    SYNTAX       CfprApManagedObjectDn
    MAX-ACCESS   read-only
    STATUS       current
    DESCRIPTION
        "Cisco Firepower vnic:ConnDef:dn managed object property"
    ::= { cfprApVnicConnDefEntry 2 }

cfprApVnicConnDefRn OBJECT-TYPE
    SYNTAX       SnmpAdminString
    MAX-ACCESS   read-only
    STATUS       current
    DESCRIPTION
        "Cisco Firepower vnic:ConnDef:rn managed object property"
    ::= { cfprApVnicConnDefEntry 3 }

cfprApVnicConnDefFltAggr OBJECT-TYPE
    SYNTAX       Unsigned64
    MAX-ACCESS   read-only
    STATUS       current
    DESCRIPTION
        "Cisco Firepower vnic:ConnDef:fltAggr managed object property"
    ::= { cfprApVnicConnDefEntry 4 }

cfprApVnicConnDefLanConnPolicyName OBJECT-TYPE
    SYNTAX       SnmpAdminString
    MAX-ACCESS   read-only
    STATUS       current
    DESCRIPTION
        "Cisco Firepower vnic:ConnDef:lanConnPolicyName
        managed object property"
    ::= { cfprApVnicConnDefEntry 5 }

cfprApVnicConnDefOperLanConnPolicyName OBJECT-TYPE
    SYNTAX       SnmpAdminString
    MAX-ACCESS   read-only
    STATUS       current
    DESCRIPTION
        "Cisco Firepower vnic:ConnDef:operLanConnPolicyName
        managed object property"
    ::= { cfprApVnicConnDefEntry 6 }

cfprApVnicDefBehTable OBJECT-TYPE
    SYNTAX           SEQUENCE OF CfprApVnicDefBehEntry
    MAX-ACCESS       not-accessible
    STATUS           current
    DESCRIPTION
        "Cisco Firepower vnic:DefBeh managed object table"
    ::= { cfprApVnicObjects 4 }

cfprApVnicDefBehEntry OBJECT-TYPE
    SYNTAX           CfprApVnicDefBehEntry
    MAX-ACCESS       not-accessible
    STATUS           current
    DESCRIPTION
        "Entry for the cfprApVnicDefBehTable table."
    INDEX { cfprApVnicDefBehInstanceId }
    ::= { cfprApVnicDefBehTable 1 }

CfprApVnicDefBehEntry ::= SEQUENCE {
    cfprApVnicDefBehInstanceId                                       CfprApManagedObjectId,
    cfprApVnicDefBehDn                                               CfprApManagedObjectDn,
    cfprApVnicDefBehRn                                               SnmpAdminString,
    cfprApVnicDefBehAction                                           CfprApVnicDefaultAction,
    cfprApVnicDefBehDescr                                            SnmpAdminString,
    cfprApVnicDefBehIntId                                            SnmpAdminString,
    cfprApVnicDefBehName                                             SnmpAdminString,
    cfprApVnicDefBehNwTemplName                                      SnmpAdminString,
    cfprApVnicDefBehPolicyLevel                                      Gauge32,
    cfprApVnicDefBehPolicyOwner                                      CfprApPolicyPolicyOwner,
    cfprApVnicDefBehType                                             CfprApVnicDefBehType
}

cfprApVnicDefBehInstanceId OBJECT-TYPE
    SYNTAX       CfprApManagedObjectId
    MAX-ACCESS   not-accessible
    STATUS       current
    DESCRIPTION
        "Instance identifier of the managed object."
    ::= { cfprApVnicDefBehEntry 1 }

cfprApVnicDefBehDn OBJECT-TYPE
    SYNTAX       CfprApManagedObjectDn
    MAX-ACCESS   read-only
    STATUS       current
    DESCRIPTION
        "Cisco Firepower vnic:DefBeh:dn managed object property"
    ::= { cfprApVnicDefBehEntry 2 }

cfprApVnicDefBehRn OBJECT-TYPE
    SYNTAX       SnmpAdminString
    MAX-ACCESS   read-only
    STATUS       current
    DESCRIPTION
        "Cisco Firepower vnic:DefBeh:rn managed object property"
    ::= { cfprApVnicDefBehEntry 3 }

cfprApVnicDefBehAction OBJECT-TYPE
    SYNTAX       CfprApVnicDefaultAction
    MAX-ACCESS   read-only
    STATUS       current
    DESCRIPTION
        "Cisco Firepower vnic:DefBeh:action managed object property"
    ::= { cfprApVnicDefBehEntry 4 }

cfprApVnicDefBehDescr OBJECT-TYPE
    SYNTAX       SnmpAdminString
    MAX-ACCESS   read-only
    STATUS       current
    DESCRIPTION
        "Cisco Firepower vnic:DefBeh:descr managed object property"
    ::= { cfprApVnicDefBehEntry 5 }

cfprApVnicDefBehIntId OBJECT-TYPE
    SYNTAX       SnmpAdminString
    MAX-ACCESS   read-only
    STATUS       current
    DESCRIPTION
        "Cisco Firepower vnic:DefBeh:intId managed object property"
    ::= { cfprApVnicDefBehEntry 6 }

cfprApVnicDefBehName OBJECT-TYPE
    SYNTAX       SnmpAdminString
    MAX-ACCESS   read-only
    STATUS       current
    DESCRIPTION
        "Cisco Firepower vnic:DefBeh:name managed object property"
    ::= { cfprApVnicDefBehEntry 7 }

cfprApVnicDefBehNwTemplName OBJECT-TYPE
    SYNTAX       SnmpAdminString
    MAX-ACCESS   read-only
    STATUS       current
    DESCRIPTION
        "Cisco Firepower vnic:DefBeh:nwTemplName managed object property"
    ::= { cfprApVnicDefBehEntry 8 }

cfprApVnicDefBehPolicyLevel OBJECT-TYPE
    SYNTAX       Gauge32
    MAX-ACCESS   read-only
    STATUS       current
    DESCRIPTION
        "Cisco Firepower vnic:DefBeh:policyLevel managed object property"
    ::= { cfprApVnicDefBehEntry 9 }

cfprApVnicDefBehPolicyOwner OBJECT-TYPE
    SYNTAX       CfprApPolicyPolicyOwner
    MAX-ACCESS   read-only
    STATUS       current
    DESCRIPTION
        "Cisco Firepower vnic:DefBeh:policyOwner managed object property"
    ::= { cfprApVnicDefBehEntry 10 }

cfprApVnicDefBehType OBJECT-TYPE
    SYNTAX       CfprApVnicDefBehType
    MAX-ACCESS   read-only
    STATUS       current
    DESCRIPTION
        "Cisco Firepower vnic:DefBeh:type managed object property"
    ::= { cfprApVnicDefBehEntry 11 }

cfprApVnicDynamicConTable OBJECT-TYPE
    SYNTAX           SEQUENCE OF CfprApVnicDynamicConEntry
    MAX-ACCESS       not-accessible
    STATUS           current
    DESCRIPTION
        "Cisco Firepower vnic:DynamicCon managed object table"
    ::= { cfprApVnicObjects 5 }

cfprApVnicDynamicConEntry OBJECT-TYPE
    SYNTAX           CfprApVnicDynamicConEntry
    MAX-ACCESS       not-accessible
    STATUS           current
    DESCRIPTION
        "Entry for the cfprApVnicDynamicConTable table."
    INDEX { cfprApVnicDynamicConInstanceId }
    ::= { cfprApVnicDynamicConTable 1 }

CfprApVnicDynamicConEntry ::= SEQUENCE {
    cfprApVnicDynamicConInstanceId                                   CfprApManagedObjectId,
    cfprApVnicDynamicConDn                                           CfprApManagedObjectDn,
    cfprApVnicDynamicConRn                                           SnmpAdminString,
    cfprApVnicDynamicConAdaptorProfileName                           SnmpAdminString,
    cfprApVnicDynamicConDescr                                        SnmpAdminString,
    cfprApVnicDynamicConDynamicEth                                   Gauge32,
    cfprApVnicDynamicConIntId                                        SnmpAdminString,
    cfprApVnicDynamicConMtu                                          Gauge32,
    cfprApVnicDynamicConName                                         SnmpAdminString,
    cfprApVnicDynamicConNamingPrefix                                 SnmpAdminString,
    cfprApVnicDynamicConPolicyLevel                                  Gauge32,
    cfprApVnicDynamicConPolicyOwner                                  CfprApPolicyPolicyOwner,
    cfprApVnicDynamicConProtection                                   CfprApVnicDynamicConReqProtection
}

cfprApVnicDynamicConInstanceId OBJECT-TYPE
    SYNTAX       CfprApManagedObjectId
    MAX-ACCESS   not-accessible
    STATUS       current
    DESCRIPTION
        "Instance identifier of the managed object."
    ::= { cfprApVnicDynamicConEntry 1 }

cfprApVnicDynamicConDn OBJECT-TYPE
    SYNTAX       CfprApManagedObjectDn
    MAX-ACCESS   read-only
    STATUS       current
    DESCRIPTION
        "Cisco Firepower vnic:DynamicCon:dn managed object property"
    ::= { cfprApVnicDynamicConEntry 2 }

cfprApVnicDynamicConRn OBJECT-TYPE
    SYNTAX       SnmpAdminString
    MAX-ACCESS   read-only
    STATUS       current
    DESCRIPTION
        "Cisco Firepower vnic:DynamicCon:rn managed object property"
    ::= { cfprApVnicDynamicConEntry 3 }

cfprApVnicDynamicConAdaptorProfileName OBJECT-TYPE
    SYNTAX       SnmpAdminString
    MAX-ACCESS   read-only
    STATUS       current
    DESCRIPTION
        "Cisco Firepower vnic:DynamicCon:adaptorProfileName
        managed object property"
    ::= { cfprApVnicDynamicConEntry 4 }

cfprApVnicDynamicConDescr OBJECT-TYPE
    SYNTAX       SnmpAdminString
    MAX-ACCESS   read-only
    STATUS       current
    DESCRIPTION
        "Cisco Firepower vnic:DynamicCon:descr managed object property"
    ::= { cfprApVnicDynamicConEntry 5 }

cfprApVnicDynamicConDynamicEth OBJECT-TYPE
    SYNTAX       Gauge32
    MAX-ACCESS   read-only
    STATUS       current
    DESCRIPTION
        "Cisco Firepower vnic:DynamicCon:dynamicEth managed
        object property"
    ::= { cfprApVnicDynamicConEntry 6 }

cfprApVnicDynamicConIntId OBJECT-TYPE
    SYNTAX       SnmpAdminString
    MAX-ACCESS   read-only
    STATUS       current
    DESCRIPTION
        "Cisco Firepower vnic:DynamicCon:intId managed object property"
    ::= { cfprApVnicDynamicConEntry 7 }

cfprApVnicDynamicConMtu OBJECT-TYPE
    SYNTAX       Gauge32
    MAX-ACCESS   read-only
    STATUS       current
    DESCRIPTION
        "Cisco Firepower vnic:DynamicCon:mtu managed object property"
    ::= { cfprApVnicDynamicConEntry 8 }

cfprApVnicDynamicConName OBJECT-TYPE
    SYNTAX       SnmpAdminString
    MAX-ACCESS   read-only
    STATUS       current
    DESCRIPTION
        "Cisco Firepower vnic:DynamicCon:name managed object property"
    ::= { cfprApVnicDynamicConEntry 9 }

cfprApVnicDynamicConNamingPrefix OBJECT-TYPE
    SYNTAX       SnmpAdminString
    MAX-ACCESS   read-only
    STATUS       current
    DESCRIPTION
        "Cisco Firepower vnic:DynamicCon:namingPrefix managed
        object property"
    ::= { cfprApVnicDynamicConEntry 10 }

cfprApVnicDynamicConPolicyLevel OBJECT-TYPE
    SYNTAX       Gauge32
    MAX-ACCESS   read-only
    STATUS       current
    DESCRIPTION
        "Cisco Firepower vnic:DynamicCon:policyLevel managed
        object property"
    ::= { cfprApVnicDynamicConEntry 11 }

cfprApVnicDynamicConPolicyOwner OBJECT-TYPE
    SYNTAX       CfprApPolicyPolicyOwner
    MAX-ACCESS   read-only
    STATUS       current
    DESCRIPTION
        "Cisco Firepower vnic:DynamicCon:policyOwner managed
        object property"
    ::= { cfprApVnicDynamicConEntry 12 }

cfprApVnicDynamicConProtection OBJECT-TYPE
    SYNTAX       CfprApVnicDynamicConReqProtection
    MAX-ACCESS   read-only
    STATUS       current
    DESCRIPTION
        "Cisco Firepower vnic:DynamicCon:protection managed
        object property"
    ::= { cfprApVnicDynamicConEntry 13 }

cfprApVnicDynamicConPolicyTable OBJECT-TYPE
    SYNTAX           SEQUENCE OF CfprApVnicDynamicConPolicyEntry
    MAX-ACCESS       not-accessible
    STATUS           current
    DESCRIPTION
        "Cisco Firepower vnic:DynamicConPolicy managed object table"
    ::= { cfprApVnicObjects 6 }

cfprApVnicDynamicConPolicyEntry OBJECT-TYPE
    SYNTAX           CfprApVnicDynamicConPolicyEntry
    MAX-ACCESS       not-accessible
    STATUS           current
    DESCRIPTION
        "Entry for the cfprApVnicDynamicConPolicyTable table."
    INDEX { cfprApVnicDynamicConPolicyInstanceId }
    ::= { cfprApVnicDynamicConPolicyTable 1 }

CfprApVnicDynamicConPolicyEntry ::= SEQUENCE {
    cfprApVnicDynamicConPolicyInstanceId                             CfprApManagedObjectId,
    cfprApVnicDynamicConPolicyDn                                     CfprApManagedObjectDn,
    cfprApVnicDynamicConPolicyRn                                     SnmpAdminString,
    cfprApVnicDynamicConPolicyAdaptorProfileName                     SnmpAdminString,
    cfprApVnicDynamicConPolicyDescr                                  SnmpAdminString,
    cfprApVnicDynamicConPolicyDynamicEth                             Gauge32,
    cfprApVnicDynamicConPolicyIntId                                  SnmpAdminString,
    cfprApVnicDynamicConPolicyMtu                                    Gauge32,
    cfprApVnicDynamicConPolicyName                                   SnmpAdminString,
    cfprApVnicDynamicConPolicyNamingPrefix                           SnmpAdminString,
    cfprApVnicDynamicConPolicyPolicyLevel                            Gauge32,
    cfprApVnicDynamicConPolicyPolicyOwner                            CfprApPolicyPolicyOwner,
    cfprApVnicDynamicConPolicyProtection                             CfprApVnicDynamicConReqProtection
}

cfprApVnicDynamicConPolicyInstanceId OBJECT-TYPE
    SYNTAX       CfprApManagedObjectId
    MAX-ACCESS   not-accessible
    STATUS       current
    DESCRIPTION
        "Instance identifier of the managed object."
    ::= { cfprApVnicDynamicConPolicyEntry 1 }

cfprApVnicDynamicConPolicyDn OBJECT-TYPE
    SYNTAX       CfprApManagedObjectDn
    MAX-ACCESS   read-only
    STATUS       current
    DESCRIPTION
        "Cisco Firepower vnic:DynamicConPolicy:dn managed object property"
    ::= { cfprApVnicDynamicConPolicyEntry 2 }

cfprApVnicDynamicConPolicyRn OBJECT-TYPE
    SYNTAX       SnmpAdminString
    MAX-ACCESS   read-only
    STATUS       current
    DESCRIPTION
        "Cisco Firepower vnic:DynamicConPolicy:rn managed object property"
    ::= { cfprApVnicDynamicConPolicyEntry 3 }

cfprApVnicDynamicConPolicyAdaptorProfileName OBJECT-TYPE
    SYNTAX       SnmpAdminString
    MAX-ACCESS   read-only
    STATUS       current
    DESCRIPTION
        "Cisco Firepower vnic:DynamicConPolicy:adaptorProfileName
        managed object property"
    ::= { cfprApVnicDynamicConPolicyEntry 4 }

cfprApVnicDynamicConPolicyDescr OBJECT-TYPE
    SYNTAX       SnmpAdminString
    MAX-ACCESS   read-only
    STATUS       current
    DESCRIPTION
        "Cisco Firepower vnic:DynamicConPolicy:descr managed
        object property"
    ::= { cfprApVnicDynamicConPolicyEntry 5 }

cfprApVnicDynamicConPolicyDynamicEth OBJECT-TYPE
    SYNTAX       Gauge32
    MAX-ACCESS   read-only
    STATUS       current
    DESCRIPTION
        "Cisco Firepower vnic:DynamicConPolicy:dynamicEth
        managed object property"
    ::= { cfprApVnicDynamicConPolicyEntry 6 }

cfprApVnicDynamicConPolicyIntId OBJECT-TYPE
    SYNTAX       SnmpAdminString
    MAX-ACCESS   read-only
    STATUS       current
    DESCRIPTION
        "Cisco Firepower vnic:DynamicConPolicy:intId managed
        object property"
    ::= { cfprApVnicDynamicConPolicyEntry 7 }

cfprApVnicDynamicConPolicyMtu OBJECT-TYPE
    SYNTAX       Gauge32
    MAX-ACCESS   read-only
    STATUS       current
    DESCRIPTION
        "Cisco Firepower vnic:DynamicConPolicy:mtu managed
        object property"
    ::= { cfprApVnicDynamicConPolicyEntry 8 }

cfprApVnicDynamicConPolicyName OBJECT-TYPE
    SYNTAX       SnmpAdminString
    MAX-ACCESS   read-only
    STATUS       current
    DESCRIPTION
        "Cisco Firepower vnic:DynamicConPolicy:name managed
        object property"
    ::= { cfprApVnicDynamicConPolicyEntry 9 }

cfprApVnicDynamicConPolicyNamingPrefix OBJECT-TYPE
    SYNTAX       SnmpAdminString
    MAX-ACCESS   read-only
    STATUS       current
    DESCRIPTION
        "Cisco Firepower vnic:DynamicConPolicy:namingPrefix
        managed object property"
    ::= { cfprApVnicDynamicConPolicyEntry 10 }

cfprApVnicDynamicConPolicyPolicyLevel OBJECT-TYPE
    SYNTAX       Gauge32
    MAX-ACCESS   read-only
    STATUS       current
    DESCRIPTION
        "Cisco Firepower vnic:DynamicConPolicy:policyLevel
        managed object property"
    ::= { cfprApVnicDynamicConPolicyEntry 11 }

cfprApVnicDynamicConPolicyPolicyOwner OBJECT-TYPE
    SYNTAX       CfprApPolicyPolicyOwner
    MAX-ACCESS   read-only
    STATUS       current
    DESCRIPTION
        "Cisco Firepower vnic:DynamicConPolicy:policyOwner
        managed object property"
    ::= { cfprApVnicDynamicConPolicyEntry 12 }

cfprApVnicDynamicConPolicyProtection OBJECT-TYPE
    SYNTAX       CfprApVnicDynamicConReqProtection
    MAX-ACCESS   read-only
    STATUS       current
    DESCRIPTION
        "Cisco Firepower vnic:DynamicConPolicy:protection
        managed object property"
    ::= { cfprApVnicDynamicConPolicyEntry 13 }

cfprApVnicDynamicConPolicyRefTable OBJECT-TYPE
    SYNTAX           SEQUENCE OF CfprApVnicDynamicConPolicyRefEntry
    MAX-ACCESS       not-accessible
    STATUS           current
    DESCRIPTION
        "Cisco Firepower vnic:DynamicConPolicyRef managed object table"
    ::= { cfprApVnicObjects 7 }

cfprApVnicDynamicConPolicyRefEntry OBJECT-TYPE
    SYNTAX           CfprApVnicDynamicConPolicyRefEntry
    MAX-ACCESS       not-accessible
    STATUS           current
    DESCRIPTION
        "Entry for the cfprApVnicDynamicConPolicyRefTable table."
    INDEX { cfprApVnicDynamicConPolicyRefInstanceId }
    ::= { cfprApVnicDynamicConPolicyRefTable 1 }

CfprApVnicDynamicConPolicyRefEntry ::= SEQUENCE {
    cfprApVnicDynamicConPolicyRefInstanceId                          CfprApManagedObjectId,
    cfprApVnicDynamicConPolicyRefDn                                  CfprApManagedObjectDn,
    cfprApVnicDynamicConPolicyRefRn                                  SnmpAdminString,
    cfprApVnicDynamicConPolicyRefConPolicyName                       SnmpAdminString,
    cfprApVnicDynamicConPolicyRefOperConPolicyName                   SnmpAdminString
}

cfprApVnicDynamicConPolicyRefInstanceId OBJECT-TYPE
    SYNTAX       CfprApManagedObjectId
    MAX-ACCESS   not-accessible
    STATUS       current
    DESCRIPTION
        "Instance identifier of the managed object."
    ::= { cfprApVnicDynamicConPolicyRefEntry 1 }

cfprApVnicDynamicConPolicyRefDn OBJECT-TYPE
    SYNTAX       CfprApManagedObjectDn
    MAX-ACCESS   read-only
    STATUS       current
    DESCRIPTION
        "Cisco Firepower vnic:DynamicConPolicyRef:dn managed
        object property"
    ::= { cfprApVnicDynamicConPolicyRefEntry 2 }

cfprApVnicDynamicConPolicyRefRn OBJECT-TYPE
    SYNTAX       SnmpAdminString
    MAX-ACCESS   read-only
    STATUS       current
    DESCRIPTION
        "Cisco Firepower vnic:DynamicConPolicyRef:rn managed
        object property"
    ::= { cfprApVnicDynamicConPolicyRefEntry 3 }

cfprApVnicDynamicConPolicyRefConPolicyName OBJECT-TYPE
    SYNTAX       SnmpAdminString
    MAX-ACCESS   read-only
    STATUS       current
    DESCRIPTION
        "Cisco Firepower vnic:DynamicConPolicyRef:conPolicyName
        managed object property"
    ::= { cfprApVnicDynamicConPolicyRefEntry 4 }

cfprApVnicDynamicConPolicyRefOperConPolicyName OBJECT-TYPE
    SYNTAX       SnmpAdminString
    MAX-ACCESS   read-only
    STATUS       current
    DESCRIPTION
        "Cisco Firepower vnic:DynamicConPolicyRef:operConPolicyName
        managed object property"
    ::= { cfprApVnicDynamicConPolicyRefEntry 5 }

cfprApVnicDynamicIdUniverseTable OBJECT-TYPE
    SYNTAX           SEQUENCE OF CfprApVnicDynamicIdUniverseEntry
    MAX-ACCESS       not-accessible
    STATUS           current
    DESCRIPTION
        "Cisco Firepower vnic:DynamicIdUniverse managed object table"
    ::= { cfprApVnicObjects 8 }

cfprApVnicDynamicIdUniverseEntry OBJECT-TYPE
    SYNTAX           CfprApVnicDynamicIdUniverseEntry
    MAX-ACCESS       not-accessible
    STATUS           current
    DESCRIPTION
        "Entry for the cfprApVnicDynamicIdUniverseTable table."
    INDEX { cfprApVnicDynamicIdUniverseInstanceId }
    ::= { cfprApVnicDynamicIdUniverseTable 1 }

CfprApVnicDynamicIdUniverseEntry ::= SEQUENCE {
    cfprApVnicDynamicIdUniverseInstanceId                            CfprApManagedObjectId,
    cfprApVnicDynamicIdUniverseDn                                    CfprApManagedObjectDn,
    cfprApVnicDynamicIdUniverseRn                                    SnmpAdminString,
    cfprApVnicDynamicIdUniverseDescr                                 SnmpAdminString,
    cfprApVnicDynamicIdUniverseIntId                                 SnmpAdminString,
    cfprApVnicDynamicIdUniverseName                                  SnmpAdminString,
    cfprApVnicDynamicIdUniversePolicyLevel                           Gauge32,
    cfprApVnicDynamicIdUniversePolicyOwner                           CfprApPolicyPolicyOwner
}

cfprApVnicDynamicIdUniverseInstanceId OBJECT-TYPE
    SYNTAX       CfprApManagedObjectId
    MAX-ACCESS   not-accessible
    STATUS       current
    DESCRIPTION
        "Instance identifier of the managed object."
    ::= { cfprApVnicDynamicIdUniverseEntry 1 }

cfprApVnicDynamicIdUniverseDn OBJECT-TYPE
    SYNTAX       CfprApManagedObjectDn
    MAX-ACCESS   read-only
    STATUS       current
    DESCRIPTION
        "Cisco Firepower vnic:DynamicIdUniverse:dn managed
        object property"
    ::= { cfprApVnicDynamicIdUniverseEntry 2 }

cfprApVnicDynamicIdUniverseRn OBJECT-TYPE
    SYNTAX       SnmpAdminString
    MAX-ACCESS   read-only
    STATUS       current
    DESCRIPTION
        "Cisco Firepower vnic:DynamicIdUniverse:rn managed
        object property"
    ::= { cfprApVnicDynamicIdUniverseEntry 3 }

cfprApVnicDynamicIdUniverseDescr OBJECT-TYPE
    SYNTAX       SnmpAdminString
    MAX-ACCESS   read-only
    STATUS       current
    DESCRIPTION
        "Cisco Firepower vnic:DynamicIdUniverse:descr managed
        object property"
    ::= { cfprApVnicDynamicIdUniverseEntry 4 }

cfprApVnicDynamicIdUniverseIntId OBJECT-TYPE
    SYNTAX       SnmpAdminString
    MAX-ACCESS   read-only
    STATUS       current
    DESCRIPTION
        "Cisco Firepower vnic:DynamicIdUniverse:intId managed
        object property"
    ::= { cfprApVnicDynamicIdUniverseEntry 5 }

cfprApVnicDynamicIdUniverseName OBJECT-TYPE
    SYNTAX       SnmpAdminString
    MAX-ACCESS   read-only
    STATUS       current
    DESCRIPTION
        "Cisco Firepower vnic:DynamicIdUniverse:name managed
        object property"
    ::= { cfprApVnicDynamicIdUniverseEntry 6 }

cfprApVnicDynamicIdUniversePolicyLevel OBJECT-TYPE
    SYNTAX       Gauge32
    MAX-ACCESS   read-only
    STATUS       current
    DESCRIPTION
        "Cisco Firepower vnic:DynamicIdUniverse:policyLevel
        managed object property"
    ::= { cfprApVnicDynamicIdUniverseEntry 7 }

cfprApVnicDynamicIdUniversePolicyOwner OBJECT-TYPE
    SYNTAX       CfprApPolicyPolicyOwner
    MAX-ACCESS   read-only
    STATUS       current
    DESCRIPTION
        "Cisco Firepower vnic:DynamicIdUniverse:policyOwner
        managed object property"
    ::= { cfprApVnicDynamicIdUniverseEntry 8 }

cfprApVnicDynamicProviderTable OBJECT-TYPE
    SYNTAX           SEQUENCE OF CfprApVnicDynamicProviderEntry
    MAX-ACCESS       not-accessible
    STATUS           current
    DESCRIPTION
        "Cisco Firepower vnic:DynamicProvider managed object table"
    ::= { cfprApVnicObjects 9 }

cfprApVnicDynamicProviderEntry OBJECT-TYPE
    SYNTAX           CfprApVnicDynamicProviderEntry
    MAX-ACCESS       not-accessible
    STATUS           current
    DESCRIPTION
        "Entry for the cfprApVnicDynamicProviderTable table."
    INDEX { cfprApVnicDynamicProviderInstanceId }
    ::= { cfprApVnicDynamicProviderTable 1 }

CfprApVnicDynamicProviderEntry ::= SEQUENCE {
    cfprApVnicDynamicProviderInstanceId                              CfprApManagedObjectId,
    cfprApVnicDynamicProviderDn                                      CfprApManagedObjectDn,
    cfprApVnicDynamicProviderRn                                      SnmpAdminString,
    cfprApVnicDynamicProviderName                                    SnmpAdminString
}

cfprApVnicDynamicProviderInstanceId OBJECT-TYPE
    SYNTAX       CfprApManagedObjectId
    MAX-ACCESS   not-accessible
    STATUS       current
    DESCRIPTION
        "Instance identifier of the managed object."
    ::= { cfprApVnicDynamicProviderEntry 1 }

cfprApVnicDynamicProviderDn OBJECT-TYPE
    SYNTAX       CfprApManagedObjectDn
    MAX-ACCESS   read-only
    STATUS       current
    DESCRIPTION
        "Cisco Firepower vnic:DynamicProvider:dn managed object property"
    ::= { cfprApVnicDynamicProviderEntry 2 }

cfprApVnicDynamicProviderRn OBJECT-TYPE
    SYNTAX       SnmpAdminString
    MAX-ACCESS   read-only
    STATUS       current
    DESCRIPTION
        "Cisco Firepower vnic:DynamicProvider:rn managed object property"
    ::= { cfprApVnicDynamicProviderEntry 3 }

cfprApVnicDynamicProviderName OBJECT-TYPE
    SYNTAX       SnmpAdminString
    MAX-ACCESS   read-only
    STATUS       current
    DESCRIPTION
        "Cisco Firepower vnic:DynamicProvider:name managed
        object property"
    ::= { cfprApVnicDynamicProviderEntry 4 }

cfprApVnicDynamicProviderEpTable OBJECT-TYPE
    SYNTAX           SEQUENCE OF CfprApVnicDynamicProviderEpEntry
    MAX-ACCESS       not-accessible
    STATUS           current
    DESCRIPTION
        "Cisco Firepower vnic:DynamicProviderEp managed object table"
    ::= { cfprApVnicObjects 10 }

cfprApVnicDynamicProviderEpEntry OBJECT-TYPE
    SYNTAX           CfprApVnicDynamicProviderEpEntry
    MAX-ACCESS       not-accessible
    STATUS           current
    DESCRIPTION
        "Entry for the cfprApVnicDynamicProviderEpTable table."
    INDEX { cfprApVnicDynamicProviderEpInstanceId }
    ::= { cfprApVnicDynamicProviderEpTable 1 }

CfprApVnicDynamicProviderEpEntry ::= SEQUENCE {
    cfprApVnicDynamicProviderEpInstanceId                            CfprApManagedObjectId,
    cfprApVnicDynamicProviderEpDn                                    CfprApManagedObjectDn,
    cfprApVnicDynamicProviderEpRn                                    SnmpAdminString,
    cfprApVnicDynamicProviderEpChassisId                             Gauge32,
    cfprApVnicDynamicProviderEpPortId                                Gauge32,
    cfprApVnicDynamicProviderEpSlotId                                Gauge32,
    cfprApVnicDynamicProviderEpSwitchId                              CfprApNetworkSwitchId
}

cfprApVnicDynamicProviderEpInstanceId OBJECT-TYPE
    SYNTAX       CfprApManagedObjectId
    MAX-ACCESS   not-accessible
    STATUS       current
    DESCRIPTION
        "Instance identifier of the managed object."
    ::= { cfprApVnicDynamicProviderEpEntry 1 }

cfprApVnicDynamicProviderEpDn OBJECT-TYPE
    SYNTAX       CfprApManagedObjectDn
    MAX-ACCESS   read-only
    STATUS       current
    DESCRIPTION
        "Cisco Firepower vnic:DynamicProviderEp:dn managed
        object property"
    ::= { cfprApVnicDynamicProviderEpEntry 2 }

cfprApVnicDynamicProviderEpRn OBJECT-TYPE
    SYNTAX       SnmpAdminString
    MAX-ACCESS   read-only
    STATUS       current
    DESCRIPTION
        "Cisco Firepower vnic:DynamicProviderEp:rn managed
        object property"
    ::= { cfprApVnicDynamicProviderEpEntry 3 }

cfprApVnicDynamicProviderEpChassisId OBJECT-TYPE
    SYNTAX       Gauge32
    MAX-ACCESS   read-only
    STATUS       current
    DESCRIPTION
        "Cisco Firepower vnic:DynamicProviderEp:chassisId
        managed object property"
    ::= { cfprApVnicDynamicProviderEpEntry 4 }

cfprApVnicDynamicProviderEpPortId OBJECT-TYPE
    SYNTAX       Gauge32
    MAX-ACCESS   read-only
    STATUS       current
    DESCRIPTION
        "Cisco Firepower vnic:DynamicProviderEp:portId
        managed object property"
    ::= { cfprApVnicDynamicProviderEpEntry 5 }

cfprApVnicDynamicProviderEpSlotId OBJECT-TYPE
    SYNTAX       Gauge32
    MAX-ACCESS   read-only
    STATUS       current
    DESCRIPTION
        "Cisco Firepower vnic:DynamicProviderEp:slotId
        managed object property"
    ::= { cfprApVnicDynamicProviderEpEntry 6 }

cfprApVnicDynamicProviderEpSwitchId OBJECT-TYPE
    SYNTAX       CfprApNetworkSwitchId
    MAX-ACCESS   read-only
    STATUS       current
    DESCRIPTION
        "Cisco Firepower vnic:DynamicProviderEp:switchId
        managed object property"
    ::= { cfprApVnicDynamicProviderEpEntry 7 }

cfprApVnicEthLifTable OBJECT-TYPE
    SYNTAX           SEQUENCE OF CfprApVnicEthLifEntry
    MAX-ACCESS       not-accessible
    STATUS           current
    DESCRIPTION
        "Cisco Firepower vnic:EthLif managed object table"
    ::= { cfprApVnicObjects 11 }

cfprApVnicEthLifEntry OBJECT-TYPE
    SYNTAX           CfprApVnicEthLifEntry
    MAX-ACCESS       not-accessible
    STATUS           current
    DESCRIPTION
        "Entry for the cfprApVnicEthLifTable table."
    INDEX { cfprApVnicEthLifInstanceId }
    ::= { cfprApVnicEthLifTable 1 }

CfprApVnicEthLifEntry ::= SEQUENCE {
    cfprApVnicEthLifInstanceId                                       CfprApManagedObjectId,
    cfprApVnicEthLifDn                                               CfprApManagedObjectDn,
    cfprApVnicEthLifRn                                               SnmpAdminString,
    cfprApVnicEthLifAddr                                             MacAddress,
    cfprApVnicEthLifName                                             SnmpAdminString,
    cfprApVnicEthLifNicDn                                            SnmpAdminString,
    cfprApVnicEthLifOwner                                            CfprApVnicConnectionOwner,
    cfprApVnicEthLifSwitchId                                         CfprApNetworkSwitchId,
    cfprApVnicEthLifType                                             CfprApVnicConnectionType,
    cfprApVnicEthLifVnicDn                                           SnmpAdminString
}

cfprApVnicEthLifInstanceId OBJECT-TYPE
    SYNTAX       CfprApManagedObjectId
    MAX-ACCESS   not-accessible
    STATUS       current
    DESCRIPTION
        "Instance identifier of the managed object."
    ::= { cfprApVnicEthLifEntry 1 }

cfprApVnicEthLifDn OBJECT-TYPE
    SYNTAX       CfprApManagedObjectDn
    MAX-ACCESS   read-only
    STATUS       current
    DESCRIPTION
        "Cisco Firepower vnic:EthLif:dn managed object property"
    ::= { cfprApVnicEthLifEntry 2 }

cfprApVnicEthLifRn OBJECT-TYPE
    SYNTAX       SnmpAdminString
    MAX-ACCESS   read-only
    STATUS       current
    DESCRIPTION
        "Cisco Firepower vnic:EthLif:rn managed object property"
    ::= { cfprApVnicEthLifEntry 3 }

cfprApVnicEthLifAddr OBJECT-TYPE
    SYNTAX       MacAddress
    MAX-ACCESS   read-only
    STATUS       current
    DESCRIPTION
        "Cisco Firepower vnic:EthLif:addr managed object property"
    ::= { cfprApVnicEthLifEntry 4 }

cfprApVnicEthLifName OBJECT-TYPE
    SYNTAX       SnmpAdminString
    MAX-ACCESS   read-only
    STATUS       current
    DESCRIPTION
        "Cisco Firepower vnic:EthLif:name managed object property"
    ::= { cfprApVnicEthLifEntry 5 }

cfprApVnicEthLifNicDn OBJECT-TYPE
    SYNTAX       SnmpAdminString
    MAX-ACCESS   read-only
    STATUS       current
    DESCRIPTION
        "Cisco Firepower vnic:EthLif:nicDn managed object property"
    ::= { cfprApVnicEthLifEntry 6 }

cfprApVnicEthLifOwner OBJECT-TYPE
    SYNTAX       CfprApVnicConnectionOwner
    MAX-ACCESS   read-only
    STATUS       current
    DESCRIPTION
        "Cisco Firepower vnic:EthLif:owner managed object property"
    ::= { cfprApVnicEthLifEntry 7 }

cfprApVnicEthLifSwitchId OBJECT-TYPE
    SYNTAX       CfprApNetworkSwitchId
    MAX-ACCESS   read-only
    STATUS       current
    DESCRIPTION
        "Cisco Firepower vnic:EthLif:switchId managed object property"
    ::= { cfprApVnicEthLifEntry 8 }

cfprApVnicEthLifType OBJECT-TYPE
    SYNTAX       CfprApVnicConnectionType
    MAX-ACCESS   read-only
    STATUS       current
    DESCRIPTION
        "Cisco Firepower vnic:EthLif:type managed object property"
    ::= { cfprApVnicEthLifEntry 9 }

cfprApVnicEthLifVnicDn OBJECT-TYPE
    SYNTAX       SnmpAdminString
    MAX-ACCESS   read-only
    STATUS       current
    DESCRIPTION
        "Cisco Firepower vnic:EthLif:vnicDn managed object property"
    ::= { cfprApVnicEthLifEntry 10 }

cfprApVnicEtherTable OBJECT-TYPE
    SYNTAX           SEQUENCE OF CfprApVnicEtherEntry
    MAX-ACCESS       not-accessible
    STATUS           current
    DESCRIPTION
        "Cisco Firepower vnic:Ether managed object table"
    ::= { cfprApVnicObjects 12 }

cfprApVnicEtherEntry OBJECT-TYPE
    SYNTAX           CfprApVnicEtherEntry
    MAX-ACCESS       not-accessible
    STATUS           current
    DESCRIPTION
        "Entry for the cfprApVnicEtherTable table."
    INDEX { cfprApVnicEtherInstanceId }
    ::= { cfprApVnicEtherTable 1 }

CfprApVnicEtherEntry ::= SEQUENCE {
    cfprApVnicEtherInstanceId                                        CfprApManagedObjectId,
    cfprApVnicEtherDn                                                CfprApManagedObjectDn,
    cfprApVnicEtherRn                                                SnmpAdminString,
    cfprApVnicEtherAdaptorProfileName                                SnmpAdminString,
    cfprApVnicEtherAddr                                              MacAddress,
    cfprApVnicEtherAdminHostPort                                     CfprApFabricHostPortId,
    cfprApVnicEtherAdminVcon                                         SnmpAdminString,
    cfprApVnicEtherAppInstId                                         SnmpAdminString,
    cfprApVnicEtherAppRole                                           CfprApVnicAppRole,
    cfprApVnicEtherBootDev                                           CfprApVnicVnicBootDev,
    cfprApVnicEtherConfigQualifier                                   CfprApVnicConfigIssues,
    cfprApVnicEtherConfigState                                       CfprApLsConfigState,
    cfprApVnicEtherDynamicId                                         Gauge32,
    cfprApVnicEtherEquipmentDn                                       SnmpAdminString,
    cfprApVnicEtherFltAggr                                           Unsigned64,
    cfprApVnicEtherIdentPoolName                                     SnmpAdminString,
    cfprApVnicEtherInstType                                          CfprApVnicInstantiation,
    cfprApVnicEtherIsAllocated                                       TruthValue,
    cfprApVnicEtherMtu                                               Gauge32,
    cfprApVnicEtherName                                              SnmpAdminString,
    cfprApVnicEtherNwCtrlPolicyName                                  SnmpAdminString,
    cfprApVnicEtherNwTemplName                                       SnmpAdminString,
    cfprApVnicEtherOperAdaptorProfileName                            SnmpAdminString,
    cfprApVnicEtherOperHostPort                                      CfprApVnicVnicOperHostPort,
    cfprApVnicEtherOperIdentPoolName                                 SnmpAdminString,
    cfprApVnicEtherOperNwCtrlPolicyName                              SnmpAdminString,
    cfprApVnicEtherOperNwTemplName                                   SnmpAdminString,
    cfprApVnicEtherOperOrder                                         Gauge32,
    cfprApVnicEtherOperPinToGroupName                                SnmpAdminString,
    cfprApVnicEtherOperQosPolicyName                                 SnmpAdminString,
    cfprApVnicEtherOperSpeed                                         Gauge32,
    cfprApVnicEtherOperStatsPolicyName                               SnmpAdminString,
    cfprApVnicEtherOperVcon                                          SnmpAdminString,
    cfprApVnicEtherOrder                                             Gauge32,
    cfprApVnicEtherOwner                                             CfprApVnicConnectionOwner,
    cfprApVnicEtherPfDn                                              SnmpAdminString,
    cfprApVnicEtherPinToGroupName                                    SnmpAdminString,
    cfprApVnicEtherPortType                                          CfprApFabricSSAPortType,
    cfprApVnicEtherQosPolicyName                                     SnmpAdminString,
    cfprApVnicEtherStatsPolicyName                                   SnmpAdminString,
    cfprApVnicEtherSwitchId                                          CfprApVnicEtherBaseSwitchId,
    cfprApVnicEtherType                                              CfprApVnicEtherType,
    cfprApVnicEtherVirtualizationPreference                          CfprApVnicVirtualizationPreferenceType
}

cfprApVnicEtherInstanceId OBJECT-TYPE
    SYNTAX       CfprApManagedObjectId
    MAX-ACCESS   not-accessible
    STATUS       current
    DESCRIPTION
        "Instance identifier of the managed object."
    ::= { cfprApVnicEtherEntry 1 }

cfprApVnicEtherDn OBJECT-TYPE
    SYNTAX       CfprApManagedObjectDn
    MAX-ACCESS   read-only
    STATUS       current
    DESCRIPTION
        "Cisco Firepower vnic:Ether:dn managed object property"
    ::= { cfprApVnicEtherEntry 2 }

cfprApVnicEtherRn OBJECT-TYPE
    SYNTAX       SnmpAdminString
    MAX-ACCESS   read-only
    STATUS       current
    DESCRIPTION
        "Cisco Firepower vnic:Ether:rn managed object property"
    ::= { cfprApVnicEtherEntry 3 }

cfprApVnicEtherAdaptorProfileName OBJECT-TYPE
    SYNTAX       SnmpAdminString
    MAX-ACCESS   read-only
    STATUS       current
    DESCRIPTION
        "Cisco Firepower vnic:Ether:adaptorProfileName
        managed object property"
    ::= { cfprApVnicEtherEntry 4 }

cfprApVnicEtherAddr OBJECT-TYPE
    SYNTAX       MacAddress
    MAX-ACCESS   read-only
    STATUS       current
    DESCRIPTION
        "Cisco Firepower vnic:Ether:addr managed object property"
    ::= { cfprApVnicEtherEntry 5 }

cfprApVnicEtherAdminHostPort OBJECT-TYPE
    SYNTAX       CfprApFabricHostPortId
    MAX-ACCESS   read-only
    STATUS       current
    DESCRIPTION
        "Cisco Firepower vnic:Ether:adminHostPort managed object property"
    ::= { cfprApVnicEtherEntry 6 }

cfprApVnicEtherAdminVcon OBJECT-TYPE
    SYNTAX       SnmpAdminString
    MAX-ACCESS   read-only
    STATUS       current
    DESCRIPTION
        "Cisco Firepower vnic:Ether:adminVcon managed object property"
    ::= { cfprApVnicEtherEntry 7 }

cfprApVnicEtherAppInstId OBJECT-TYPE
    SYNTAX       SnmpAdminString
    MAX-ACCESS   read-only
    STATUS       current
    DESCRIPTION
        "Cisco Firepower vnic:Ether:appInstId managed object property"
    ::= { cfprApVnicEtherEntry 8 }

cfprApVnicEtherAppRole OBJECT-TYPE
    SYNTAX       CfprApVnicAppRole
    MAX-ACCESS   read-only
    STATUS       current
    DESCRIPTION
        "Cisco Firepower vnic:Ether:appRole managed object property"
    ::= { cfprApVnicEtherEntry 9 }

cfprApVnicEtherBootDev OBJECT-TYPE
    SYNTAX       CfprApVnicVnicBootDev
    MAX-ACCESS   read-only
    STATUS       current
    DESCRIPTION
        "Cisco Firepower vnic:Ether:bootDev managed object property"
    ::= { cfprApVnicEtherEntry 10 }

cfprApVnicEtherConfigQualifier OBJECT-TYPE
    SYNTAX       CfprApVnicConfigIssues
    MAX-ACCESS   read-only
    STATUS       current
    DESCRIPTION
        "Cisco Firepower vnic:Ether:configQualifier managed
        object property"
    ::= { cfprApVnicEtherEntry 11 }

cfprApVnicEtherConfigState OBJECT-TYPE
    SYNTAX       CfprApLsConfigState
    MAX-ACCESS   read-only
    STATUS       current
    DESCRIPTION
        "Cisco Firepower vnic:Ether:configState managed object property"
    ::= { cfprApVnicEtherEntry 12 }

cfprApVnicEtherDynamicId OBJECT-TYPE
    SYNTAX       Gauge32
    MAX-ACCESS   read-only
    STATUS       current
    DESCRIPTION
        "Cisco Firepower vnic:Ether:dynamicId managed object property"
    ::= { cfprApVnicEtherEntry 13 }

cfprApVnicEtherEquipmentDn OBJECT-TYPE
    SYNTAX       SnmpAdminString
    MAX-ACCESS   read-only
    STATUS       current
    DESCRIPTION
        "Cisco Firepower vnic:Ether:equipmentDn managed object property"
    ::= { cfprApVnicEtherEntry 14 }

cfprApVnicEtherFltAggr OBJECT-TYPE
    SYNTAX       Unsigned64
    MAX-ACCESS   read-only
    STATUS       current
    DESCRIPTION
        "Cisco Firepower vnic:Ether:fltAggr managed object property"
    ::= { cfprApVnicEtherEntry 15 }

cfprApVnicEtherIdentPoolName OBJECT-TYPE
    SYNTAX       SnmpAdminString
    MAX-ACCESS   read-only
    STATUS       current
    DESCRIPTION
        "Cisco Firepower vnic:Ether:identPoolName managed object property"
    ::= { cfprApVnicEtherEntry 16 }

cfprApVnicEtherInstType OBJECT-TYPE
    SYNTAX       CfprApVnicInstantiation
    MAX-ACCESS   read-only
    STATUS       current
    DESCRIPTION
        "Cisco Firepower vnic:Ether:instType managed object property"
    ::= { cfprApVnicEtherEntry 17 }

cfprApVnicEtherIsAllocated OBJECT-TYPE
    SYNTAX       TruthValue
    MAX-ACCESS   read-only
    STATUS       current
    DESCRIPTION
        "Cisco Firepower vnic:Ether:isAllocated managed object property"
    ::= { cfprApVnicEtherEntry 18 }

cfprApVnicEtherMtu OBJECT-TYPE
    SYNTAX       Gauge32
    MAX-ACCESS   read-only
    STATUS       current
    DESCRIPTION
        "Cisco Firepower vnic:Ether:mtu managed object property"
    ::= { cfprApVnicEtherEntry 19 }

cfprApVnicEtherName OBJECT-TYPE
    SYNTAX       SnmpAdminString
    MAX-ACCESS   read-only
    STATUS       current
    DESCRIPTION
        "Cisco Firepower vnic:Ether:name managed object property"
    ::= { cfprApVnicEtherEntry 20 }

cfprApVnicEtherNwCtrlPolicyName OBJECT-TYPE
    SYNTAX       SnmpAdminString
    MAX-ACCESS   read-only
    STATUS       current
    DESCRIPTION
        "Cisco Firepower vnic:Ether:nwCtrlPolicyName managed
        object property"
    ::= { cfprApVnicEtherEntry 21 }

cfprApVnicEtherNwTemplName OBJECT-TYPE
    SYNTAX       SnmpAdminString
    MAX-ACCESS   read-only
    STATUS       current
    DESCRIPTION
        "Cisco Firepower vnic:Ether:nwTemplName managed object property"
    ::= { cfprApVnicEtherEntry 22 }

cfprApVnicEtherOperAdaptorProfileName OBJECT-TYPE
    SYNTAX       SnmpAdminString
    MAX-ACCESS   read-only
    STATUS       current
    DESCRIPTION
        "Cisco Firepower vnic:Ether:operAdaptorProfileName
        managed object property"
    ::= { cfprApVnicEtherEntry 23 }

cfprApVnicEtherOperHostPort OBJECT-TYPE
    SYNTAX       CfprApVnicVnicOperHostPort
    MAX-ACCESS   read-only
    STATUS       current
    DESCRIPTION
        "Cisco Firepower vnic:Ether:operHostPort managed object property"
    ::= { cfprApVnicEtherEntry 24 }

cfprApVnicEtherOperIdentPoolName OBJECT-TYPE
    SYNTAX       SnmpAdminString
    MAX-ACCESS   read-only
    STATUS       current
    DESCRIPTION
        "Cisco Firepower vnic:Ether:operIdentPoolName managed
        object property"
    ::= { cfprApVnicEtherEntry 25 }

cfprApVnicEtherOperNwCtrlPolicyName OBJECT-TYPE
    SYNTAX       SnmpAdminString
    MAX-ACCESS   read-only
    STATUS       current
    DESCRIPTION
        "Cisco Firepower vnic:Ether:operNwCtrlPolicyName
        managed object property"
    ::= { cfprApVnicEtherEntry 26 }

cfprApVnicEtherOperNwTemplName OBJECT-TYPE
    SYNTAX       SnmpAdminString
    MAX-ACCESS   read-only
    STATUS       current
    DESCRIPTION
        "Cisco Firepower vnic:Ether:operNwTemplName managed
        object property"
    ::= { cfprApVnicEtherEntry 27 }

cfprApVnicEtherOperOrder OBJECT-TYPE
    SYNTAX       Gauge32
    MAX-ACCESS   read-only
    STATUS       current
    DESCRIPTION
        "Cisco Firepower vnic:Ether:operOrder managed object property"
    ::= { cfprApVnicEtherEntry 28 }

cfprApVnicEtherOperPinToGroupName OBJECT-TYPE
    SYNTAX       SnmpAdminString
    MAX-ACCESS   read-only
    STATUS       current
    DESCRIPTION
        "Cisco Firepower vnic:Ether:operPinToGroupName
        managed object property"
    ::= { cfprApVnicEtherEntry 29 }

cfprApVnicEtherOperQosPolicyName OBJECT-TYPE
    SYNTAX       SnmpAdminString
    MAX-ACCESS   read-only
    STATUS       current
    DESCRIPTION
        "Cisco Firepower vnic:Ether:operQosPolicyName managed
        object property"
    ::= { cfprApVnicEtherEntry 30 }

cfprApVnicEtherOperSpeed OBJECT-TYPE
    SYNTAX       Gauge32
    MAX-ACCESS   read-only
    STATUS       current
    DESCRIPTION
        "Cisco Firepower vnic:Ether:operSpeed managed object property"
    ::= { cfprApVnicEtherEntry 31 }

cfprApVnicEtherOperStatsPolicyName OBJECT-TYPE
    SYNTAX       SnmpAdminString
    MAX-ACCESS   read-only
    STATUS       current
    DESCRIPTION
        "Cisco Firepower vnic:Ether:operStatsPolicyName
        managed object property"
    ::= { cfprApVnicEtherEntry 32 }

cfprApVnicEtherOperVcon OBJECT-TYPE
    SYNTAX       SnmpAdminString
    MAX-ACCESS   read-only
    STATUS       current
    DESCRIPTION
        "Cisco Firepower vnic:Ether:operVcon managed object property"
    ::= { cfprApVnicEtherEntry 33 }

cfprApVnicEtherOrder OBJECT-TYPE
    SYNTAX       Gauge32
    MAX-ACCESS   read-only
    STATUS       current
    DESCRIPTION
        "Cisco Firepower vnic:Ether:order managed object property"
    ::= { cfprApVnicEtherEntry 34 }

cfprApVnicEtherOwner OBJECT-TYPE
    SYNTAX       CfprApVnicConnectionOwner
    MAX-ACCESS   read-only
    STATUS       current
    DESCRIPTION
        "Cisco Firepower vnic:Ether:owner managed object property"
    ::= { cfprApVnicEtherEntry 35 }

cfprApVnicEtherPfDn OBJECT-TYPE
    SYNTAX       SnmpAdminString
    MAX-ACCESS   read-only
    STATUS       current
    DESCRIPTION
        "Cisco Firepower vnic:Ether:pfDn managed object property"
    ::= { cfprApVnicEtherEntry 36 }

cfprApVnicEtherPinToGroupName OBJECT-TYPE
    SYNTAX       SnmpAdminString
    MAX-ACCESS   read-only
    STATUS       current
    DESCRIPTION
        "Cisco Firepower vnic:Ether:pinToGroupName managed
        object property"
    ::= { cfprApVnicEtherEntry 37 }

cfprApVnicEtherPortType OBJECT-TYPE
    SYNTAX       CfprApFabricSSAPortType
    MAX-ACCESS   read-only
    STATUS       current
    DESCRIPTION
        "Cisco Firepower vnic:Ether:portType managed object property"
    ::= { cfprApVnicEtherEntry 38 }

cfprApVnicEtherQosPolicyName OBJECT-TYPE
    SYNTAX       SnmpAdminString
    MAX-ACCESS   read-only
    STATUS       current
    DESCRIPTION
        "Cisco Firepower vnic:Ether:qosPolicyName managed object property"
    ::= { cfprApVnicEtherEntry 39 }

cfprApVnicEtherStatsPolicyName OBJECT-TYPE
    SYNTAX       SnmpAdminString
    MAX-ACCESS   read-only
    STATUS       current
    DESCRIPTION
        "Cisco Firepower vnic:Ether:statsPolicyName managed
        object property"
    ::= { cfprApVnicEtherEntry 40 }

cfprApVnicEtherSwitchId OBJECT-TYPE
    SYNTAX       CfprApVnicEtherBaseSwitchId
    MAX-ACCESS   read-only
    STATUS       current
    DESCRIPTION
        "Cisco Firepower vnic:Ether:switchId managed object property"
    ::= { cfprApVnicEtherEntry 41 }

cfprApVnicEtherType OBJECT-TYPE
    SYNTAX       CfprApVnicEtherType
    MAX-ACCESS   read-only
    STATUS       current
    DESCRIPTION
        "Cisco Firepower vnic:Ether:type managed object property"
    ::= { cfprApVnicEtherEntry 42 }

cfprApVnicEtherVirtualizationPreference OBJECT-TYPE
    SYNTAX       CfprApVnicVirtualizationPreferenceType
    MAX-ACCESS   read-only
    STATUS       current
    DESCRIPTION
        "Cisco Firepower vnic:Ether:virtualizationPreference
        managed object property"
    ::= { cfprApVnicEtherEntry 43 }

cfprApVnicEtherIfTable OBJECT-TYPE
    SYNTAX           SEQUENCE OF CfprApVnicEtherIfEntry
    MAX-ACCESS       not-accessible
    STATUS           current
    DESCRIPTION
        "Cisco Firepower vnic:EtherIf managed object table"
    ::= { cfprApVnicObjects 13 }

cfprApVnicEtherIfEntry OBJECT-TYPE
    SYNTAX           CfprApVnicEtherIfEntry
    MAX-ACCESS       not-accessible
    STATUS           current
    DESCRIPTION
        "Entry for the cfprApVnicEtherIfTable table."
    INDEX { cfprApVnicEtherIfInstanceId }
    ::= { cfprApVnicEtherIfTable 1 }

CfprApVnicEtherIfEntry ::= SEQUENCE {
    cfprApVnicEtherIfInstanceId                                      CfprApManagedObjectId,
    cfprApVnicEtherIfDn                                              CfprApManagedObjectDn,
    cfprApVnicEtherIfRn                                              SnmpAdminString,
    cfprApVnicEtherIfAddr                                            MacAddress,
    cfprApVnicEtherIfConfigQualifier                                 CfprApVnicConfigIssues,
    cfprApVnicEtherIfDefaultNet                                      TruthValue,
    cfprApVnicEtherIfFltAggr                                         Unsigned64,
    cfprApVnicEtherIfName                                            SnmpAdminString,
    cfprApVnicEtherIfOperState                                       CfprApVnicIfOperState,
    cfprApVnicEtherIfOperVnetDn                                      SnmpAdminString,
    cfprApVnicEtherIfOperVnetName                                    SnmpAdminString,
    cfprApVnicEtherIfOwner                                           CfprApVnicConnectionOwner,
    cfprApVnicEtherIfPubNwId                                         Gauge32,
    cfprApVnicEtherIfSharing                                         CfprApFabricVlanSharingType,
    cfprApVnicEtherIfSwitchId                                        CfprApVnicL2IfSwitchId,
    cfprApVnicEtherIfType                                            CfprApVnicAEtherIfType,
    cfprApVnicEtherIfVnet                                            Gauge32
}

cfprApVnicEtherIfInstanceId OBJECT-TYPE
    SYNTAX       CfprApManagedObjectId
    MAX-ACCESS   not-accessible
    STATUS       current
    DESCRIPTION
        "Instance identifier of the managed object."
    ::= { cfprApVnicEtherIfEntry 1 }

cfprApVnicEtherIfDn OBJECT-TYPE
    SYNTAX       CfprApManagedObjectDn
    MAX-ACCESS   read-only
    STATUS       current
    DESCRIPTION
        "Cisco Firepower vnic:EtherIf:dn managed object property"
    ::= { cfprApVnicEtherIfEntry 2 }

cfprApVnicEtherIfRn OBJECT-TYPE
    SYNTAX       SnmpAdminString
    MAX-ACCESS   read-only
    STATUS       current
    DESCRIPTION
        "Cisco Firepower vnic:EtherIf:rn managed object property"
    ::= { cfprApVnicEtherIfEntry 3 }

cfprApVnicEtherIfAddr OBJECT-TYPE
    SYNTAX       MacAddress
    MAX-ACCESS   read-only
    STATUS       current
    DESCRIPTION
        "Cisco Firepower vnic:EtherIf:addr managed object property"
    ::= { cfprApVnicEtherIfEntry 4 }

cfprApVnicEtherIfConfigQualifier OBJECT-TYPE
    SYNTAX       CfprApVnicConfigIssues
    MAX-ACCESS   read-only
    STATUS       current
    DESCRIPTION
        "Cisco Firepower vnic:EtherIf:configQualifier managed
        object property"
    ::= { cfprApVnicEtherIfEntry 5 }

cfprApVnicEtherIfDefaultNet OBJECT-TYPE
    SYNTAX       TruthValue
    MAX-ACCESS   read-only
    STATUS       current
    DESCRIPTION
        "Cisco Firepower vnic:EtherIf:defaultNet managed object property"
    ::= { cfprApVnicEtherIfEntry 6 }

cfprApVnicEtherIfFltAggr OBJECT-TYPE
    SYNTAX       Unsigned64
    MAX-ACCESS   read-only
    STATUS       current
    DESCRIPTION
        "Cisco Firepower vnic:EtherIf:fltAggr managed object property"
    ::= { cfprApVnicEtherIfEntry 7 }

cfprApVnicEtherIfName OBJECT-TYPE
    SYNTAX       SnmpAdminString
    MAX-ACCESS   read-only
    STATUS       current
    DESCRIPTION
        "Cisco Firepower vnic:EtherIf:name managed object property"
    ::= { cfprApVnicEtherIfEntry 8 }

cfprApVnicEtherIfOperState OBJECT-TYPE
    SYNTAX       CfprApVnicIfOperState
    MAX-ACCESS   read-only
    STATUS       current
    DESCRIPTION
        "Cisco Firepower vnic:EtherIf:operState managed object property"
    ::= { cfprApVnicEtherIfEntry 9 }

cfprApVnicEtherIfOperVnetDn OBJECT-TYPE
    SYNTAX       SnmpAdminString
    MAX-ACCESS   read-only
    STATUS       current
    DESCRIPTION
        "Cisco Firepower vnic:EtherIf:operVnetDn managed object property"
    ::= { cfprApVnicEtherIfEntry 10 }

cfprApVnicEtherIfOperVnetName OBJECT-TYPE
    SYNTAX       SnmpAdminString
    MAX-ACCESS   read-only
    STATUS       current
    DESCRIPTION
        "Cisco Firepower vnic:EtherIf:operVnetName managed
        object property"
    ::= { cfprApVnicEtherIfEntry 11 }

cfprApVnicEtherIfOwner OBJECT-TYPE
    SYNTAX       CfprApVnicConnectionOwner
    MAX-ACCESS   read-only
    STATUS       current
    DESCRIPTION
        "Cisco Firepower vnic:EtherIf:owner managed object property"
    ::= { cfprApVnicEtherIfEntry 12 }

cfprApVnicEtherIfPubNwId OBJECT-TYPE
    SYNTAX       Gauge32
    MAX-ACCESS   read-only
    STATUS       current
    DESCRIPTION
        "Cisco Firepower vnic:EtherIf:pubNwId managed object property"
    ::= { cfprApVnicEtherIfEntry 13 }

cfprApVnicEtherIfSharing OBJECT-TYPE
    SYNTAX       CfprApFabricVlanSharingType
    MAX-ACCESS   read-only
    STATUS       current
    DESCRIPTION
        "Cisco Firepower vnic:EtherIf:sharing managed object property"
    ::= { cfprApVnicEtherIfEntry 14 }

cfprApVnicEtherIfSwitchId OBJECT-TYPE
    SYNTAX       CfprApVnicL2IfSwitchId
    MAX-ACCESS   read-only
    STATUS       current
    DESCRIPTION
        "Cisco Firepower vnic:EtherIf:switchId managed object property"
    ::= { cfprApVnicEtherIfEntry 15 }

cfprApVnicEtherIfType OBJECT-TYPE
    SYNTAX       CfprApVnicAEtherIfType
    MAX-ACCESS   read-only
    STATUS       current
    DESCRIPTION
        "Cisco Firepower vnic:EtherIf:type managed object property"
    ::= { cfprApVnicEtherIfEntry 16 }

cfprApVnicEtherIfVnet OBJECT-TYPE
    SYNTAX       Gauge32
    MAX-ACCESS   read-only
    STATUS       current
    DESCRIPTION
        "Cisco Firepower vnic:EtherIf:vnet managed object property"
    ::= { cfprApVnicEtherIfEntry 17 }

cfprApVnicFcTable OBJECT-TYPE
    SYNTAX           SEQUENCE OF CfprApVnicFcEntry
    MAX-ACCESS       not-accessible
    STATUS           current
    DESCRIPTION
        "Cisco Firepower vnic:Fc managed object table"
    ::= { cfprApVnicObjects 14 }

cfprApVnicFcEntry OBJECT-TYPE
    SYNTAX           CfprApVnicFcEntry
    MAX-ACCESS       not-accessible
    STATUS           current
    DESCRIPTION
        "Entry for the cfprApVnicFcTable table."
    INDEX { cfprApVnicFcInstanceId }
    ::= { cfprApVnicFcTable 1 }

CfprApVnicFcEntry ::= SEQUENCE {
    cfprApVnicFcInstanceId                                           CfprApManagedObjectId,
    cfprApVnicFcDn                                                   CfprApManagedObjectDn,
    cfprApVnicFcRn                                                   SnmpAdminString,
    cfprApVnicFcAdaptorProfileName                                   SnmpAdminString,
    cfprApVnicFcAddr                                                 Unsigned64,
    cfprApVnicFcAdminHostPort                                        CfprApFabricHostPortId,
    cfprApVnicFcAdminVcon                                            SnmpAdminString,
    cfprApVnicFcAppRole                                              CfprApVnicAppRole,
    cfprApVnicFcBootDev                                              CfprApVnicVnicBootDev,
    cfprApVnicFcConfigQualifier                                      CfprApVnicConfigIssues,
    cfprApVnicFcConfigState                                          CfprApLsConfigState,
    cfprApVnicFcEquipmentDn                                          SnmpAdminString,
    cfprApVnicFcFltAggr                                              Unsigned64,
    cfprApVnicFcIdentPoolName                                        SnmpAdminString,
    cfprApVnicFcInstType                                             CfprApVnicInstantiation,
    cfprApVnicFcMaxDataFieldSize                                     Gauge32,
    cfprApVnicFcName                                                 SnmpAdminString,
    cfprApVnicFcNodeAddr                                             Unsigned64,
    cfprApVnicFcNwTemplName                                          SnmpAdminString,
    cfprApVnicFcOperHostPort                                         CfprApVnicVnicOperHostPort,
    cfprApVnicFcOperIdentPoolName                                    SnmpAdminString,
    cfprApVnicFcOperNwTemplName                                      SnmpAdminString,
    cfprApVnicFcOperOrder                                            Gauge32,
    cfprApVnicFcOperPinToGroupName                                   SnmpAdminString,
    cfprApVnicFcOperQosPolicyName                                    SnmpAdminString,
    cfprApVnicFcOperSpeed                                            Gauge32,
    cfprApVnicFcOperStatsPolicyName                                  SnmpAdminString,
    cfprApVnicFcOperVcon                                             SnmpAdminString,
    cfprApVnicFcOrder                                                Gauge32,
    cfprApVnicFcOwner                                                CfprApVnicConnectionOwner,
    cfprApVnicFcPersBind                                             CfprApVnicFcBasePersBind,
    cfprApVnicFcPersBindClear                                        TruthValue,
    cfprApVnicFcPinToGroupName                                       SnmpAdminString,
    cfprApVnicFcQosPolicyName                                        SnmpAdminString,
    cfprApVnicFcStatsPolicyName                                      SnmpAdminString,
    cfprApVnicFcSwitchId                                             CfprApNetworkSwitchId,
    cfprApVnicFcType                                                 CfprApVnicFcBaseType
}

cfprApVnicFcInstanceId OBJECT-TYPE
    SYNTAX       CfprApManagedObjectId
    MAX-ACCESS   not-accessible
    STATUS       current
    DESCRIPTION
        "Instance identifier of the managed object."
    ::= { cfprApVnicFcEntry 1 }

cfprApVnicFcDn OBJECT-TYPE
    SYNTAX       CfprApManagedObjectDn
    MAX-ACCESS   read-only
    STATUS       current
    DESCRIPTION
        "Cisco Firepower vnic:Fc:dn managed object property"
    ::= { cfprApVnicFcEntry 2 }

cfprApVnicFcRn OBJECT-TYPE
    SYNTAX       SnmpAdminString
    MAX-ACCESS   read-only
    STATUS       current
    DESCRIPTION
        "Cisco Firepower vnic:Fc:rn managed object property"
    ::= { cfprApVnicFcEntry 3 }

cfprApVnicFcAdaptorProfileName OBJECT-TYPE
    SYNTAX       SnmpAdminString
    MAX-ACCESS   read-only
    STATUS       current
    DESCRIPTION
        "Cisco Firepower vnic:Fc:adaptorProfileName managed
        object property"
    ::= { cfprApVnicFcEntry 4 }

cfprApVnicFcAddr OBJECT-TYPE
    SYNTAX       Unsigned64
    MAX-ACCESS   read-only
    STATUS       current
    DESCRIPTION
        "Cisco Firepower vnic:Fc:addr managed object property"
    ::= { cfprApVnicFcEntry 5 }

cfprApVnicFcAdminHostPort OBJECT-TYPE
    SYNTAX       CfprApFabricHostPortId
    MAX-ACCESS   read-only
    STATUS       current
    DESCRIPTION
        "Cisco Firepower vnic:Fc:adminHostPort managed object property"
    ::= { cfprApVnicFcEntry 6 }

cfprApVnicFcAdminVcon OBJECT-TYPE
    SYNTAX       SnmpAdminString
    MAX-ACCESS   read-only
    STATUS       current
    DESCRIPTION
        "Cisco Firepower vnic:Fc:adminVcon managed object property"
    ::= { cfprApVnicFcEntry 7 }

cfprApVnicFcAppRole OBJECT-TYPE
    SYNTAX       CfprApVnicAppRole
    MAX-ACCESS   read-only
    STATUS       current
    DESCRIPTION
        "Cisco Firepower vnic:Fc:appRole managed object property"
    ::= { cfprApVnicFcEntry 8 }

cfprApVnicFcBootDev OBJECT-TYPE
    SYNTAX       CfprApVnicVnicBootDev
    MAX-ACCESS   read-only
    STATUS       current
    DESCRIPTION
        "Cisco Firepower vnic:Fc:bootDev managed object property"
    ::= { cfprApVnicFcEntry 9 }

cfprApVnicFcConfigQualifier OBJECT-TYPE
    SYNTAX       CfprApVnicConfigIssues
    MAX-ACCESS   read-only
    STATUS       current
    DESCRIPTION
        "Cisco Firepower vnic:Fc:configQualifier managed object property"
    ::= { cfprApVnicFcEntry 10 }

cfprApVnicFcConfigState OBJECT-TYPE
    SYNTAX       CfprApLsConfigState
    MAX-ACCESS   read-only
    STATUS       current
    DESCRIPTION
        "Cisco Firepower vnic:Fc:configState managed object property"
    ::= { cfprApVnicFcEntry 11 }

cfprApVnicFcEquipmentDn OBJECT-TYPE
    SYNTAX       SnmpAdminString
    MAX-ACCESS   read-only
    STATUS       current
    DESCRIPTION
        "Cisco Firepower vnic:Fc:equipmentDn managed object property"
    ::= { cfprApVnicFcEntry 12 }

cfprApVnicFcFltAggr OBJECT-TYPE
    SYNTAX       Unsigned64
    MAX-ACCESS   read-only
    STATUS       current
    DESCRIPTION
        "Cisco Firepower vnic:Fc:fltAggr managed object property"
    ::= { cfprApVnicFcEntry 13 }

cfprApVnicFcIdentPoolName OBJECT-TYPE
    SYNTAX       SnmpAdminString
    MAX-ACCESS   read-only
    STATUS       current
    DESCRIPTION
        "Cisco Firepower vnic:Fc:identPoolName managed object property"
    ::= { cfprApVnicFcEntry 14 }

cfprApVnicFcInstType OBJECT-TYPE
    SYNTAX       CfprApVnicInstantiation
    MAX-ACCESS   read-only
    STATUS       current
    DESCRIPTION
        "Cisco Firepower vnic:Fc:instType managed object property"
    ::= { cfprApVnicFcEntry 15 }

cfprApVnicFcMaxDataFieldSize OBJECT-TYPE
    SYNTAX       Gauge32
    MAX-ACCESS   read-only
    STATUS       current
    DESCRIPTION
        "Cisco Firepower vnic:Fc:maxDataFieldSize managed object property"
    ::= { cfprApVnicFcEntry 16 }

cfprApVnicFcName OBJECT-TYPE
    SYNTAX       SnmpAdminString
    MAX-ACCESS   read-only
    STATUS       current
    DESCRIPTION
        "Cisco Firepower vnic:Fc:name managed object property"
    ::= { cfprApVnicFcEntry 17 }

cfprApVnicFcNodeAddr OBJECT-TYPE
    SYNTAX       Unsigned64
    MAX-ACCESS   read-only
    STATUS       current
    DESCRIPTION
        "Cisco Firepower vnic:Fc:nodeAddr managed object property"
    ::= { cfprApVnicFcEntry 18 }

cfprApVnicFcNwTemplName OBJECT-TYPE
    SYNTAX       SnmpAdminString
    MAX-ACCESS   read-only
    STATUS       current
    DESCRIPTION
        "Cisco Firepower vnic:Fc:nwTemplName managed object property"
    ::= { cfprApVnicFcEntry 19 }

cfprApVnicFcOperHostPort OBJECT-TYPE
    SYNTAX       CfprApVnicVnicOperHostPort
    MAX-ACCESS   read-only
    STATUS       current
    DESCRIPTION
        "Cisco Firepower vnic:Fc:operHostPort managed object property"
    ::= { cfprApVnicFcEntry 21 }

cfprApVnicFcOperIdentPoolName OBJECT-TYPE
    SYNTAX       SnmpAdminString
    MAX-ACCESS   read-only
    STATUS       current
    DESCRIPTION
        "Cisco Firepower vnic:Fc:operIdentPoolName managed
        object property"
    ::= { cfprApVnicFcEntry 22 }

cfprApVnicFcOperNwTemplName OBJECT-TYPE
    SYNTAX       SnmpAdminString
    MAX-ACCESS   read-only
    STATUS       current
    DESCRIPTION
        "Cisco Firepower vnic:Fc:operNwTemplName managed object property"
    ::= { cfprApVnicFcEntry 23 }

cfprApVnicFcOperOrder OBJECT-TYPE
    SYNTAX       Gauge32
    MAX-ACCESS   read-only
    STATUS       current
    DESCRIPTION
        "Cisco Firepower vnic:Fc:operOrder managed object property"
    ::= { cfprApVnicFcEntry 24 }

cfprApVnicFcOperPinToGroupName OBJECT-TYPE
    SYNTAX       SnmpAdminString
    MAX-ACCESS   read-only
    STATUS       current
    DESCRIPTION
        "Cisco Firepower vnic:Fc:operPinToGroupName managed
        object property"
    ::= { cfprApVnicFcEntry 25 }

cfprApVnicFcOperQosPolicyName OBJECT-TYPE
    SYNTAX       SnmpAdminString
    MAX-ACCESS   read-only
    STATUS       current
    DESCRIPTION
        "Cisco Firepower vnic:Fc:operQosPolicyName managed
        object property"
    ::= { cfprApVnicFcEntry 26 }

cfprApVnicFcOperSpeed OBJECT-TYPE
    SYNTAX       Gauge32
    MAX-ACCESS   read-only
    STATUS       current
    DESCRIPTION
        "Cisco Firepower vnic:Fc:operSpeed managed object property"
    ::= { cfprApVnicFcEntry 27 }

cfprApVnicFcOperStatsPolicyName OBJECT-TYPE
    SYNTAX       SnmpAdminString
    MAX-ACCESS   read-only
    STATUS       current
    DESCRIPTION
        "Cisco Firepower vnic:Fc:operStatsPolicyName managed
        object property"
    ::= { cfprApVnicFcEntry 28 }

cfprApVnicFcOperVcon OBJECT-TYPE
    SYNTAX       SnmpAdminString
    MAX-ACCESS   read-only
    STATUS       current
    DESCRIPTION
        "Cisco Firepower vnic:Fc:operVcon managed object property"
    ::= { cfprApVnicFcEntry 29 }

cfprApVnicFcOrder OBJECT-TYPE
    SYNTAX       Gauge32
    MAX-ACCESS   read-only
    STATUS       current
    DESCRIPTION
        "Cisco Firepower vnic:Fc:order managed object property"
    ::= { cfprApVnicFcEntry 30 }

cfprApVnicFcOwner OBJECT-TYPE
    SYNTAX       CfprApVnicConnectionOwner
    MAX-ACCESS   read-only
    STATUS       current
    DESCRIPTION
        "Cisco Firepower vnic:Fc:owner managed object property"
    ::= { cfprApVnicFcEntry 31 }

cfprApVnicFcPersBind OBJECT-TYPE
    SYNTAX       CfprApVnicFcBasePersBind
    MAX-ACCESS   read-only
    STATUS       current
    DESCRIPTION
        "Cisco Firepower vnic:Fc:persBind managed object property"
    ::= { cfprApVnicFcEntry 32 }

cfprApVnicFcPersBindClear OBJECT-TYPE
    SYNTAX       TruthValue
    MAX-ACCESS   read-only
    STATUS       current
    DESCRIPTION
        "Cisco Firepower vnic:Fc:persBindClear managed object property"
    ::= { cfprApVnicFcEntry 33 }

cfprApVnicFcPinToGroupName OBJECT-TYPE
    SYNTAX       SnmpAdminString
    MAX-ACCESS   read-only
    STATUS       current
    DESCRIPTION
        "Cisco Firepower vnic:Fc:pinToGroupName managed object property"
    ::= { cfprApVnicFcEntry 34 }

cfprApVnicFcQosPolicyName OBJECT-TYPE
    SYNTAX       SnmpAdminString
    MAX-ACCESS   read-only
    STATUS       current
    DESCRIPTION
        "Cisco Firepower vnic:Fc:qosPolicyName managed object property"
    ::= { cfprApVnicFcEntry 35 }

cfprApVnicFcStatsPolicyName OBJECT-TYPE
    SYNTAX       SnmpAdminString
    MAX-ACCESS   read-only
    STATUS       current
    DESCRIPTION
        "Cisco Firepower vnic:Fc:statsPolicyName managed object property"
    ::= { cfprApVnicFcEntry 36 }

cfprApVnicFcSwitchId OBJECT-TYPE
    SYNTAX       CfprApNetworkSwitchId
    MAX-ACCESS   read-only
    STATUS       current
    DESCRIPTION
        "Cisco Firepower vnic:Fc:switchId managed object property"
    ::= { cfprApVnicFcEntry 37 }

cfprApVnicFcType OBJECT-TYPE
    SYNTAX       CfprApVnicFcBaseType
    MAX-ACCESS   read-only
    STATUS       current
    DESCRIPTION
        "Cisco Firepower vnic:Fc:type managed object property"
    ::= { cfprApVnicFcEntry 38 }

cfprApVnicFcGroupDefTable OBJECT-TYPE
    SYNTAX           SEQUENCE OF CfprApVnicFcGroupDefEntry
    MAX-ACCESS       not-accessible
    STATUS           current
    DESCRIPTION
        "Cisco Firepower vnic:FcGroupDef managed object table"
    ::= { cfprApVnicObjects 15 }

cfprApVnicFcGroupDefEntry OBJECT-TYPE
    SYNTAX           CfprApVnicFcGroupDefEntry
    MAX-ACCESS       not-accessible
    STATUS           current
    DESCRIPTION
        "Entry for the cfprApVnicFcGroupDefTable table."
    INDEX { cfprApVnicFcGroupDefInstanceId }
    ::= { cfprApVnicFcGroupDefTable 1 }

CfprApVnicFcGroupDefEntry ::= SEQUENCE {
    cfprApVnicFcGroupDefInstanceId                                   CfprApManagedObjectId,
    cfprApVnicFcGroupDefDn                                           CfprApManagedObjectDn,
    cfprApVnicFcGroupDefRn                                           SnmpAdminString,
    cfprApVnicFcGroupDefAdaptorProfileName                           SnmpAdminString,
    cfprApVnicFcGroupDefDescr                                        SnmpAdminString,
    cfprApVnicFcGroupDefIdentPoolName                                SnmpAdminString,
    cfprApVnicFcGroupDefIntId                                        SnmpAdminString,
    cfprApVnicFcGroupDefMaxDataFieldSize                             Gauge32,
    cfprApVnicFcGroupDefName                                         SnmpAdminString,
    cfprApVnicFcGroupDefNwTemplName                                  SnmpAdminString,
    cfprApVnicFcGroupDefOperStatsPolicyName                          SnmpAdminString,
    cfprApVnicFcGroupDefPolicyLevel                                  Gauge32,
    cfprApVnicFcGroupDefPolicyOwner                                  CfprApPolicyPolicyOwner,
    cfprApVnicFcGroupDefQosPolicyName                                SnmpAdminString,
    cfprApVnicFcGroupDefStatsPolicyName                              SnmpAdminString
}

cfprApVnicFcGroupDefInstanceId OBJECT-TYPE
    SYNTAX       CfprApManagedObjectId
    MAX-ACCESS   not-accessible
    STATUS       current
    DESCRIPTION
        "Instance identifier of the managed object."
    ::= { cfprApVnicFcGroupDefEntry 1 }

cfprApVnicFcGroupDefDn OBJECT-TYPE
    SYNTAX       CfprApManagedObjectDn
    MAX-ACCESS   read-only
    STATUS       current
    DESCRIPTION
        "Cisco Firepower vnic:FcGroupDef:dn managed object property"
    ::= { cfprApVnicFcGroupDefEntry 2 }

cfprApVnicFcGroupDefRn OBJECT-TYPE
    SYNTAX       SnmpAdminString
    MAX-ACCESS   read-only
    STATUS       current
    DESCRIPTION
        "Cisco Firepower vnic:FcGroupDef:rn managed object property"
    ::= { cfprApVnicFcGroupDefEntry 3 }

cfprApVnicFcGroupDefAdaptorProfileName OBJECT-TYPE
    SYNTAX       SnmpAdminString
    MAX-ACCESS   read-only
    STATUS       current
    DESCRIPTION
        "Cisco Firepower vnic:FcGroupDef:adaptorProfileName
        managed object property"
    ::= { cfprApVnicFcGroupDefEntry 4 }

cfprApVnicFcGroupDefDescr OBJECT-TYPE
    SYNTAX       SnmpAdminString
    MAX-ACCESS   read-only
    STATUS       current
    DESCRIPTION
        "Cisco Firepower vnic:FcGroupDef:descr managed object property"
    ::= { cfprApVnicFcGroupDefEntry 5 }

cfprApVnicFcGroupDefIdentPoolName OBJECT-TYPE
    SYNTAX       SnmpAdminString
    MAX-ACCESS   read-only
    STATUS       current
    DESCRIPTION
        "Cisco Firepower vnic:FcGroupDef:identPoolName
        managed object property"
    ::= { cfprApVnicFcGroupDefEntry 6 }

cfprApVnicFcGroupDefIntId OBJECT-TYPE
    SYNTAX       SnmpAdminString
    MAX-ACCESS   read-only
    STATUS       current
    DESCRIPTION
        "Cisco Firepower vnic:FcGroupDef:intId managed object property"
    ::= { cfprApVnicFcGroupDefEntry 7 }

cfprApVnicFcGroupDefMaxDataFieldSize OBJECT-TYPE
    SYNTAX       Gauge32
    MAX-ACCESS   read-only
    STATUS       current
    DESCRIPTION
        "Cisco Firepower vnic:FcGroupDef:maxDataFieldSize
        managed object property"
    ::= { cfprApVnicFcGroupDefEntry 8 }

cfprApVnicFcGroupDefName OBJECT-TYPE
    SYNTAX       SnmpAdminString
    MAX-ACCESS   read-only
    STATUS       current
    DESCRIPTION
        "Cisco Firepower vnic:FcGroupDef:name managed object property"
    ::= { cfprApVnicFcGroupDefEntry 9 }

cfprApVnicFcGroupDefNwTemplName OBJECT-TYPE
    SYNTAX       SnmpAdminString
    MAX-ACCESS   read-only
    STATUS       current
    DESCRIPTION
        "Cisco Firepower vnic:FcGroupDef:nwTemplName managed
        object property"
    ::= { cfprApVnicFcGroupDefEntry 10 }

cfprApVnicFcGroupDefOperStatsPolicyName OBJECT-TYPE
    SYNTAX       SnmpAdminString
    MAX-ACCESS   read-only
    STATUS       current
    DESCRIPTION
        "Cisco Firepower vnic:FcGroupDef:operStatsPolicyName
        managed object property"
    ::= { cfprApVnicFcGroupDefEntry 11 }

cfprApVnicFcGroupDefPolicyLevel OBJECT-TYPE
    SYNTAX       Gauge32
    MAX-ACCESS   read-only
    STATUS       current
    DESCRIPTION
        "Cisco Firepower vnic:FcGroupDef:policyLevel managed
        object property"
    ::= { cfprApVnicFcGroupDefEntry 13 }

cfprApVnicFcGroupDefPolicyOwner OBJECT-TYPE
    SYNTAX       CfprApPolicyPolicyOwner
    MAX-ACCESS   read-only
    STATUS       current
    DESCRIPTION
        "Cisco Firepower vnic:FcGroupDef:policyOwner managed
        object property"
    ::= { cfprApVnicFcGroupDefEntry 14 }

cfprApVnicFcGroupDefQosPolicyName OBJECT-TYPE
    SYNTAX       SnmpAdminString
    MAX-ACCESS   read-only
    STATUS       current
    DESCRIPTION
        "Cisco Firepower vnic:FcGroupDef:qosPolicyName
        managed object property"
    ::= { cfprApVnicFcGroupDefEntry 15 }

cfprApVnicFcGroupDefStatsPolicyName OBJECT-TYPE
    SYNTAX       SnmpAdminString
    MAX-ACCESS   read-only
    STATUS       current
    DESCRIPTION
        "Cisco Firepower vnic:FcGroupDef:statsPolicyName
        managed object property"
    ::= { cfprApVnicFcGroupDefEntry 16 }

cfprApVnicFcGroupTemplTable OBJECT-TYPE
    SYNTAX           SEQUENCE OF CfprApVnicFcGroupTemplEntry
    MAX-ACCESS       not-accessible
    STATUS           current
    DESCRIPTION
        "Cisco Firepower vnic:FcGroupTempl managed object table"
    ::= { cfprApVnicObjects 16 }

cfprApVnicFcGroupTemplEntry OBJECT-TYPE
    SYNTAX           CfprApVnicFcGroupTemplEntry
    MAX-ACCESS       not-accessible
    STATUS           current
    DESCRIPTION
        "Entry for the cfprApVnicFcGroupTemplTable table."
    INDEX { cfprApVnicFcGroupTemplInstanceId }
    ::= { cfprApVnicFcGroupTemplTable 1 }

CfprApVnicFcGroupTemplEntry ::= SEQUENCE {
    cfprApVnicFcGroupTemplInstanceId                                 CfprApManagedObjectId,
    cfprApVnicFcGroupTemplDn                                         CfprApManagedObjectDn,
    cfprApVnicFcGroupTemplRn                                         SnmpAdminString,
    cfprApVnicFcGroupTemplAdaptorProfileName                         SnmpAdminString,
    cfprApVnicFcGroupTemplDescr                                      SnmpAdminString,
    cfprApVnicFcGroupTemplIdentPoolName                              SnmpAdminString,
    cfprApVnicFcGroupTemplIntId                                      SnmpAdminString,
    cfprApVnicFcGroupTemplMaxDataFieldSize                           Gauge32,
    cfprApVnicFcGroupTemplName                                       SnmpAdminString,
    cfprApVnicFcGroupTemplNwTemplName                                SnmpAdminString,
    cfprApVnicFcGroupTemplOperStatsPolicyName                        SnmpAdminString,
    cfprApVnicFcGroupTemplPolicyLevel                                Gauge32,
    cfprApVnicFcGroupTemplPolicyOwner                                CfprApPolicyPolicyOwner,
    cfprApVnicFcGroupTemplQosPolicyName                              SnmpAdminString,
    cfprApVnicFcGroupTemplStatsPolicyName                            SnmpAdminString,
    cfprApVnicFcGroupTemplTemplType                                  CfprApVnicTemplateType
}

cfprApVnicFcGroupTemplInstanceId OBJECT-TYPE
    SYNTAX       CfprApManagedObjectId
    MAX-ACCESS   not-accessible
    STATUS       current
    DESCRIPTION
        "Instance identifier of the managed object."
    ::= { cfprApVnicFcGroupTemplEntry 1 }

cfprApVnicFcGroupTemplDn OBJECT-TYPE
    SYNTAX       CfprApManagedObjectDn
    MAX-ACCESS   read-only
    STATUS       current
    DESCRIPTION
        "Cisco Firepower vnic:FcGroupTempl:dn managed object property"
    ::= { cfprApVnicFcGroupTemplEntry 2 }

cfprApVnicFcGroupTemplRn OBJECT-TYPE
    SYNTAX       SnmpAdminString
    MAX-ACCESS   read-only
    STATUS       current
    DESCRIPTION
        "Cisco Firepower vnic:FcGroupTempl:rn managed object property"
    ::= { cfprApVnicFcGroupTemplEntry 3 }

cfprApVnicFcGroupTemplAdaptorProfileName OBJECT-TYPE
    SYNTAX       SnmpAdminString
    MAX-ACCESS   read-only
    STATUS       current
    DESCRIPTION
        "Cisco Firepower vnic:FcGroupTempl:adaptorProfileName
        managed object property"
    ::= { cfprApVnicFcGroupTemplEntry 4 }

cfprApVnicFcGroupTemplDescr OBJECT-TYPE
    SYNTAX       SnmpAdminString
    MAX-ACCESS   read-only
    STATUS       current
    DESCRIPTION
        "Cisco Firepower vnic:FcGroupTempl:descr managed object property"
    ::= { cfprApVnicFcGroupTemplEntry 5 }

cfprApVnicFcGroupTemplIdentPoolName OBJECT-TYPE
    SYNTAX       SnmpAdminString
    MAX-ACCESS   read-only
    STATUS       current
    DESCRIPTION
        "Cisco Firepower vnic:FcGroupTempl:identPoolName
        managed object property"
    ::= { cfprApVnicFcGroupTemplEntry 6 }

cfprApVnicFcGroupTemplIntId OBJECT-TYPE
    SYNTAX       SnmpAdminString
    MAX-ACCESS   read-only
    STATUS       current
    DESCRIPTION
        "Cisco Firepower vnic:FcGroupTempl:intId managed object property"
    ::= { cfprApVnicFcGroupTemplEntry 7 }

cfprApVnicFcGroupTemplMaxDataFieldSize OBJECT-TYPE
    SYNTAX       Gauge32
    MAX-ACCESS   read-only
    STATUS       current
    DESCRIPTION
        "Cisco Firepower vnic:FcGroupTempl:maxDataFieldSize
        managed object property"
    ::= { cfprApVnicFcGroupTemplEntry 8 }

cfprApVnicFcGroupTemplName OBJECT-TYPE
    SYNTAX       SnmpAdminString
    MAX-ACCESS   read-only
    STATUS       current
    DESCRIPTION
        "Cisco Firepower vnic:FcGroupTempl:name managed object property"
    ::= { cfprApVnicFcGroupTemplEntry 9 }

cfprApVnicFcGroupTemplNwTemplName OBJECT-TYPE
    SYNTAX       SnmpAdminString
    MAX-ACCESS   read-only
    STATUS       current
    DESCRIPTION
        "Cisco Firepower vnic:FcGroupTempl:nwTemplName
        managed object property"
    ::= { cfprApVnicFcGroupTemplEntry 10 }

cfprApVnicFcGroupTemplOperStatsPolicyName OBJECT-TYPE
    SYNTAX       SnmpAdminString
    MAX-ACCESS   read-only
    STATUS       current
    DESCRIPTION
        "Cisco Firepower vnic:FcGroupTempl:operStatsPolicyName
        managed object property"
    ::= { cfprApVnicFcGroupTemplEntry 11 }

cfprApVnicFcGroupTemplPolicyLevel OBJECT-TYPE
    SYNTAX       Gauge32
    MAX-ACCESS   read-only
    STATUS       current
    DESCRIPTION
        "Cisco Firepower vnic:FcGroupTempl:policyLevel
        managed object property"
    ::= { cfprApVnicFcGroupTemplEntry 13 }

cfprApVnicFcGroupTemplPolicyOwner OBJECT-TYPE
    SYNTAX       CfprApPolicyPolicyOwner
    MAX-ACCESS   read-only
    STATUS       current
    DESCRIPTION
        "Cisco Firepower vnic:FcGroupTempl:policyOwner
        managed object property"
    ::= { cfprApVnicFcGroupTemplEntry 14 }

cfprApVnicFcGroupTemplQosPolicyName OBJECT-TYPE
    SYNTAX       SnmpAdminString
    MAX-ACCESS   read-only
    STATUS       current
    DESCRIPTION
        "Cisco Firepower vnic:FcGroupTempl:qosPolicyName
        managed object property"
    ::= { cfprApVnicFcGroupTemplEntry 15 }

cfprApVnicFcGroupTemplStatsPolicyName OBJECT-TYPE
    SYNTAX       SnmpAdminString
    MAX-ACCESS   read-only
    STATUS       current
    DESCRIPTION
        "Cisco Firepower vnic:FcGroupTempl:statsPolicyName
        managed object property"
    ::= { cfprApVnicFcGroupTemplEntry 16 }

cfprApVnicFcGroupTemplTemplType OBJECT-TYPE
    SYNTAX       CfprApVnicTemplateType
    MAX-ACCESS   read-only
    STATUS       current
    DESCRIPTION
        "Cisco Firepower vnic:FcGroupTempl:templType managed
        object property"
    ::= { cfprApVnicFcGroupTemplEntry 18 }

cfprApVnicFcIfTable OBJECT-TYPE
    SYNTAX           SEQUENCE OF CfprApVnicFcIfEntry
    MAX-ACCESS       not-accessible
    STATUS           current
    DESCRIPTION
        "Cisco Firepower vnic:FcIf managed object table"
    ::= { cfprApVnicObjects 17 }

cfprApVnicFcIfEntry OBJECT-TYPE
    SYNTAX           CfprApVnicFcIfEntry
    MAX-ACCESS       not-accessible
    STATUS           current
    DESCRIPTION
        "Entry for the cfprApVnicFcIfTable table."
    INDEX { cfprApVnicFcIfInstanceId }
    ::= { cfprApVnicFcIfTable 1 }

CfprApVnicFcIfEntry ::= SEQUENCE {
    cfprApVnicFcIfInstanceId                                         CfprApManagedObjectId,
    cfprApVnicFcIfDn                                                 CfprApManagedObjectDn,
    cfprApVnicFcIfRn                                                 SnmpAdminString,
    cfprApVnicFcIfConfigQualifier                                    CfprApVnicConfigIssues,
    cfprApVnicFcIfInitiator                                          Unsigned64,
    cfprApVnicFcIfName                                               SnmpAdminString,
    cfprApVnicFcIfOperState                                          CfprApVnicIfOperState,
    cfprApVnicFcIfOperVnetDn                                         SnmpAdminString,
    cfprApVnicFcIfOperVnetName                                       SnmpAdminString,
    cfprApVnicFcIfOwner                                              CfprApVnicConnectionOwner,
    cfprApVnicFcIfPubNwId                                            Gauge32,
    cfprApVnicFcIfSharing                                            CfprApFabricVlanSharingType,
    cfprApVnicFcIfSwitchId                                           CfprApVnicL2IfSwitchId,
    cfprApVnicFcIfType                                               CfprApVnicAFcIfType,
    cfprApVnicFcIfVnet                                               Gauge32
}

cfprApVnicFcIfInstanceId OBJECT-TYPE
    SYNTAX       CfprApManagedObjectId
    MAX-ACCESS   not-accessible
    STATUS       current
    DESCRIPTION
        "Instance identifier of the managed object."
    ::= { cfprApVnicFcIfEntry 1 }

cfprApVnicFcIfDn OBJECT-TYPE
    SYNTAX       CfprApManagedObjectDn
    MAX-ACCESS   read-only
    STATUS       current
    DESCRIPTION
        "Cisco Firepower vnic:FcIf:dn managed object property"
    ::= { cfprApVnicFcIfEntry 2 }

cfprApVnicFcIfRn OBJECT-TYPE
    SYNTAX       SnmpAdminString
    MAX-ACCESS   read-only
    STATUS       current
    DESCRIPTION
        "Cisco Firepower vnic:FcIf:rn managed object property"
    ::= { cfprApVnicFcIfEntry 3 }

cfprApVnicFcIfConfigQualifier OBJECT-TYPE
    SYNTAX       CfprApVnicConfigIssues
    MAX-ACCESS   read-only
    STATUS       current
    DESCRIPTION
        "Cisco Firepower vnic:FcIf:configQualifier managed
        object property"
    ::= { cfprApVnicFcIfEntry 4 }

cfprApVnicFcIfInitiator OBJECT-TYPE
    SYNTAX       Unsigned64
    MAX-ACCESS   read-only
    STATUS       current
    DESCRIPTION
        "Cisco Firepower vnic:FcIf:initiator managed object property"
    ::= { cfprApVnicFcIfEntry 5 }

cfprApVnicFcIfName OBJECT-TYPE
    SYNTAX       SnmpAdminString
    MAX-ACCESS   read-only
    STATUS       current
    DESCRIPTION
        "Cisco Firepower vnic:FcIf:name managed object property"
    ::= { cfprApVnicFcIfEntry 6 }

cfprApVnicFcIfOperState OBJECT-TYPE
    SYNTAX       CfprApVnicIfOperState
    MAX-ACCESS   read-only
    STATUS       current
    DESCRIPTION
        "Cisco Firepower vnic:FcIf:operState managed object property"
    ::= { cfprApVnicFcIfEntry 7 }

cfprApVnicFcIfOperVnetDn OBJECT-TYPE
    SYNTAX       SnmpAdminString
    MAX-ACCESS   read-only
    STATUS       current
    DESCRIPTION
        "Cisco Firepower vnic:FcIf:operVnetDn managed object property"
    ::= { cfprApVnicFcIfEntry 8 }

cfprApVnicFcIfOperVnetName OBJECT-TYPE
    SYNTAX       SnmpAdminString
    MAX-ACCESS   read-only
    STATUS       current
    DESCRIPTION
        "Cisco Firepower vnic:FcIf:operVnetName managed object property"
    ::= { cfprApVnicFcIfEntry 9 }

cfprApVnicFcIfOwner OBJECT-TYPE
    SYNTAX       CfprApVnicConnectionOwner
    MAX-ACCESS   read-only
    STATUS       current
    DESCRIPTION
        "Cisco Firepower vnic:FcIf:owner managed object property"
    ::= { cfprApVnicFcIfEntry 10 }

cfprApVnicFcIfPubNwId OBJECT-TYPE
    SYNTAX       Gauge32
    MAX-ACCESS   read-only
    STATUS       current
    DESCRIPTION
        "Cisco Firepower vnic:FcIf:pubNwId managed object property"
    ::= { cfprApVnicFcIfEntry 11 }

cfprApVnicFcIfSharing OBJECT-TYPE
    SYNTAX       CfprApFabricVlanSharingType
    MAX-ACCESS   read-only
    STATUS       current
    DESCRIPTION
        "Cisco Firepower vnic:FcIf:sharing managed object property"
    ::= { cfprApVnicFcIfEntry 12 }

cfprApVnicFcIfSwitchId OBJECT-TYPE
    SYNTAX       CfprApVnicL2IfSwitchId
    MAX-ACCESS   read-only
    STATUS       current
    DESCRIPTION
        "Cisco Firepower vnic:FcIf:switchId managed object property"
    ::= { cfprApVnicFcIfEntry 13 }

cfprApVnicFcIfType OBJECT-TYPE
    SYNTAX       CfprApVnicAFcIfType
    MAX-ACCESS   read-only
    STATUS       current
    DESCRIPTION
        "Cisco Firepower vnic:FcIf:type managed object property"
    ::= { cfprApVnicFcIfEntry 14 }

cfprApVnicFcIfVnet OBJECT-TYPE
    SYNTAX       Gauge32
    MAX-ACCESS   read-only
    STATUS       current
    DESCRIPTION
        "Cisco Firepower vnic:FcIf:vnet managed object property"
    ::= { cfprApVnicFcIfEntry 15 }

cfprApVnicFcLifTable OBJECT-TYPE
    SYNTAX           SEQUENCE OF CfprApVnicFcLifEntry
    MAX-ACCESS       not-accessible
    STATUS           current
    DESCRIPTION
        "Cisco Firepower vnic:FcLif managed object table"
    ::= { cfprApVnicObjects 18 }

cfprApVnicFcLifEntry OBJECT-TYPE
    SYNTAX           CfprApVnicFcLifEntry
    MAX-ACCESS       not-accessible
    STATUS           current
    DESCRIPTION
        "Entry for the cfprApVnicFcLifTable table."
    INDEX { cfprApVnicFcLifInstanceId }
    ::= { cfprApVnicFcLifTable 1 }

CfprApVnicFcLifEntry ::= SEQUENCE {
    cfprApVnicFcLifInstanceId                                        CfprApManagedObjectId,
    cfprApVnicFcLifDn                                                CfprApManagedObjectDn,
    cfprApVnicFcLifRn                                                SnmpAdminString,
    cfprApVnicFcLifAddr                                              Unsigned64,
    cfprApVnicFcLifName                                              SnmpAdminString,
    cfprApVnicFcLifNicDn                                             SnmpAdminString,
    cfprApVnicFcLifOwner                                             CfprApVnicConnectionOwner,
    cfprApVnicFcLifSwitchId                                          CfprApNetworkSwitchId,
    cfprApVnicFcLifType                                              CfprApVnicConnectionType,
    cfprApVnicFcLifVnicDn                                            SnmpAdminString
}

cfprApVnicFcLifInstanceId OBJECT-TYPE
    SYNTAX       CfprApManagedObjectId
    MAX-ACCESS   not-accessible
    STATUS       current
    DESCRIPTION
        "Instance identifier of the managed object."
    ::= { cfprApVnicFcLifEntry 1 }

cfprApVnicFcLifDn OBJECT-TYPE
    SYNTAX       CfprApManagedObjectDn
    MAX-ACCESS   read-only
    STATUS       current
    DESCRIPTION
        "Cisco Firepower vnic:FcLif:dn managed object property"
    ::= { cfprApVnicFcLifEntry 2 }

cfprApVnicFcLifRn OBJECT-TYPE
    SYNTAX       SnmpAdminString
    MAX-ACCESS   read-only
    STATUS       current
    DESCRIPTION
        "Cisco Firepower vnic:FcLif:rn managed object property"
    ::= { cfprApVnicFcLifEntry 3 }

cfprApVnicFcLifAddr OBJECT-TYPE
    SYNTAX       Unsigned64
    MAX-ACCESS   read-only
    STATUS       current
    DESCRIPTION
        "Cisco Firepower vnic:FcLif:addr managed object property"
    ::= { cfprApVnicFcLifEntry 4 }

cfprApVnicFcLifName OBJECT-TYPE
    SYNTAX       SnmpAdminString
    MAX-ACCESS   read-only
    STATUS       current
    DESCRIPTION
        "Cisco Firepower vnic:FcLif:name managed object property"
    ::= { cfprApVnicFcLifEntry 5 }

cfprApVnicFcLifNicDn OBJECT-TYPE
    SYNTAX       SnmpAdminString
    MAX-ACCESS   read-only
    STATUS       current
    DESCRIPTION
        "Cisco Firepower vnic:FcLif:nicDn managed object property"
    ::= { cfprApVnicFcLifEntry 6 }

cfprApVnicFcLifOwner OBJECT-TYPE
    SYNTAX       CfprApVnicConnectionOwner
    MAX-ACCESS   read-only
    STATUS       current
    DESCRIPTION
        "Cisco Firepower vnic:FcLif:owner managed object property"
    ::= { cfprApVnicFcLifEntry 7 }

cfprApVnicFcLifSwitchId OBJECT-TYPE
    SYNTAX       CfprApNetworkSwitchId
    MAX-ACCESS   read-only
    STATUS       current
    DESCRIPTION
        "Cisco Firepower vnic:FcLif:switchId managed object property"
    ::= { cfprApVnicFcLifEntry 8 }

cfprApVnicFcLifType OBJECT-TYPE
    SYNTAX       CfprApVnicConnectionType
    MAX-ACCESS   read-only
    STATUS       current
    DESCRIPTION
        "Cisco Firepower vnic:FcLif:type managed object property"
    ::= { cfprApVnicFcLifEntry 9 }

cfprApVnicFcLifVnicDn OBJECT-TYPE
    SYNTAX       SnmpAdminString
    MAX-ACCESS   read-only
    STATUS       current
    DESCRIPTION
        "Cisco Firepower vnic:FcLif:vnicDn managed object property"
    ::= { cfprApVnicFcLifEntry 10 }

cfprApVnicFcOEIfTable OBJECT-TYPE
    SYNTAX           SEQUENCE OF CfprApVnicFcOEIfEntry
    MAX-ACCESS       not-accessible
    STATUS           current
    DESCRIPTION
        "Cisco Firepower vnic:FcOEIf managed object table"
    ::= { cfprApVnicObjects 20 }

cfprApVnicFcOEIfEntry OBJECT-TYPE
    SYNTAX           CfprApVnicFcOEIfEntry
    MAX-ACCESS       not-accessible
    STATUS           current
    DESCRIPTION
        "Entry for the cfprApVnicFcOEIfTable table."
    INDEX { cfprApVnicFcOEIfInstanceId }
    ::= { cfprApVnicFcOEIfTable 1 }

CfprApVnicFcOEIfEntry ::= SEQUENCE {
    cfprApVnicFcOEIfInstanceId                                       CfprApManagedObjectId,
    cfprApVnicFcOEIfDn                                               CfprApManagedObjectDn,
    cfprApVnicFcOEIfRn                                               SnmpAdminString,
    cfprApVnicFcOEIfConfigQualifier                                  CfprApVnicConfigIssues,
    cfprApVnicFcOEIfInitiator                                        Unsigned64,
    cfprApVnicFcOEIfName                                             SnmpAdminString,
    cfprApVnicFcOEIfOperState                                        CfprApVnicIfOperState,
    cfprApVnicFcOEIfOperVnetDn                                       SnmpAdminString,
    cfprApVnicFcOEIfOperVnetName                                     SnmpAdminString,
    cfprApVnicFcOEIfOwner                                            CfprApVnicConnectionOwner,
    cfprApVnicFcOEIfPubNwId                                          Gauge32,
    cfprApVnicFcOEIfSharing                                          CfprApFabricVlanSharingType,
    cfprApVnicFcOEIfSwitchId                                         CfprApVnicL2IfSwitchId,
    cfprApVnicFcOEIfType                                             CfprApVnicAFcIfType,
    cfprApVnicFcOEIfVnet                                             Gauge32
}

cfprApVnicFcOEIfInstanceId OBJECT-TYPE
    SYNTAX       CfprApManagedObjectId
    MAX-ACCESS   not-accessible
    STATUS       current
    DESCRIPTION
        "Instance identifier of the managed object."
    ::= { cfprApVnicFcOEIfEntry 1 }

cfprApVnicFcOEIfDn OBJECT-TYPE
    SYNTAX       CfprApManagedObjectDn
    MAX-ACCESS   read-only
    STATUS       current
    DESCRIPTION
        "Cisco Firepower vnic:FcOEIf:dn managed object property"
    ::= { cfprApVnicFcOEIfEntry 2 }

cfprApVnicFcOEIfRn OBJECT-TYPE
    SYNTAX       SnmpAdminString
    MAX-ACCESS   read-only
    STATUS       current
    DESCRIPTION
        "Cisco Firepower vnic:FcOEIf:rn managed object property"
    ::= { cfprApVnicFcOEIfEntry 3 }

cfprApVnicFcOEIfConfigQualifier OBJECT-TYPE
    SYNTAX       CfprApVnicConfigIssues
    MAX-ACCESS   read-only
    STATUS       current
    DESCRIPTION
        "Cisco Firepower vnic:FcOEIf:configQualifier managed
        object property"
    ::= { cfprApVnicFcOEIfEntry 4 }

cfprApVnicFcOEIfInitiator OBJECT-TYPE
    SYNTAX       Unsigned64
    MAX-ACCESS   read-only
    STATUS       current
    DESCRIPTION
        "Cisco Firepower vnic:FcOEIf:initiator managed object property"
    ::= { cfprApVnicFcOEIfEntry 5 }

cfprApVnicFcOEIfName OBJECT-TYPE
    SYNTAX       SnmpAdminString
    MAX-ACCESS   read-only
    STATUS       current
    DESCRIPTION
        "Cisco Firepower vnic:FcOEIf:name managed object property"
    ::= { cfprApVnicFcOEIfEntry 6 }

cfprApVnicFcOEIfOperState OBJECT-TYPE
    SYNTAX       CfprApVnicIfOperState
    MAX-ACCESS   read-only
    STATUS       current
    DESCRIPTION
        "Cisco Firepower vnic:FcOEIf:operState managed object property"
    ::= { cfprApVnicFcOEIfEntry 7 }

cfprApVnicFcOEIfOperVnetDn OBJECT-TYPE
    SYNTAX       SnmpAdminString
    MAX-ACCESS   read-only
    STATUS       current
    DESCRIPTION
        "Cisco Firepower vnic:FcOEIf:operVnetDn managed object property"
    ::= { cfprApVnicFcOEIfEntry 8 }

cfprApVnicFcOEIfOperVnetName OBJECT-TYPE
    SYNTAX       SnmpAdminString
    MAX-ACCESS   read-only
    STATUS       current
    DESCRIPTION
        "Cisco Firepower vnic:FcOEIf:operVnetName managed object property"
    ::= { cfprApVnicFcOEIfEntry 9 }

cfprApVnicFcOEIfOwner OBJECT-TYPE
    SYNTAX       CfprApVnicConnectionOwner
    MAX-ACCESS   read-only
    STATUS       current
    DESCRIPTION
        "Cisco Firepower vnic:FcOEIf:owner managed object property"
    ::= { cfprApVnicFcOEIfEntry 10 }

cfprApVnicFcOEIfPubNwId OBJECT-TYPE
    SYNTAX       Gauge32
    MAX-ACCESS   read-only
    STATUS       current
    DESCRIPTION
        "Cisco Firepower vnic:FcOEIf:pubNwId managed object property"
    ::= { cfprApVnicFcOEIfEntry 11 }

cfprApVnicFcOEIfSharing OBJECT-TYPE
    SYNTAX       CfprApFabricVlanSharingType
    MAX-ACCESS   read-only
    STATUS       current
    DESCRIPTION
        "Cisco Firepower vnic:FcOEIf:sharing managed object property"
    ::= { cfprApVnicFcOEIfEntry 12 }

cfprApVnicFcOEIfSwitchId OBJECT-TYPE
    SYNTAX       CfprApVnicL2IfSwitchId
    MAX-ACCESS   read-only
    STATUS       current
    DESCRIPTION
        "Cisco Firepower vnic:FcOEIf:switchId managed object property"
    ::= { cfprApVnicFcOEIfEntry 13 }

cfprApVnicFcOEIfType OBJECT-TYPE
    SYNTAX       CfprApVnicAFcIfType
    MAX-ACCESS   read-only
    STATUS       current
    DESCRIPTION
        "Cisco Firepower vnic:FcOEIf:type managed object property"
    ::= { cfprApVnicFcOEIfEntry 14 }

cfprApVnicFcOEIfVnet OBJECT-TYPE
    SYNTAX       Gauge32
    MAX-ACCESS   read-only
    STATUS       current
    DESCRIPTION
        "Cisco Firepower vnic:FcOEIf:vnet managed object property"
    ::= { cfprApVnicFcOEIfEntry 15 }

cfprApVnicIPv4DhcpTable OBJECT-TYPE
    SYNTAX           SEQUENCE OF CfprApVnicIPv4DhcpEntry
    MAX-ACCESS       not-accessible
    STATUS           current
    DESCRIPTION
        "Cisco Firepower vnic:IPv4Dhcp managed object table"
    ::= { cfprApVnicObjects 21 }

cfprApVnicIPv4DhcpEntry OBJECT-TYPE
    SYNTAX           CfprApVnicIPv4DhcpEntry
    MAX-ACCESS       not-accessible
    STATUS           current
    DESCRIPTION
        "Entry for the cfprApVnicIPv4DhcpTable table."
    INDEX { cfprApVnicIPv4DhcpInstanceId }
    ::= { cfprApVnicIPv4DhcpTable 1 }

CfprApVnicIPv4DhcpEntry ::= SEQUENCE {
    cfprApVnicIPv4DhcpInstanceId                                     CfprApManagedObjectId,
    cfprApVnicIPv4DhcpDn                                             CfprApManagedObjectDn,
    cfprApVnicIPv4DhcpRn                                             SnmpAdminString,
    cfprApVnicIPv4DhcpAddr                                           InetAddressIPv4,
    cfprApVnicIPv4DhcpDefGw                                          InetAddressIPv4,
    cfprApVnicIPv4DhcpSubnet                                         InetAddressIPv4
}

cfprApVnicIPv4DhcpInstanceId OBJECT-TYPE
    SYNTAX       CfprApManagedObjectId
    MAX-ACCESS   not-accessible
    STATUS       current
    DESCRIPTION
        "Instance identifier of the managed object."
    ::= { cfprApVnicIPv4DhcpEntry 1 }

cfprApVnicIPv4DhcpDn OBJECT-TYPE
    SYNTAX       CfprApManagedObjectDn
    MAX-ACCESS   read-only
    STATUS       current
    DESCRIPTION
        "Cisco Firepower vnic:IPv4Dhcp:dn managed object property"
    ::= { cfprApVnicIPv4DhcpEntry 2 }

cfprApVnicIPv4DhcpRn OBJECT-TYPE
    SYNTAX       SnmpAdminString
    MAX-ACCESS   read-only
    STATUS       current
    DESCRIPTION
        "Cisco Firepower vnic:IPv4Dhcp:rn managed object property"
    ::= { cfprApVnicIPv4DhcpEntry 3 }

cfprApVnicIPv4DhcpAddr OBJECT-TYPE
    SYNTAX       InetAddressIPv4
    MAX-ACCESS   read-only
    STATUS       current
    DESCRIPTION
        "Cisco Firepower vnic:IPv4Dhcp:addr managed object property"
    ::= { cfprApVnicIPv4DhcpEntry 4 }

cfprApVnicIPv4DhcpDefGw OBJECT-TYPE
    SYNTAX       InetAddressIPv4
    MAX-ACCESS   read-only
    STATUS       current
    DESCRIPTION
        "Cisco Firepower vnic:IPv4Dhcp:defGw managed object property"
    ::= { cfprApVnicIPv4DhcpEntry 5 }

cfprApVnicIPv4DhcpSubnet OBJECT-TYPE
    SYNTAX       InetAddressIPv4
    MAX-ACCESS   read-only
    STATUS       current
    DESCRIPTION
        "Cisco Firepower vnic:IPv4Dhcp:subnet managed object property"
    ::= { cfprApVnicIPv4DhcpEntry 6 }

cfprApVnicIPv4DnsTable OBJECT-TYPE
    SYNTAX           SEQUENCE OF CfprApVnicIPv4DnsEntry
    MAX-ACCESS       not-accessible
    STATUS           current
    DESCRIPTION
        "Cisco Firepower vnic:IPv4Dns managed object table"
    ::= { cfprApVnicObjects 22 }

cfprApVnicIPv4DnsEntry OBJECT-TYPE
    SYNTAX           CfprApVnicIPv4DnsEntry
    MAX-ACCESS       not-accessible
    STATUS           current
    DESCRIPTION
        "Entry for the cfprApVnicIPv4DnsTable table."
    INDEX { cfprApVnicIPv4DnsInstanceId }
    ::= { cfprApVnicIPv4DnsTable 1 }

CfprApVnicIPv4DnsEntry ::= SEQUENCE {
    cfprApVnicIPv4DnsInstanceId                                      CfprApManagedObjectId,
    cfprApVnicIPv4DnsDn                                              CfprApManagedObjectDn,
    cfprApVnicIPv4DnsRn                                              SnmpAdminString,
    cfprApVnicIPv4DnsAddr                                            InetAddressIPv4,
    cfprApVnicIPv4DnsDefGw                                           InetAddressIPv4,
    cfprApVnicIPv4DnsPref                                            CfprApVnicIPv4DnsPref,
    cfprApVnicIPv4DnsSubnet                                          InetAddressIPv4
}

cfprApVnicIPv4DnsInstanceId OBJECT-TYPE
    SYNTAX       CfprApManagedObjectId
    MAX-ACCESS   not-accessible
    STATUS       current
    DESCRIPTION
        "Instance identifier of the managed object."
    ::= { cfprApVnicIPv4DnsEntry 1 }

cfprApVnicIPv4DnsDn OBJECT-TYPE
    SYNTAX       CfprApManagedObjectDn
    MAX-ACCESS   read-only
    STATUS       current
    DESCRIPTION
        "Cisco Firepower vnic:IPv4Dns:dn managed object property"
    ::= { cfprApVnicIPv4DnsEntry 2 }

cfprApVnicIPv4DnsRn OBJECT-TYPE
    SYNTAX       SnmpAdminString
    MAX-ACCESS   read-only
    STATUS       current
    DESCRIPTION
        "Cisco Firepower vnic:IPv4Dns:rn managed object property"
    ::= { cfprApVnicIPv4DnsEntry 3 }

cfprApVnicIPv4DnsAddr OBJECT-TYPE
    SYNTAX       InetAddressIPv4
    MAX-ACCESS   read-only
    STATUS       current
    DESCRIPTION
        "Cisco Firepower vnic:IPv4Dns:addr managed object property"
    ::= { cfprApVnicIPv4DnsEntry 4 }

cfprApVnicIPv4DnsDefGw OBJECT-TYPE
    SYNTAX       InetAddressIPv4
    MAX-ACCESS   read-only
    STATUS       current
    DESCRIPTION
        "Cisco Firepower vnic:IPv4Dns:defGw managed object property"
    ::= { cfprApVnicIPv4DnsEntry 5 }

cfprApVnicIPv4DnsPref OBJECT-TYPE
    SYNTAX       CfprApVnicIPv4DnsPref
    MAX-ACCESS   read-only
    STATUS       current
    DESCRIPTION
        "Cisco Firepower vnic:IPv4Dns:pref managed object property"
    ::= { cfprApVnicIPv4DnsEntry 6 }

cfprApVnicIPv4DnsSubnet OBJECT-TYPE
    SYNTAX       InetAddressIPv4
    MAX-ACCESS   read-only
    STATUS       current
    DESCRIPTION
        "Cisco Firepower vnic:IPv4Dns:subnet managed object property"
    ::= { cfprApVnicIPv4DnsEntry 7 }

cfprApVnicIPv4IfTable OBJECT-TYPE
    SYNTAX           SEQUENCE OF CfprApVnicIPv4IfEntry
    MAX-ACCESS       not-accessible
    STATUS           current
    DESCRIPTION
        "Cisco Firepower vnic:IPv4If managed object table"
    ::= { cfprApVnicObjects 23 }

cfprApVnicIPv4IfEntry OBJECT-TYPE
    SYNTAX           CfprApVnicIPv4IfEntry
    MAX-ACCESS       not-accessible
    STATUS           current
    DESCRIPTION
        "Entry for the cfprApVnicIPv4IfTable table."
    INDEX { cfprApVnicIPv4IfInstanceId }
    ::= { cfprApVnicIPv4IfTable 1 }

CfprApVnicIPv4IfEntry ::= SEQUENCE {
    cfprApVnicIPv4IfInstanceId                                       CfprApManagedObjectId,
    cfprApVnicIPv4IfDn                                               CfprApManagedObjectDn,
    cfprApVnicIPv4IfRn                                               SnmpAdminString,
    cfprApVnicIPv4IfAddr                                             InetAddressIPv4,
    cfprApVnicIPv4IfConfigQualifier                                  CfprApVnicConfigIssues,
    cfprApVnicIPv4IfName                                             SnmpAdminString,
    cfprApVnicIPv4IfOperState                                        CfprApVnicIfOperState,
    cfprApVnicIPv4IfOperVnetDn                                       SnmpAdminString,
    cfprApVnicIPv4IfOperVnetName                                     SnmpAdminString,
    cfprApVnicIPv4IfOwner                                            CfprApVnicConnectionOwner,
    cfprApVnicIPv4IfPubNwId                                          Gauge32,
    cfprApVnicIPv4IfSharing                                          CfprApFabricVlanSharingType,
    cfprApVnicIPv4IfSwitchId                                         CfprApNetworkSwitchId,
    cfprApVnicIPv4IfType                                             CfprApVnicConnectionType,
    cfprApVnicIPv4IfVnet                                             Gauge32
}

cfprApVnicIPv4IfInstanceId OBJECT-TYPE
    SYNTAX       CfprApManagedObjectId
    MAX-ACCESS   not-accessible
    STATUS       current
    DESCRIPTION
        "Instance identifier of the managed object."
    ::= { cfprApVnicIPv4IfEntry 1 }

cfprApVnicIPv4IfDn OBJECT-TYPE
    SYNTAX       CfprApManagedObjectDn
    MAX-ACCESS   read-only
    STATUS       current
    DESCRIPTION
        "Cisco Firepower vnic:IPv4If:dn managed object property"
    ::= { cfprApVnicIPv4IfEntry 2 }

cfprApVnicIPv4IfRn OBJECT-TYPE
    SYNTAX       SnmpAdminString
    MAX-ACCESS   read-only
    STATUS       current
    DESCRIPTION
        "Cisco Firepower vnic:IPv4If:rn managed object property"
    ::= { cfprApVnicIPv4IfEntry 3 }

cfprApVnicIPv4IfAddr OBJECT-TYPE
    SYNTAX       InetAddressIPv4
    MAX-ACCESS   read-only
    STATUS       current
    DESCRIPTION
        "Cisco Firepower vnic:IPv4If:addr managed object property"
    ::= { cfprApVnicIPv4IfEntry 4 }

cfprApVnicIPv4IfConfigQualifier OBJECT-TYPE
    SYNTAX       CfprApVnicConfigIssues
    MAX-ACCESS   read-only
    STATUS       current
    DESCRIPTION
        "Cisco Firepower vnic:IPv4If:configQualifier managed
        object property"
    ::= { cfprApVnicIPv4IfEntry 5 }

cfprApVnicIPv4IfName OBJECT-TYPE
    SYNTAX       SnmpAdminString
    MAX-ACCESS   read-only
    STATUS       current
    DESCRIPTION
        "Cisco Firepower vnic:IPv4If:name managed object property"
    ::= { cfprApVnicIPv4IfEntry 6 }

cfprApVnicIPv4IfOperState OBJECT-TYPE
    SYNTAX       CfprApVnicIfOperState
    MAX-ACCESS   read-only
    STATUS       current
    DESCRIPTION
        "Cisco Firepower vnic:IPv4If:operState managed object property"
    ::= { cfprApVnicIPv4IfEntry 7 }

cfprApVnicIPv4IfOperVnetDn OBJECT-TYPE
    SYNTAX       SnmpAdminString
    MAX-ACCESS   read-only
    STATUS       current
    DESCRIPTION
        "Cisco Firepower vnic:IPv4If:operVnetDn managed object property"
    ::= { cfprApVnicIPv4IfEntry 8 }

cfprApVnicIPv4IfOperVnetName OBJECT-TYPE
    SYNTAX       SnmpAdminString
    MAX-ACCESS   read-only
    STATUS       current
    DESCRIPTION
        "Cisco Firepower vnic:IPv4If:operVnetName managed object property"
    ::= { cfprApVnicIPv4IfEntry 9 }

cfprApVnicIPv4IfOwner OBJECT-TYPE
    SYNTAX       CfprApVnicConnectionOwner
    MAX-ACCESS   read-only
    STATUS       current
    DESCRIPTION
        "Cisco Firepower vnic:IPv4If:owner managed object property"
    ::= { cfprApVnicIPv4IfEntry 10 }

cfprApVnicIPv4IfPubNwId OBJECT-TYPE
    SYNTAX       Gauge32
    MAX-ACCESS   read-only
    STATUS       current
    DESCRIPTION
        "Cisco Firepower vnic:IPv4If:pubNwId managed object property"
    ::= { cfprApVnicIPv4IfEntry 11 }

cfprApVnicIPv4IfSharing OBJECT-TYPE
    SYNTAX       CfprApFabricVlanSharingType
    MAX-ACCESS   read-only
    STATUS       current
    DESCRIPTION
        "Cisco Firepower vnic:IPv4If:sharing managed object property"
    ::= { cfprApVnicIPv4IfEntry 12 }

cfprApVnicIPv4IfSwitchId OBJECT-TYPE
    SYNTAX       CfprApNetworkSwitchId
    MAX-ACCESS   read-only
    STATUS       current
    DESCRIPTION
        "Cisco Firepower vnic:IPv4If:switchId managed object property"
    ::= { cfprApVnicIPv4IfEntry 13 }

cfprApVnicIPv4IfType OBJECT-TYPE
    SYNTAX       CfprApVnicConnectionType
    MAX-ACCESS   read-only
    STATUS       current
    DESCRIPTION
        "Cisco Firepower vnic:IPv4If:type managed object property"
    ::= { cfprApVnicIPv4IfEntry 14 }

cfprApVnicIPv4IfVnet OBJECT-TYPE
    SYNTAX       Gauge32
    MAX-ACCESS   read-only
    STATUS       current
    DESCRIPTION
        "Cisco Firepower vnic:IPv4If:vnet managed object property"
    ::= { cfprApVnicIPv4IfEntry 15 }

cfprApVnicIPv4IscsiAddrTable OBJECT-TYPE
    SYNTAX           SEQUENCE OF CfprApVnicIPv4IscsiAddrEntry
    MAX-ACCESS       not-accessible
    STATUS           current
    DESCRIPTION
        "Cisco Firepower vnic:IPv4IscsiAddr managed object table"
    ::= { cfprApVnicObjects 24 }

cfprApVnicIPv4IscsiAddrEntry OBJECT-TYPE
    SYNTAX           CfprApVnicIPv4IscsiAddrEntry
    MAX-ACCESS       not-accessible
    STATUS           current
    DESCRIPTION
        "Entry for the cfprApVnicIPv4IscsiAddrTable table."
    INDEX { cfprApVnicIPv4IscsiAddrInstanceId }
    ::= { cfprApVnicIPv4IscsiAddrTable 1 }

CfprApVnicIPv4IscsiAddrEntry ::= SEQUENCE {
    cfprApVnicIPv4IscsiAddrInstanceId                                CfprApManagedObjectId,
    cfprApVnicIPv4IscsiAddrDn                                        CfprApManagedObjectDn,
    cfprApVnicIPv4IscsiAddrRn                                        SnmpAdminString,
    cfprApVnicIPv4IscsiAddrAddr                                      InetAddressIPv4,
    cfprApVnicIPv4IscsiAddrDefGw                                     InetAddressIPv4,
    cfprApVnicIPv4IscsiAddrPrimDns                                   InetAddressIPv4,
    cfprApVnicIPv4IscsiAddrSecDns                                    InetAddressIPv4,
    cfprApVnicIPv4IscsiAddrSubnet                                    InetAddressIPv4
}

cfprApVnicIPv4IscsiAddrInstanceId OBJECT-TYPE
    SYNTAX       CfprApManagedObjectId
    MAX-ACCESS   not-accessible
    STATUS       current
    DESCRIPTION
        "Instance identifier of the managed object."
    ::= { cfprApVnicIPv4IscsiAddrEntry 1 }

cfprApVnicIPv4IscsiAddrDn OBJECT-TYPE
    SYNTAX       CfprApManagedObjectDn
    MAX-ACCESS   read-only
    STATUS       current
    DESCRIPTION
        "Cisco Firepower vnic:IPv4IscsiAddr:dn managed object property"
    ::= { cfprApVnicIPv4IscsiAddrEntry 2 }

cfprApVnicIPv4IscsiAddrRn OBJECT-TYPE
    SYNTAX       SnmpAdminString
    MAX-ACCESS   read-only
    STATUS       current
    DESCRIPTION
        "Cisco Firepower vnic:IPv4IscsiAddr:rn managed object property"
    ::= { cfprApVnicIPv4IscsiAddrEntry 3 }

cfprApVnicIPv4IscsiAddrAddr OBJECT-TYPE
    SYNTAX       InetAddressIPv4
    MAX-ACCESS   read-only
    STATUS       current
    DESCRIPTION
        "Cisco Firepower vnic:IPv4IscsiAddr:addr managed object property"
    ::= { cfprApVnicIPv4IscsiAddrEntry 4 }

cfprApVnicIPv4IscsiAddrDefGw OBJECT-TYPE
    SYNTAX       InetAddressIPv4
    MAX-ACCESS   read-only
    STATUS       current
    DESCRIPTION
        "Cisco Firepower vnic:IPv4IscsiAddr:defGw managed object property"
    ::= { cfprApVnicIPv4IscsiAddrEntry 5 }

cfprApVnicIPv4IscsiAddrPrimDns OBJECT-TYPE
    SYNTAX       InetAddressIPv4
    MAX-ACCESS   read-only
    STATUS       current
    DESCRIPTION
        "Cisco Firepower vnic:IPv4IscsiAddr:primDns managed
        object property"
    ::= { cfprApVnicIPv4IscsiAddrEntry 6 }

cfprApVnicIPv4IscsiAddrSecDns OBJECT-TYPE
    SYNTAX       InetAddressIPv4
    MAX-ACCESS   read-only
    STATUS       current
    DESCRIPTION
        "Cisco Firepower vnic:IPv4IscsiAddr:secDns managed
        object property"
    ::= { cfprApVnicIPv4IscsiAddrEntry 7 }

cfprApVnicIPv4IscsiAddrSubnet OBJECT-TYPE
    SYNTAX       InetAddressIPv4
    MAX-ACCESS   read-only
    STATUS       current
    DESCRIPTION
        "Cisco Firepower vnic:IPv4IscsiAddr:subnet managed
        object property"
    ::= { cfprApVnicIPv4IscsiAddrEntry 8 }

cfprApVnicIPv4PooledIscsiAddrTable OBJECT-TYPE
    SYNTAX           SEQUENCE OF CfprApVnicIPv4PooledIscsiAddrEntry
    MAX-ACCESS       not-accessible
    STATUS           current
    DESCRIPTION
        "Cisco Firepower vnic:IPv4PooledIscsiAddr managed object table"
    ::= { cfprApVnicObjects 25 }

cfprApVnicIPv4PooledIscsiAddrEntry OBJECT-TYPE
    SYNTAX           CfprApVnicIPv4PooledIscsiAddrEntry
    MAX-ACCESS       not-accessible
    STATUS           current
    DESCRIPTION
        "Entry for the cfprApVnicIPv4PooledIscsiAddrTable table."
    INDEX { cfprApVnicIPv4PooledIscsiAddrInstanceId }
    ::= { cfprApVnicIPv4PooledIscsiAddrTable 1 }

CfprApVnicIPv4PooledIscsiAddrEntry ::= SEQUENCE {
    cfprApVnicIPv4PooledIscsiAddrInstanceId                          CfprApManagedObjectId,
    cfprApVnicIPv4PooledIscsiAddrDn                                  CfprApManagedObjectDn,
    cfprApVnicIPv4PooledIscsiAddrRn                                  SnmpAdminString,
    cfprApVnicIPv4PooledIscsiAddrAddr                                InetAddressIPv4,
    cfprApVnicIPv4PooledIscsiAddrDefGw                               InetAddressIPv4,
    cfprApVnicIPv4PooledIscsiAddrIdentPoolName                       SnmpAdminString,
    cfprApVnicIPv4PooledIscsiAddrOperIdentPoolName                   SnmpAdminString,
    cfprApVnicIPv4PooledIscsiAddrPrimDns                             InetAddressIPv4,
    cfprApVnicIPv4PooledIscsiAddrSecDns                              InetAddressIPv4,
    cfprApVnicIPv4PooledIscsiAddrSubnet                              InetAddressIPv4
}

cfprApVnicIPv4PooledIscsiAddrInstanceId OBJECT-TYPE
    SYNTAX       CfprApManagedObjectId
    MAX-ACCESS   not-accessible
    STATUS       current
    DESCRIPTION
        "Instance identifier of the managed object."
    ::= { cfprApVnicIPv4PooledIscsiAddrEntry 1 }

cfprApVnicIPv4PooledIscsiAddrDn OBJECT-TYPE
    SYNTAX       CfprApManagedObjectDn
    MAX-ACCESS   read-only
    STATUS       current
    DESCRIPTION
        "Cisco Firepower vnic:IPv4PooledIscsiAddr:dn managed
        object property"
    ::= { cfprApVnicIPv4PooledIscsiAddrEntry 2 }

cfprApVnicIPv4PooledIscsiAddrRn OBJECT-TYPE
    SYNTAX       SnmpAdminString
    MAX-ACCESS   read-only
    STATUS       current
    DESCRIPTION
        "Cisco Firepower vnic:IPv4PooledIscsiAddr:rn managed
        object property"
    ::= { cfprApVnicIPv4PooledIscsiAddrEntry 3 }

cfprApVnicIPv4PooledIscsiAddrAddr OBJECT-TYPE
    SYNTAX       InetAddressIPv4
    MAX-ACCESS   read-only
    STATUS       current
    DESCRIPTION
        "Cisco Firepower vnic:IPv4PooledIscsiAddr:addr
        managed object property"
    ::= { cfprApVnicIPv4PooledIscsiAddrEntry 4 }

cfprApVnicIPv4PooledIscsiAddrDefGw OBJECT-TYPE
    SYNTAX       InetAddressIPv4
    MAX-ACCESS   read-only
    STATUS       current
    DESCRIPTION
        "Cisco Firepower vnic:IPv4PooledIscsiAddr:defGw
        managed object property"
    ::= { cfprApVnicIPv4PooledIscsiAddrEntry 5 }

cfprApVnicIPv4PooledIscsiAddrIdentPoolName OBJECT-TYPE
    SYNTAX       SnmpAdminString
    MAX-ACCESS   read-only
    STATUS       current
    DESCRIPTION
        "Cisco Firepower vnic:IPv4PooledIscsiAddr:identPoolName
        managed object property"
    ::= { cfprApVnicIPv4PooledIscsiAddrEntry 6 }

cfprApVnicIPv4PooledIscsiAddrOperIdentPoolName OBJECT-TYPE
    SYNTAX       SnmpAdminString
    MAX-ACCESS   read-only
    STATUS       current
    DESCRIPTION
        "Cisco Firepower vnic:IPv4PooledIscsiAddr:operIdentPoolName
        managed object property"
    ::= { cfprApVnicIPv4PooledIscsiAddrEntry 7 }

cfprApVnicIPv4PooledIscsiAddrPrimDns OBJECT-TYPE
    SYNTAX       InetAddressIPv4
    MAX-ACCESS   read-only
    STATUS       current
    DESCRIPTION
        "Cisco Firepower vnic:IPv4PooledIscsiAddr:primDns
        managed object property"
    ::= { cfprApVnicIPv4PooledIscsiAddrEntry 8 }

cfprApVnicIPv4PooledIscsiAddrSecDns OBJECT-TYPE
    SYNTAX       InetAddressIPv4
    MAX-ACCESS   read-only
    STATUS       current
    DESCRIPTION
        "Cisco Firepower vnic:IPv4PooledIscsiAddr:secDns
        managed object property"
    ::= { cfprApVnicIPv4PooledIscsiAddrEntry 9 }

cfprApVnicIPv4PooledIscsiAddrSubnet OBJECT-TYPE
    SYNTAX       InetAddressIPv4
    MAX-ACCESS   read-only
    STATUS       current
    DESCRIPTION
        "Cisco Firepower vnic:IPv4PooledIscsiAddr:subnet
        managed object property"
    ::= { cfprApVnicIPv4PooledIscsiAddrEntry 10 }

cfprApVnicIPv4StaticRouteTable OBJECT-TYPE
    SYNTAX           SEQUENCE OF CfprApVnicIPv4StaticRouteEntry
    MAX-ACCESS       not-accessible
    STATUS           current
    DESCRIPTION
        "Cisco Firepower vnic:IPv4StaticRoute managed object table"
    ::= { cfprApVnicObjects 26 }

cfprApVnicIPv4StaticRouteEntry OBJECT-TYPE
    SYNTAX           CfprApVnicIPv4StaticRouteEntry
    MAX-ACCESS       not-accessible
    STATUS           current
    DESCRIPTION
        "Entry for the cfprApVnicIPv4StaticRouteTable table."
    INDEX { cfprApVnicIPv4StaticRouteInstanceId }
    ::= { cfprApVnicIPv4StaticRouteTable 1 }

CfprApVnicIPv4StaticRouteEntry ::= SEQUENCE {
    cfprApVnicIPv4StaticRouteInstanceId                              CfprApManagedObjectId,
    cfprApVnicIPv4StaticRouteDn                                      CfprApManagedObjectDn,
    cfprApVnicIPv4StaticRouteRn                                      SnmpAdminString,
    cfprApVnicIPv4StaticRouteAddr                                    InetAddressIPv4,
    cfprApVnicIPv4StaticRouteDefGw                                   InetAddressIPv4,
    cfprApVnicIPv4StaticRouteGwAddr                                  InetAddressIPv4,
    cfprApVnicIPv4StaticRouteGwSubnet                                InetAddressIPv4,
    cfprApVnicIPv4StaticRouteSubnet                                  InetAddressIPv4
}

cfprApVnicIPv4StaticRouteInstanceId OBJECT-TYPE
    SYNTAX       CfprApManagedObjectId
    MAX-ACCESS   not-accessible
    STATUS       current
    DESCRIPTION
        "Instance identifier of the managed object."
    ::= { cfprApVnicIPv4StaticRouteEntry 1 }

cfprApVnicIPv4StaticRouteDn OBJECT-TYPE
    SYNTAX       CfprApManagedObjectDn
    MAX-ACCESS   read-only
    STATUS       current
    DESCRIPTION
        "Cisco Firepower vnic:IPv4StaticRoute:dn managed object property"
    ::= { cfprApVnicIPv4StaticRouteEntry 2 }

cfprApVnicIPv4StaticRouteRn OBJECT-TYPE
    SYNTAX       SnmpAdminString
    MAX-ACCESS   read-only
    STATUS       current
    DESCRIPTION
        "Cisco Firepower vnic:IPv4StaticRoute:rn managed object property"
    ::= { cfprApVnicIPv4StaticRouteEntry 3 }

cfprApVnicIPv4StaticRouteAddr OBJECT-TYPE
    SYNTAX       InetAddressIPv4
    MAX-ACCESS   read-only
    STATUS       current
    DESCRIPTION
        "Cisco Firepower vnic:IPv4StaticRoute:addr managed
        object property"
    ::= { cfprApVnicIPv4StaticRouteEntry 4 }

cfprApVnicIPv4StaticRouteDefGw OBJECT-TYPE
    SYNTAX       InetAddressIPv4
    MAX-ACCESS   read-only
    STATUS       current
    DESCRIPTION
        "Cisco Firepower vnic:IPv4StaticRoute:defGw managed
        object property"
    ::= { cfprApVnicIPv4StaticRouteEntry 5 }

cfprApVnicIPv4StaticRouteGwAddr OBJECT-TYPE
    SYNTAX       InetAddressIPv4
    MAX-ACCESS   read-only
    STATUS       current
    DESCRIPTION
        "Cisco Firepower vnic:IPv4StaticRoute:gwAddr managed
        object property"
    ::= { cfprApVnicIPv4StaticRouteEntry 6 }

cfprApVnicIPv4StaticRouteGwSubnet OBJECT-TYPE
    SYNTAX       InetAddressIPv4
    MAX-ACCESS   read-only
    STATUS       current
    DESCRIPTION
        "Cisco Firepower vnic:IPv4StaticRoute:gwSubnet
        managed object property"
    ::= { cfprApVnicIPv4StaticRouteEntry 7 }

cfprApVnicIPv4StaticRouteSubnet OBJECT-TYPE
    SYNTAX       InetAddressIPv4
    MAX-ACCESS   read-only
    STATUS       current
    DESCRIPTION
        "Cisco Firepower vnic:IPv4StaticRoute:subnet managed
        object property"
    ::= { cfprApVnicIPv4StaticRouteEntry 8 }

cfprApVnicIScsiTable OBJECT-TYPE
    SYNTAX           SEQUENCE OF CfprApVnicIScsiEntry
    MAX-ACCESS       not-accessible
    STATUS           current
    DESCRIPTION
        "Cisco Firepower vnic:IScsi managed object table"
    ::= { cfprApVnicObjects 27 }

cfprApVnicIScsiEntry OBJECT-TYPE
    SYNTAX           CfprApVnicIScsiEntry
    MAX-ACCESS       not-accessible
    STATUS           current
    DESCRIPTION
        "Entry for the cfprApVnicIScsiTable table."
    INDEX { cfprApVnicIScsiInstanceId }
    ::= { cfprApVnicIScsiTable 1 }

CfprApVnicIScsiEntry ::= SEQUENCE {
    cfprApVnicIScsiInstanceId                                        CfprApManagedObjectId,
    cfprApVnicIScsiDn                                                CfprApManagedObjectDn,
    cfprApVnicIScsiRn                                                SnmpAdminString,
    cfprApVnicIScsiAdaptorProfileName                                SnmpAdminString,
    cfprApVnicIScsiAddr                                              MacAddress,
    cfprApVnicIScsiAdminHostPort                                     CfprApFabricHostPortId,
    cfprApVnicIScsiAdminVcon                                         SnmpAdminString,
    cfprApVnicIScsiAppRole                                           CfprApVnicAppRole,
    cfprApVnicIScsiBootDev                                           CfprApVnicVnicBootDev,
    cfprApVnicIScsiConfigQualifier                                   CfprApVnicConfigIssues,
    cfprApVnicIScsiConfigState                                       CfprApLsConfigState,
    cfprApVnicIScsiEquipmentDn                                       SnmpAdminString,
    cfprApVnicIScsiEthEpDn                                           SnmpAdminString,
    cfprApVnicIScsiExtIPState                                        CfprApVnicExternalMgmtIPMode,
    cfprApVnicIScsiFltAggr                                           Unsigned64,
    cfprApVnicIScsiIdentPoolName                                     SnmpAdminString,
    cfprApVnicIScsiInitNameSuffix                                    SnmpAdminString,
    cfprApVnicIScsiInitiatorName                                     SnmpAdminString,
    cfprApVnicIScsiInstType                                          CfprApVnicInstantiation,
    cfprApVnicIScsiIqnIdentPoolName                                  SnmpAdminString,
    cfprApVnicIScsiName                                              SnmpAdminString,
    cfprApVnicIScsiNwTemplName                                       SnmpAdminString,
    cfprApVnicIScsiOperHostPort                                      CfprApVnicVnicOperHostPort,
    cfprApVnicIScsiOperIdentPoolName                                 SnmpAdminString,
    cfprApVnicIScsiOperIqnIdentPoolName                              SnmpAdminString,
    cfprApVnicIScsiOperOrder                                         Gauge32,
    cfprApVnicIScsiOperSpeed                                         Gauge32,
    cfprApVnicIScsiOperStatsPolicyName                               SnmpAdminString,
    cfprApVnicIScsiOperVcon                                          SnmpAdminString,
    cfprApVnicIScsiOrder                                             Gauge32,
    cfprApVnicIScsiOwner                                             CfprApVnicConnectionOwner,
    cfprApVnicIScsiPinToGroupName                                    SnmpAdminString,
    cfprApVnicIScsiQosPolicyName                                     SnmpAdminString,
    cfprApVnicIScsiStatsPolicyName                                   SnmpAdminString,
    cfprApVnicIScsiSwitchId                                          CfprApNetworkSwitchId,
    cfprApVnicIScsiType                                              CfprApVnicConnectionType,
    cfprApVnicIScsiVnicDefType                                       CfprApVnicIScsiIfDefType,
    cfprApVnicIScsiVnicName                                          SnmpAdminString
}

cfprApVnicIScsiInstanceId OBJECT-TYPE
    SYNTAX       CfprApManagedObjectId
    MAX-ACCESS   not-accessible
    STATUS       current
    DESCRIPTION
        "Instance identifier of the managed object."
    ::= { cfprApVnicIScsiEntry 1 }

cfprApVnicIScsiDn OBJECT-TYPE
    SYNTAX       CfprApManagedObjectDn
    MAX-ACCESS   read-only
    STATUS       current
    DESCRIPTION
        "Cisco Firepower vnic:IScsi:dn managed object property"
    ::= { cfprApVnicIScsiEntry 2 }

cfprApVnicIScsiRn OBJECT-TYPE
    SYNTAX       SnmpAdminString
    MAX-ACCESS   read-only
    STATUS       current
    DESCRIPTION
        "Cisco Firepower vnic:IScsi:rn managed object property"
    ::= { cfprApVnicIScsiEntry 3 }

cfprApVnicIScsiAdaptorProfileName OBJECT-TYPE
    SYNTAX       SnmpAdminString
    MAX-ACCESS   read-only
    STATUS       current
    DESCRIPTION
        "Cisco Firepower vnic:IScsi:adaptorProfileName
        managed object property"
    ::= { cfprApVnicIScsiEntry 4 }

cfprApVnicIScsiAddr OBJECT-TYPE
    SYNTAX       MacAddress
    MAX-ACCESS   read-only
    STATUS       current
    DESCRIPTION
        "Cisco Firepower vnic:IScsi:addr managed object property"
    ::= { cfprApVnicIScsiEntry 5 }

cfprApVnicIScsiAdminHostPort OBJECT-TYPE
    SYNTAX       CfprApFabricHostPortId
    MAX-ACCESS   read-only
    STATUS       current
    DESCRIPTION
        "Cisco Firepower vnic:IScsi:adminHostPort managed object property"
    ::= { cfprApVnicIScsiEntry 6 }

cfprApVnicIScsiAdminVcon OBJECT-TYPE
    SYNTAX       SnmpAdminString
    MAX-ACCESS   read-only
    STATUS       current
    DESCRIPTION
        "Cisco Firepower vnic:IScsi:adminVcon managed object property"
    ::= { cfprApVnicIScsiEntry 7 }

cfprApVnicIScsiAppRole OBJECT-TYPE
    SYNTAX       CfprApVnicAppRole
    MAX-ACCESS   read-only
    STATUS       current
    DESCRIPTION
        "Cisco Firepower vnic:IScsi:appRole managed object property"
    ::= { cfprApVnicIScsiEntry 8 }

cfprApVnicIScsiBootDev OBJECT-TYPE
    SYNTAX       CfprApVnicVnicBootDev
    MAX-ACCESS   read-only
    STATUS       current
    DESCRIPTION
        "Cisco Firepower vnic:IScsi:bootDev managed object property"
    ::= { cfprApVnicIScsiEntry 10 }

cfprApVnicIScsiConfigQualifier OBJECT-TYPE
    SYNTAX       CfprApVnicConfigIssues
    MAX-ACCESS   read-only
    STATUS       current
    DESCRIPTION
        "Cisco Firepower vnic:IScsi:configQualifier managed
        object property"
    ::= { cfprApVnicIScsiEntry 11 }

cfprApVnicIScsiConfigState OBJECT-TYPE
    SYNTAX       CfprApLsConfigState
    MAX-ACCESS   read-only
    STATUS       current
    DESCRIPTION
        "Cisco Firepower vnic:IScsi:configState managed object property"
    ::= { cfprApVnicIScsiEntry 12 }

cfprApVnicIScsiEquipmentDn OBJECT-TYPE
    SYNTAX       SnmpAdminString
    MAX-ACCESS   read-only
    STATUS       current
    DESCRIPTION
        "Cisco Firepower vnic:IScsi:equipmentDn managed object property"
    ::= { cfprApVnicIScsiEntry 13 }

cfprApVnicIScsiEthEpDn OBJECT-TYPE
    SYNTAX       SnmpAdminString
    MAX-ACCESS   read-only
    STATUS       current
    DESCRIPTION
        "Cisco Firepower vnic:IScsi:ethEpDn managed object property"
    ::= { cfprApVnicIScsiEntry 14 }

cfprApVnicIScsiExtIPState OBJECT-TYPE
    SYNTAX       CfprApVnicExternalMgmtIPMode
    MAX-ACCESS   read-only
    STATUS       current
    DESCRIPTION
        "Cisco Firepower vnic:IScsi:extIPState managed object property"
    ::= { cfprApVnicIScsiEntry 15 }

cfprApVnicIScsiFltAggr OBJECT-TYPE
    SYNTAX       Unsigned64
    MAX-ACCESS   read-only
    STATUS       current
    DESCRIPTION
        "Cisco Firepower vnic:IScsi:fltAggr managed object property"
    ::= { cfprApVnicIScsiEntry 16 }

cfprApVnicIScsiIdentPoolName OBJECT-TYPE
    SYNTAX       SnmpAdminString
    MAX-ACCESS   read-only
    STATUS       current
    DESCRIPTION
        "Cisco Firepower vnic:IScsi:identPoolName managed object property"
    ::= { cfprApVnicIScsiEntry 17 }

cfprApVnicIScsiInitNameSuffix OBJECT-TYPE
    SYNTAX       SnmpAdminString
    MAX-ACCESS   read-only
    STATUS       current
    DESCRIPTION
        "Cisco Firepower vnic:IScsi:initNameSuffix managed
        object property"
    ::= { cfprApVnicIScsiEntry 18 }

cfprApVnicIScsiInitiatorName OBJECT-TYPE
    SYNTAX       SnmpAdminString
    MAX-ACCESS   read-only
    STATUS       current
    DESCRIPTION
        "Cisco Firepower vnic:IScsi:initiatorName managed object property"
    ::= { cfprApVnicIScsiEntry 19 }

cfprApVnicIScsiInstType OBJECT-TYPE
    SYNTAX       CfprApVnicInstantiation
    MAX-ACCESS   read-only
    STATUS       current
    DESCRIPTION
        "Cisco Firepower vnic:IScsi:instType managed object property"
    ::= { cfprApVnicIScsiEntry 20 }

cfprApVnicIScsiIqnIdentPoolName OBJECT-TYPE
    SYNTAX       SnmpAdminString
    MAX-ACCESS   read-only
    STATUS       current
    DESCRIPTION
        "Cisco Firepower vnic:IScsi:iqnIdentPoolName managed
        object property"
    ::= { cfprApVnicIScsiEntry 21 }

cfprApVnicIScsiName OBJECT-TYPE
    SYNTAX       SnmpAdminString
    MAX-ACCESS   read-only
    STATUS       current
    DESCRIPTION
        "Cisco Firepower vnic:IScsi:name managed object property"
    ::= { cfprApVnicIScsiEntry 22 }

cfprApVnicIScsiNwTemplName OBJECT-TYPE
    SYNTAX       SnmpAdminString
    MAX-ACCESS   read-only
    STATUS       current
    DESCRIPTION
        "Cisco Firepower vnic:IScsi:nwTemplName managed object property"
    ::= { cfprApVnicIScsiEntry 23 }

cfprApVnicIScsiOperHostPort OBJECT-TYPE
    SYNTAX       CfprApVnicVnicOperHostPort
    MAX-ACCESS   read-only
    STATUS       current
    DESCRIPTION
        "Cisco Firepower vnic:IScsi:operHostPort managed object property"
    ::= { cfprApVnicIScsiEntry 26 }

cfprApVnicIScsiOperIdentPoolName OBJECT-TYPE
    SYNTAX       SnmpAdminString
    MAX-ACCESS   read-only
    STATUS       current
    DESCRIPTION
        "Cisco Firepower vnic:IScsi:operIdentPoolName managed
        object property"
    ::= { cfprApVnicIScsiEntry 27 }

cfprApVnicIScsiOperIqnIdentPoolName OBJECT-TYPE
    SYNTAX       SnmpAdminString
    MAX-ACCESS   read-only
    STATUS       current
    DESCRIPTION
        "Cisco Firepower vnic:IScsi:operIqnIdentPoolName
        managed object property"
    ::= { cfprApVnicIScsiEntry 28 }

cfprApVnicIScsiOperOrder OBJECT-TYPE
    SYNTAX       Gauge32
    MAX-ACCESS   read-only
    STATUS       current
    DESCRIPTION
        "Cisco Firepower vnic:IScsi:operOrder managed object property"
    ::= { cfprApVnicIScsiEntry 29 }

cfprApVnicIScsiOperSpeed OBJECT-TYPE
    SYNTAX       Gauge32
    MAX-ACCESS   read-only
    STATUS       current
    DESCRIPTION
        "Cisco Firepower vnic:IScsi:operSpeed managed object property"
    ::= { cfprApVnicIScsiEntry 30 }

cfprApVnicIScsiOperStatsPolicyName OBJECT-TYPE
    SYNTAX       SnmpAdminString
    MAX-ACCESS   read-only
    STATUS       current
    DESCRIPTION
        "Cisco Firepower vnic:IScsi:operStatsPolicyName
        managed object property"
    ::= { cfprApVnicIScsiEntry 31 }

cfprApVnicIScsiOperVcon OBJECT-TYPE
    SYNTAX       SnmpAdminString
    MAX-ACCESS   read-only
    STATUS       current
    DESCRIPTION
        "Cisco Firepower vnic:IScsi:operVcon managed object property"
    ::= { cfprApVnicIScsiEntry 32 }

cfprApVnicIScsiOrder OBJECT-TYPE
    SYNTAX       Gauge32
    MAX-ACCESS   read-only
    STATUS       current
    DESCRIPTION
        "Cisco Firepower vnic:IScsi:order managed object property"
    ::= { cfprApVnicIScsiEntry 33 }

cfprApVnicIScsiOwner OBJECT-TYPE
    SYNTAX       CfprApVnicConnectionOwner
    MAX-ACCESS   read-only
    STATUS       current
    DESCRIPTION
        "Cisco Firepower vnic:IScsi:owner managed object property"
    ::= { cfprApVnicIScsiEntry 34 }

cfprApVnicIScsiPinToGroupName OBJECT-TYPE
    SYNTAX       SnmpAdminString
    MAX-ACCESS   read-only
    STATUS       current
    DESCRIPTION
        "Cisco Firepower vnic:IScsi:pinToGroupName managed
        object property"
    ::= { cfprApVnicIScsiEntry 35 }

cfprApVnicIScsiQosPolicyName OBJECT-TYPE
    SYNTAX       SnmpAdminString
    MAX-ACCESS   read-only
    STATUS       current
    DESCRIPTION
        "Cisco Firepower vnic:IScsi:qosPolicyName managed object property"
    ::= { cfprApVnicIScsiEntry 36 }

cfprApVnicIScsiStatsPolicyName OBJECT-TYPE
    SYNTAX       SnmpAdminString
    MAX-ACCESS   read-only
    STATUS       current
    DESCRIPTION
        "Cisco Firepower vnic:IScsi:statsPolicyName managed
        object property"
    ::= { cfprApVnicIScsiEntry 37 }

cfprApVnicIScsiSwitchId OBJECT-TYPE
    SYNTAX       CfprApNetworkSwitchId
    MAX-ACCESS   read-only
    STATUS       current
    DESCRIPTION
        "Cisco Firepower vnic:IScsi:switchId managed object property"
    ::= { cfprApVnicIScsiEntry 38 }

cfprApVnicIScsiType OBJECT-TYPE
    SYNTAX       CfprApVnicConnectionType
    MAX-ACCESS   read-only
    STATUS       current
    DESCRIPTION
        "Cisco Firepower vnic:IScsi:type managed object property"
    ::= { cfprApVnicIScsiEntry 39 }

cfprApVnicIScsiVnicDefType OBJECT-TYPE
    SYNTAX       CfprApVnicIScsiIfDefType
    MAX-ACCESS   read-only
    STATUS       current
    DESCRIPTION
        "Cisco Firepower vnic:IScsi:vnicDefType managed object property"
    ::= { cfprApVnicIScsiEntry 40 }

cfprApVnicIScsiVnicName OBJECT-TYPE
    SYNTAX       SnmpAdminString
    MAX-ACCESS   read-only
    STATUS       current
    DESCRIPTION
        "Cisco Firepower vnic:IScsi:vnicName managed object property"
    ::= { cfprApVnicIScsiEntry 41 }

cfprApVnicIScsiAutoTargetIfTable OBJECT-TYPE
    SYNTAX           SEQUENCE OF CfprApVnicIScsiAutoTargetIfEntry
    MAX-ACCESS       not-accessible
    STATUS           current
    DESCRIPTION
        "Cisco Firepower vnic:IScsiAutoTargetIf managed object table"
    ::= { cfprApVnicObjects 28 }

cfprApVnicIScsiAutoTargetIfEntry OBJECT-TYPE
    SYNTAX           CfprApVnicIScsiAutoTargetIfEntry
    MAX-ACCESS       not-accessible
    STATUS           current
    DESCRIPTION
        "Entry for the cfprApVnicIScsiAutoTargetIfTable table."
    INDEX { cfprApVnicIScsiAutoTargetIfInstanceId }
    ::= { cfprApVnicIScsiAutoTargetIfTable 1 }

CfprApVnicIScsiAutoTargetIfEntry ::= SEQUENCE {
    cfprApVnicIScsiAutoTargetIfInstanceId                            CfprApManagedObjectId,
    cfprApVnicIScsiAutoTargetIfDn                                    CfprApManagedObjectDn,
    cfprApVnicIScsiAutoTargetIfRn                                    SnmpAdminString,
    cfprApVnicIScsiAutoTargetIfDhcpVendorId                          SnmpAdminString
}

cfprApVnicIScsiAutoTargetIfInstanceId OBJECT-TYPE
    SYNTAX       CfprApManagedObjectId
    MAX-ACCESS   not-accessible
    STATUS       current
    DESCRIPTION
        "Instance identifier of the managed object."
    ::= { cfprApVnicIScsiAutoTargetIfEntry 1 }

cfprApVnicIScsiAutoTargetIfDn OBJECT-TYPE
    SYNTAX       CfprApManagedObjectDn
    MAX-ACCESS   read-only
    STATUS       current
    DESCRIPTION
        "Cisco Firepower vnic:IScsiAutoTargetIf:dn managed
        object property"
    ::= { cfprApVnicIScsiAutoTargetIfEntry 2 }

cfprApVnicIScsiAutoTargetIfRn OBJECT-TYPE
    SYNTAX       SnmpAdminString
    MAX-ACCESS   read-only
    STATUS       current
    DESCRIPTION
        "Cisco Firepower vnic:IScsiAutoTargetIf:rn managed
        object property"
    ::= { cfprApVnicIScsiAutoTargetIfEntry 3 }

cfprApVnicIScsiAutoTargetIfDhcpVendorId OBJECT-TYPE
    SYNTAX       SnmpAdminString
    MAX-ACCESS   read-only
    STATUS       current
    DESCRIPTION
        "Cisco Firepower vnic:IScsiAutoTargetIf:dhcpVendorId
        managed object property"
    ::= { cfprApVnicIScsiAutoTargetIfEntry 4 }

cfprApVnicIScsiBootParamsTable OBJECT-TYPE
    SYNTAX           SEQUENCE OF CfprApVnicIScsiBootParamsEntry
    MAX-ACCESS       not-accessible
    STATUS           current
    DESCRIPTION
        "Cisco Firepower vnic:IScsiBootParams managed object table"
    ::= { cfprApVnicObjects 29 }

cfprApVnicIScsiBootParamsEntry OBJECT-TYPE
    SYNTAX           CfprApVnicIScsiBootParamsEntry
    MAX-ACCESS       not-accessible
    STATUS           current
    DESCRIPTION
        "Entry for the cfprApVnicIScsiBootParamsTable table."
    INDEX { cfprApVnicIScsiBootParamsInstanceId }
    ::= { cfprApVnicIScsiBootParamsTable 1 }

CfprApVnicIScsiBootParamsEntry ::= SEQUENCE {
    cfprApVnicIScsiBootParamsInstanceId                              CfprApManagedObjectId,
    cfprApVnicIScsiBootParamsDn                                      CfprApManagedObjectDn,
    cfprApVnicIScsiBootParamsRn                                      SnmpAdminString,
    cfprApVnicIScsiBootParamsDescr                                   SnmpAdminString,
    cfprApVnicIScsiBootParamsIntId                                   SnmpAdminString,
    cfprApVnicIScsiBootParamsName                                    SnmpAdminString,
    cfprApVnicIScsiBootParamsPolicyLevel                             Gauge32,
    cfprApVnicIScsiBootParamsPolicyOwner                             CfprApPolicyPolicyOwner
}

cfprApVnicIScsiBootParamsInstanceId OBJECT-TYPE
    SYNTAX       CfprApManagedObjectId
    MAX-ACCESS   not-accessible
    STATUS       current
    DESCRIPTION
        "Instance identifier of the managed object."
    ::= { cfprApVnicIScsiBootParamsEntry 1 }

cfprApVnicIScsiBootParamsDn OBJECT-TYPE
    SYNTAX       CfprApManagedObjectDn
    MAX-ACCESS   read-only
    STATUS       current
    DESCRIPTION
        "Cisco Firepower vnic:IScsiBootParams:dn managed object property"
    ::= { cfprApVnicIScsiBootParamsEntry 2 }

cfprApVnicIScsiBootParamsRn OBJECT-TYPE
    SYNTAX       SnmpAdminString
    MAX-ACCESS   read-only
    STATUS       current
    DESCRIPTION
        "Cisco Firepower vnic:IScsiBootParams:rn managed object property"
    ::= { cfprApVnicIScsiBootParamsEntry 3 }

cfprApVnicIScsiBootParamsDescr OBJECT-TYPE
    SYNTAX       SnmpAdminString
    MAX-ACCESS   read-only
    STATUS       current
    DESCRIPTION
        "Cisco Firepower vnic:IScsiBootParams:descr managed
        object property"
    ::= { cfprApVnicIScsiBootParamsEntry 4 }

cfprApVnicIScsiBootParamsIntId OBJECT-TYPE
    SYNTAX       SnmpAdminString
    MAX-ACCESS   read-only
    STATUS       current
    DESCRIPTION
        "Cisco Firepower vnic:IScsiBootParams:intId managed
        object property"
    ::= { cfprApVnicIScsiBootParamsEntry 5 }

cfprApVnicIScsiBootParamsName OBJECT-TYPE
    SYNTAX       SnmpAdminString
    MAX-ACCESS   read-only
    STATUS       current
    DESCRIPTION
        "Cisco Firepower vnic:IScsiBootParams:name managed
        object property"
    ::= { cfprApVnicIScsiBootParamsEntry 6 }

cfprApVnicIScsiBootParamsPolicyLevel OBJECT-TYPE
    SYNTAX       Gauge32
    MAX-ACCESS   read-only
    STATUS       current
    DESCRIPTION
        "Cisco Firepower vnic:IScsiBootParams:policyLevel
        managed object property"
    ::= { cfprApVnicIScsiBootParamsEntry 7 }

cfprApVnicIScsiBootParamsPolicyOwner OBJECT-TYPE
    SYNTAX       CfprApPolicyPolicyOwner
    MAX-ACCESS   read-only
    STATUS       current
    DESCRIPTION
        "Cisco Firepower vnic:IScsiBootParams:policyOwner
        managed object property"
    ::= { cfprApVnicIScsiBootParamsEntry 8 }

cfprApVnicIScsiBootVnicTable OBJECT-TYPE
    SYNTAX           SEQUENCE OF CfprApVnicIScsiBootVnicEntry
    MAX-ACCESS       not-accessible
    STATUS           current
    DESCRIPTION
        "Cisco Firepower vnic:IScsiBootVnic managed object table"
    ::= { cfprApVnicObjects 30 }

cfprApVnicIScsiBootVnicEntry OBJECT-TYPE
    SYNTAX           CfprApVnicIScsiBootVnicEntry
    MAX-ACCESS       not-accessible
    STATUS           current
    DESCRIPTION
        "Entry for the cfprApVnicIScsiBootVnicTable table."
    INDEX { cfprApVnicIScsiBootVnicInstanceId }
    ::= { cfprApVnicIScsiBootVnicTable 1 }

CfprApVnicIScsiBootVnicEntry ::= SEQUENCE {
    cfprApVnicIScsiBootVnicInstanceId                                CfprApManagedObjectId,
    cfprApVnicIScsiBootVnicDn                                        CfprApManagedObjectDn,
    cfprApVnicIScsiBootVnicRn                                        SnmpAdminString,
    cfprApVnicIScsiBootVnicDescr                                     SnmpAdminString,
    cfprApVnicIScsiBootVnicInitiatorName                             SnmpAdminString,
    cfprApVnicIScsiBootVnicIntId                                     SnmpAdminString,
    cfprApVnicIScsiBootVnicIqnIdentPoolName                          SnmpAdminString,
    cfprApVnicIScsiBootVnicName                                      SnmpAdminString,
    cfprApVnicIScsiBootVnicOperIqnIdentPoolName                      SnmpAdminString,
    cfprApVnicIScsiBootVnicPolicyLevel                               Gauge32,
    cfprApVnicIScsiBootVnicPolicyOwner                               CfprApPolicyPolicyOwner
}

cfprApVnicIScsiBootVnicInstanceId OBJECT-TYPE
    SYNTAX       CfprApManagedObjectId
    MAX-ACCESS   not-accessible
    STATUS       current
    DESCRIPTION
        "Instance identifier of the managed object."
    ::= { cfprApVnicIScsiBootVnicEntry 1 }

cfprApVnicIScsiBootVnicDn OBJECT-TYPE
    SYNTAX       CfprApManagedObjectDn
    MAX-ACCESS   read-only
    STATUS       current
    DESCRIPTION
        "Cisco Firepower vnic:IScsiBootVnic:dn managed object property"
    ::= { cfprApVnicIScsiBootVnicEntry 2 }

cfprApVnicIScsiBootVnicRn OBJECT-TYPE
    SYNTAX       SnmpAdminString
    MAX-ACCESS   read-only
    STATUS       current
    DESCRIPTION
        "Cisco Firepower vnic:IScsiBootVnic:rn managed object property"
    ::= { cfprApVnicIScsiBootVnicEntry 3 }

cfprApVnicIScsiBootVnicDescr OBJECT-TYPE
    SYNTAX       SnmpAdminString
    MAX-ACCESS   read-only
    STATUS       current
    DESCRIPTION
        "Cisco Firepower vnic:IScsiBootVnic:descr managed object property"
    ::= { cfprApVnicIScsiBootVnicEntry 5 }

cfprApVnicIScsiBootVnicInitiatorName OBJECT-TYPE
    SYNTAX       SnmpAdminString
    MAX-ACCESS   read-only
    STATUS       current
    DESCRIPTION
        "Cisco Firepower vnic:IScsiBootVnic:initiatorName
        managed object property"
    ::= { cfprApVnicIScsiBootVnicEntry 6 }

cfprApVnicIScsiBootVnicIntId OBJECT-TYPE
    SYNTAX       SnmpAdminString
    MAX-ACCESS   read-only
    STATUS       current
    DESCRIPTION
        "Cisco Firepower vnic:IScsiBootVnic:intId managed object property"
    ::= { cfprApVnicIScsiBootVnicEntry 7 }

cfprApVnicIScsiBootVnicIqnIdentPoolName OBJECT-TYPE
    SYNTAX       SnmpAdminString
    MAX-ACCESS   read-only
    STATUS       current
    DESCRIPTION
        "Cisco Firepower vnic:IScsiBootVnic:iqnIdentPoolName
        managed object property"
    ::= { cfprApVnicIScsiBootVnicEntry 8 }

cfprApVnicIScsiBootVnicName OBJECT-TYPE
    SYNTAX       SnmpAdminString
    MAX-ACCESS   read-only
    STATUS       current
    DESCRIPTION
        "Cisco Firepower vnic:IScsiBootVnic:name managed object property"
    ::= { cfprApVnicIScsiBootVnicEntry 9 }

cfprApVnicIScsiBootVnicOperIqnIdentPoolName OBJECT-TYPE
    SYNTAX       SnmpAdminString
    MAX-ACCESS   read-only
    STATUS       current
    DESCRIPTION
        "Cisco Firepower vnic:IScsiBootVnic:operIqnIdentPoolName
        managed object property"
    ::= { cfprApVnicIScsiBootVnicEntry 11 }

cfprApVnicIScsiBootVnicPolicyLevel OBJECT-TYPE
    SYNTAX       Gauge32
    MAX-ACCESS   read-only
    STATUS       current
    DESCRIPTION
        "Cisco Firepower vnic:IScsiBootVnic:policyLevel
        managed object property"
    ::= { cfprApVnicIScsiBootVnicEntry 12 }

cfprApVnicIScsiBootVnicPolicyOwner OBJECT-TYPE
    SYNTAX       CfprApPolicyPolicyOwner
    MAX-ACCESS   read-only
    STATUS       current
    DESCRIPTION
        "Cisco Firepower vnic:IScsiBootVnic:policyOwner
        managed object property"
    ::= { cfprApVnicIScsiBootVnicEntry 13 }

cfprApVnicIScsiLCPTable OBJECT-TYPE
    SYNTAX           SEQUENCE OF CfprApVnicIScsiLCPEntry
    MAX-ACCESS       not-accessible
    STATUS           current
    DESCRIPTION
        "Cisco Firepower vnic:IScsiLCP managed object table"
    ::= { cfprApVnicObjects 31 }

cfprApVnicIScsiLCPEntry OBJECT-TYPE
    SYNTAX           CfprApVnicIScsiLCPEntry
    MAX-ACCESS       not-accessible
    STATUS           current
    DESCRIPTION
        "Entry for the cfprApVnicIScsiLCPTable table."
    INDEX { cfprApVnicIScsiLCPInstanceId }
    ::= { cfprApVnicIScsiLCPTable 1 }

CfprApVnicIScsiLCPEntry ::= SEQUENCE {
    cfprApVnicIScsiLCPInstanceId                                     CfprApManagedObjectId,
    cfprApVnicIScsiLCPDn                                             CfprApManagedObjectDn,
    cfprApVnicIScsiLCPRn                                             SnmpAdminString,
    cfprApVnicIScsiLCPAdaptorProfileName                             SnmpAdminString,
    cfprApVnicIScsiLCPAddr                                           MacAddress,
    cfprApVnicIScsiLCPAdminHostPort                                  CfprApFabricHostPortId,
    cfprApVnicIScsiLCPAdminVcon                                      SnmpAdminString,
    cfprApVnicIScsiLCPAppRole                                        CfprApVnicAppRole,
    cfprApVnicIScsiLCPBootDev                                        CfprApVnicVnicBootDev,
    cfprApVnicIScsiLCPConfigQualifier                                CfprApVnicConfigIssues,
    cfprApVnicIScsiLCPConfigState                                    CfprApLsConfigState,
    cfprApVnicIScsiLCPEquipmentDn                                    SnmpAdminString,
    cfprApVnicIScsiLCPFltAggr                                        Unsigned64,
    cfprApVnicIScsiLCPIdentPoolName                                  SnmpAdminString,
    cfprApVnicIScsiLCPInstType                                       CfprApVnicInstantiation,
    cfprApVnicIScsiLCPName                                           SnmpAdminString,
    cfprApVnicIScsiLCPNwTemplName                                    SnmpAdminString,
    cfprApVnicIScsiLCPOperHostPort                                   CfprApVnicVnicOperHostPort,
    cfprApVnicIScsiLCPOperIdentPoolName                              SnmpAdminString,
    cfprApVnicIScsiLCPOperOrder                                      Gauge32,
    cfprApVnicIScsiLCPOperSpeed                                      Gauge32,
    cfprApVnicIScsiLCPOperStatsPolicyName                            SnmpAdminString,
    cfprApVnicIScsiLCPOperVcon                                       SnmpAdminString,
    cfprApVnicIScsiLCPOrder                                          Gauge32,
    cfprApVnicIScsiLCPOwner                                          CfprApVnicConnectionOwner,
    cfprApVnicIScsiLCPPinToGroupName                                 SnmpAdminString,
    cfprApVnicIScsiLCPQosPolicyName                                  SnmpAdminString,
    cfprApVnicIScsiLCPStatsPolicyName                                SnmpAdminString,
    cfprApVnicIScsiLCPSwitchId                                       CfprApNetworkSwitchId,
    cfprApVnicIScsiLCPType                                           CfprApVnicConnectionType,
    cfprApVnicIScsiLCPVnicName                                       SnmpAdminString
}

cfprApVnicIScsiLCPInstanceId OBJECT-TYPE
    SYNTAX       CfprApManagedObjectId
    MAX-ACCESS   not-accessible
    STATUS       current
    DESCRIPTION
        "Instance identifier of the managed object."
    ::= { cfprApVnicIScsiLCPEntry 1 }

cfprApVnicIScsiLCPDn OBJECT-TYPE
    SYNTAX       CfprApManagedObjectDn
    MAX-ACCESS   read-only
    STATUS       current
    DESCRIPTION
        "Cisco Firepower vnic:IScsiLCP:dn managed object property"
    ::= { cfprApVnicIScsiLCPEntry 2 }

cfprApVnicIScsiLCPRn OBJECT-TYPE
    SYNTAX       SnmpAdminString
    MAX-ACCESS   read-only
    STATUS       current
    DESCRIPTION
        "Cisco Firepower vnic:IScsiLCP:rn managed object property"
    ::= { cfprApVnicIScsiLCPEntry 3 }

cfprApVnicIScsiLCPAdaptorProfileName OBJECT-TYPE
    SYNTAX       SnmpAdminString
    MAX-ACCESS   read-only
    STATUS       current
    DESCRIPTION
        "Cisco Firepower vnic:IScsiLCP:adaptorProfileName
        managed object property"
    ::= { cfprApVnicIScsiLCPEntry 4 }

cfprApVnicIScsiLCPAddr OBJECT-TYPE
    SYNTAX       MacAddress
    MAX-ACCESS   read-only
    STATUS       current
    DESCRIPTION
        "Cisco Firepower vnic:IScsiLCP:addr managed object property"
    ::= { cfprApVnicIScsiLCPEntry 5 }

cfprApVnicIScsiLCPAdminHostPort OBJECT-TYPE
    SYNTAX       CfprApFabricHostPortId
    MAX-ACCESS   read-only
    STATUS       current
    DESCRIPTION
        "Cisco Firepower vnic:IScsiLCP:adminHostPort managed
        object property"
    ::= { cfprApVnicIScsiLCPEntry 6 }

cfprApVnicIScsiLCPAdminVcon OBJECT-TYPE
    SYNTAX       SnmpAdminString
    MAX-ACCESS   read-only
    STATUS       current
    DESCRIPTION
        "Cisco Firepower vnic:IScsiLCP:adminVcon managed object property"
    ::= { cfprApVnicIScsiLCPEntry 7 }

cfprApVnicIScsiLCPAppRole OBJECT-TYPE
    SYNTAX       CfprApVnicAppRole
    MAX-ACCESS   read-only
    STATUS       current
    DESCRIPTION
        "Cisco Firepower vnic:IScsiLCP:appRole managed object property"
    ::= { cfprApVnicIScsiLCPEntry 8 }

cfprApVnicIScsiLCPBootDev OBJECT-TYPE
    SYNTAX       CfprApVnicVnicBootDev
    MAX-ACCESS   read-only
    STATUS       current
    DESCRIPTION
        "Cisco Firepower vnic:IScsiLCP:bootDev managed object property"
    ::= { cfprApVnicIScsiLCPEntry 9 }

cfprApVnicIScsiLCPConfigQualifier OBJECT-TYPE
    SYNTAX       CfprApVnicConfigIssues
    MAX-ACCESS   read-only
    STATUS       current
    DESCRIPTION
        "Cisco Firepower vnic:IScsiLCP:configQualifier
        managed object property"
    ::= { cfprApVnicIScsiLCPEntry 10 }

cfprApVnicIScsiLCPConfigState OBJECT-TYPE
    SYNTAX       CfprApLsConfigState
    MAX-ACCESS   read-only
    STATUS       current
    DESCRIPTION
        "Cisco Firepower vnic:IScsiLCP:configState managed
        object property"
    ::= { cfprApVnicIScsiLCPEntry 11 }

cfprApVnicIScsiLCPEquipmentDn OBJECT-TYPE
    SYNTAX       SnmpAdminString
    MAX-ACCESS   read-only
    STATUS       current
    DESCRIPTION
        "Cisco Firepower vnic:IScsiLCP:equipmentDn managed
        object property"
    ::= { cfprApVnicIScsiLCPEntry 12 }

cfprApVnicIScsiLCPFltAggr OBJECT-TYPE
    SYNTAX       Unsigned64
    MAX-ACCESS   read-only
    STATUS       current
    DESCRIPTION
        "Cisco Firepower vnic:IScsiLCP:fltAggr managed object property"
    ::= { cfprApVnicIScsiLCPEntry 13 }

cfprApVnicIScsiLCPIdentPoolName OBJECT-TYPE
    SYNTAX       SnmpAdminString
    MAX-ACCESS   read-only
    STATUS       current
    DESCRIPTION
        "Cisco Firepower vnic:IScsiLCP:identPoolName managed
        object property"
    ::= { cfprApVnicIScsiLCPEntry 14 }

cfprApVnicIScsiLCPInstType OBJECT-TYPE
    SYNTAX       CfprApVnicInstantiation
    MAX-ACCESS   read-only
    STATUS       current
    DESCRIPTION
        "Cisco Firepower vnic:IScsiLCP:instType managed object property"
    ::= { cfprApVnicIScsiLCPEntry 15 }

cfprApVnicIScsiLCPName OBJECT-TYPE
    SYNTAX       SnmpAdminString
    MAX-ACCESS   read-only
    STATUS       current
    DESCRIPTION
        "Cisco Firepower vnic:IScsiLCP:name managed object property"
    ::= { cfprApVnicIScsiLCPEntry 16 }

cfprApVnicIScsiLCPNwTemplName OBJECT-TYPE
    SYNTAX       SnmpAdminString
    MAX-ACCESS   read-only
    STATUS       current
    DESCRIPTION
        "Cisco Firepower vnic:IScsiLCP:nwTemplName managed
        object property"
    ::= { cfprApVnicIScsiLCPEntry 17 }

cfprApVnicIScsiLCPOperHostPort OBJECT-TYPE
    SYNTAX       CfprApVnicVnicOperHostPort
    MAX-ACCESS   read-only
    STATUS       current
    DESCRIPTION
        "Cisco Firepower vnic:IScsiLCP:operHostPort managed
        object property"
    ::= { cfprApVnicIScsiLCPEntry 19 }

cfprApVnicIScsiLCPOperIdentPoolName OBJECT-TYPE
    SYNTAX       SnmpAdminString
    MAX-ACCESS   read-only
    STATUS       current
    DESCRIPTION
        "Cisco Firepower vnic:IScsiLCP:operIdentPoolName
        managed object property"
    ::= { cfprApVnicIScsiLCPEntry 20 }

cfprApVnicIScsiLCPOperOrder OBJECT-TYPE
    SYNTAX       Gauge32
    MAX-ACCESS   read-only
    STATUS       current
    DESCRIPTION
        "Cisco Firepower vnic:IScsiLCP:operOrder managed object property"
    ::= { cfprApVnicIScsiLCPEntry 21 }

cfprApVnicIScsiLCPOperSpeed OBJECT-TYPE
    SYNTAX       Gauge32
    MAX-ACCESS   read-only
    STATUS       current
    DESCRIPTION
        "Cisco Firepower vnic:IScsiLCP:operSpeed managed object property"
    ::= { cfprApVnicIScsiLCPEntry 22 }

cfprApVnicIScsiLCPOperStatsPolicyName OBJECT-TYPE
    SYNTAX       SnmpAdminString
    MAX-ACCESS   read-only
    STATUS       current
    DESCRIPTION
        "Cisco Firepower vnic:IScsiLCP:operStatsPolicyName
        managed object property"
    ::= { cfprApVnicIScsiLCPEntry 23 }

cfprApVnicIScsiLCPOperVcon OBJECT-TYPE
    SYNTAX       SnmpAdminString
    MAX-ACCESS   read-only
    STATUS       current
    DESCRIPTION
        "Cisco Firepower vnic:IScsiLCP:operVcon managed object property"
    ::= { cfprApVnicIScsiLCPEntry 24 }

cfprApVnicIScsiLCPOrder OBJECT-TYPE
    SYNTAX       Gauge32
    MAX-ACCESS   read-only
    STATUS       current
    DESCRIPTION
        "Cisco Firepower vnic:IScsiLCP:order managed object property"
    ::= { cfprApVnicIScsiLCPEntry 25 }

cfprApVnicIScsiLCPOwner OBJECT-TYPE
    SYNTAX       CfprApVnicConnectionOwner
    MAX-ACCESS   read-only
    STATUS       current
    DESCRIPTION
        "Cisco Firepower vnic:IScsiLCP:owner managed object property"
    ::= { cfprApVnicIScsiLCPEntry 26 }

cfprApVnicIScsiLCPPinToGroupName OBJECT-TYPE
    SYNTAX       SnmpAdminString
    MAX-ACCESS   read-only
    STATUS       current
    DESCRIPTION
        "Cisco Firepower vnic:IScsiLCP:pinToGroupName managed
        object property"
    ::= { cfprApVnicIScsiLCPEntry 27 }

cfprApVnicIScsiLCPQosPolicyName OBJECT-TYPE
    SYNTAX       SnmpAdminString
    MAX-ACCESS   read-only
    STATUS       current
    DESCRIPTION
        "Cisco Firepower vnic:IScsiLCP:qosPolicyName managed
        object property"
    ::= { cfprApVnicIScsiLCPEntry 28 }

cfprApVnicIScsiLCPStatsPolicyName OBJECT-TYPE
    SYNTAX       SnmpAdminString
    MAX-ACCESS   read-only
    STATUS       current
    DESCRIPTION
        "Cisco Firepower vnic:IScsiLCP:statsPolicyName
        managed object property"
    ::= { cfprApVnicIScsiLCPEntry 29 }

cfprApVnicIScsiLCPSwitchId OBJECT-TYPE
    SYNTAX       CfprApNetworkSwitchId
    MAX-ACCESS   read-only
    STATUS       current
    DESCRIPTION
        "Cisco Firepower vnic:IScsiLCP:switchId managed object property"
    ::= { cfprApVnicIScsiLCPEntry 30 }

cfprApVnicIScsiLCPType OBJECT-TYPE
    SYNTAX       CfprApVnicConnectionType
    MAX-ACCESS   read-only
    STATUS       current
    DESCRIPTION
        "Cisco Firepower vnic:IScsiLCP:type managed object property"
    ::= { cfprApVnicIScsiLCPEntry 31 }

cfprApVnicIScsiLCPVnicName OBJECT-TYPE
    SYNTAX       SnmpAdminString
    MAX-ACCESS   read-only
    STATUS       current
    DESCRIPTION
        "Cisco Firepower vnic:IScsiLCP:vnicName managed object property"
    ::= { cfprApVnicIScsiLCPEntry 32 }

cfprApVnicIScsiNodeTable OBJECT-TYPE
    SYNTAX           SEQUENCE OF CfprApVnicIScsiNodeEntry
    MAX-ACCESS       not-accessible
    STATUS           current
    DESCRIPTION
        "Cisco Firepower vnic:IScsiNode managed object table"
    ::= { cfprApVnicObjects 32 }

cfprApVnicIScsiNodeEntry OBJECT-TYPE
    SYNTAX           CfprApVnicIScsiNodeEntry
    MAX-ACCESS       not-accessible
    STATUS           current
    DESCRIPTION
        "Entry for the cfprApVnicIScsiNodeTable table."
    INDEX { cfprApVnicIScsiNodeInstanceId }
    ::= { cfprApVnicIScsiNodeTable 1 }

CfprApVnicIScsiNodeEntry ::= SEQUENCE {
    cfprApVnicIScsiNodeInstanceId                                    CfprApManagedObjectId,
    cfprApVnicIScsiNodeDn                                            CfprApManagedObjectDn,
    cfprApVnicIScsiNodeRn                                            SnmpAdminString,
    cfprApVnicIScsiNodeFltAggr                                       Unsigned64,
    cfprApVnicIScsiNodeInitNameSuffix                                SnmpAdminString,
    cfprApVnicIScsiNodeInitiatorName                                 SnmpAdminString,
    cfprApVnicIScsiNodeIqnIdentPoolName                              SnmpAdminString,
    cfprApVnicIScsiNodeOperIqnIdentPoolName                          SnmpAdminString,
    cfprApVnicIScsiNodeOwner                                         CfprApVnicIScsiNodeOwner
}

cfprApVnicIScsiNodeInstanceId OBJECT-TYPE
    SYNTAX       CfprApManagedObjectId
    MAX-ACCESS   not-accessible
    STATUS       current
    DESCRIPTION
        "Instance identifier of the managed object."
    ::= { cfprApVnicIScsiNodeEntry 1 }

cfprApVnicIScsiNodeDn OBJECT-TYPE
    SYNTAX       CfprApManagedObjectDn
    MAX-ACCESS   read-only
    STATUS       current
    DESCRIPTION
        "Cisco Firepower vnic:IScsiNode:dn managed object property"
    ::= { cfprApVnicIScsiNodeEntry 2 }

cfprApVnicIScsiNodeRn OBJECT-TYPE
    SYNTAX       SnmpAdminString
    MAX-ACCESS   read-only
    STATUS       current
    DESCRIPTION
        "Cisco Firepower vnic:IScsiNode:rn managed object property"
    ::= { cfprApVnicIScsiNodeEntry 3 }

cfprApVnicIScsiNodeFltAggr OBJECT-TYPE
    SYNTAX       Unsigned64
    MAX-ACCESS   read-only
    STATUS       current
    DESCRIPTION
        "Cisco Firepower vnic:IScsiNode:fltAggr managed object property"
    ::= { cfprApVnicIScsiNodeEntry 4 }

cfprApVnicIScsiNodeInitNameSuffix OBJECT-TYPE
    SYNTAX       SnmpAdminString
    MAX-ACCESS   read-only
    STATUS       current
    DESCRIPTION
        "Cisco Firepower vnic:IScsiNode:initNameSuffix
        managed object property"
    ::= { cfprApVnicIScsiNodeEntry 5 }

cfprApVnicIScsiNodeInitiatorName OBJECT-TYPE
    SYNTAX       SnmpAdminString
    MAX-ACCESS   read-only
    STATUS       current
    DESCRIPTION
        "Cisco Firepower vnic:IScsiNode:initiatorName managed
        object property"
    ::= { cfprApVnicIScsiNodeEntry 6 }

cfprApVnicIScsiNodeIqnIdentPoolName OBJECT-TYPE
    SYNTAX       SnmpAdminString
    MAX-ACCESS   read-only
    STATUS       current
    DESCRIPTION
        "Cisco Firepower vnic:IScsiNode:iqnIdentPoolName
        managed object property"
    ::= { cfprApVnicIScsiNodeEntry 7 }

cfprApVnicIScsiNodeOperIqnIdentPoolName OBJECT-TYPE
    SYNTAX       SnmpAdminString
    MAX-ACCESS   read-only
    STATUS       current
    DESCRIPTION
        "Cisco Firepower vnic:IScsiNode:operIqnIdentPoolName
        managed object property"
    ::= { cfprApVnicIScsiNodeEntry 8 }

cfprApVnicIScsiNodeOwner OBJECT-TYPE
    SYNTAX       CfprApVnicIScsiNodeOwner
    MAX-ACCESS   read-only
    STATUS       current
    DESCRIPTION
        "Cisco Firepower vnic:IScsiNode:owner managed object property"
    ::= { cfprApVnicIScsiNodeEntry 9 }

cfprApVnicIScsiStaticTargetIfTable OBJECT-TYPE
    SYNTAX           SEQUENCE OF CfprApVnicIScsiStaticTargetIfEntry
    MAX-ACCESS       not-accessible
    STATUS           current
    DESCRIPTION
        "Cisco Firepower vnic:IScsiStaticTargetIf managed object table"
    ::= { cfprApVnicObjects 33 }

cfprApVnicIScsiStaticTargetIfEntry OBJECT-TYPE
    SYNTAX           CfprApVnicIScsiStaticTargetIfEntry
    MAX-ACCESS       not-accessible
    STATUS           current
    DESCRIPTION
        "Entry for the cfprApVnicIScsiStaticTargetIfTable table."
    INDEX { cfprApVnicIScsiStaticTargetIfInstanceId }
    ::= { cfprApVnicIScsiStaticTargetIfTable 1 }

CfprApVnicIScsiStaticTargetIfEntry ::= SEQUENCE {
    cfprApVnicIScsiStaticTargetIfInstanceId                          CfprApManagedObjectId,
    cfprApVnicIScsiStaticTargetIfDn                                  CfprApManagedObjectDn,
    cfprApVnicIScsiStaticTargetIfRn                                  SnmpAdminString,
    cfprApVnicIScsiStaticTargetIfIpAddress                           InetAddressIPv4,
    cfprApVnicIScsiStaticTargetIfName                                SnmpAdminString,
    cfprApVnicIScsiStaticTargetIfPort                                Gauge32,
    cfprApVnicIScsiStaticTargetIfPriority                            Gauge32
}

cfprApVnicIScsiStaticTargetIfInstanceId OBJECT-TYPE
    SYNTAX       CfprApManagedObjectId
    MAX-ACCESS   not-accessible
    STATUS       current
    DESCRIPTION
        "Instance identifier of the managed object."
    ::= { cfprApVnicIScsiStaticTargetIfEntry 1 }

cfprApVnicIScsiStaticTargetIfDn OBJECT-TYPE
    SYNTAX       CfprApManagedObjectDn
    MAX-ACCESS   read-only
    STATUS       current
    DESCRIPTION
        "Cisco Firepower vnic:IScsiStaticTargetIf:dn managed
        object property"
    ::= { cfprApVnicIScsiStaticTargetIfEntry 2 }

cfprApVnicIScsiStaticTargetIfRn OBJECT-TYPE
    SYNTAX       SnmpAdminString
    MAX-ACCESS   read-only
    STATUS       current
    DESCRIPTION
        "Cisco Firepower vnic:IScsiStaticTargetIf:rn managed
        object property"
    ::= { cfprApVnicIScsiStaticTargetIfEntry 3 }

cfprApVnicIScsiStaticTargetIfIpAddress OBJECT-TYPE
    SYNTAX       InetAddressIPv4
    MAX-ACCESS   read-only
    STATUS       current
    DESCRIPTION
        "Cisco Firepower vnic:IScsiStaticTargetIf:ipAddress
        managed object property"
    ::= { cfprApVnicIScsiStaticTargetIfEntry 5 }

cfprApVnicIScsiStaticTargetIfName OBJECT-TYPE
    SYNTAX       SnmpAdminString
    MAX-ACCESS   read-only
    STATUS       current
    DESCRIPTION
        "Cisco Firepower vnic:IScsiStaticTargetIf:name
        managed object property"
    ::= { cfprApVnicIScsiStaticTargetIfEntry 6 }

cfprApVnicIScsiStaticTargetIfPort OBJECT-TYPE
    SYNTAX       Gauge32
    MAX-ACCESS   read-only
    STATUS       current
    DESCRIPTION
        "Cisco Firepower vnic:IScsiStaticTargetIf:port
        managed object property"
    ::= { cfprApVnicIScsiStaticTargetIfEntry 8 }

cfprApVnicIScsiStaticTargetIfPriority OBJECT-TYPE
    SYNTAX       Gauge32
    MAX-ACCESS   read-only
    STATUS       current
    DESCRIPTION
        "Cisco Firepower vnic:IScsiStaticTargetIf:priority
        managed object property"
    ::= { cfprApVnicIScsiStaticTargetIfEntry 9 }

cfprApVnicInternalProfileTable OBJECT-TYPE
    SYNTAX           SEQUENCE OF CfprApVnicInternalProfileEntry
    MAX-ACCESS       not-accessible
    STATUS           current
    DESCRIPTION
        "Cisco Firepower vnic:InternalProfile managed object table"
    ::= { cfprApVnicObjects 34 }

cfprApVnicInternalProfileEntry OBJECT-TYPE
    SYNTAX           CfprApVnicInternalProfileEntry
    MAX-ACCESS       not-accessible
    STATUS           current
    DESCRIPTION
        "Entry for the cfprApVnicInternalProfileTable table."
    INDEX { cfprApVnicInternalProfileInstanceId }
    ::= { cfprApVnicInternalProfileTable 1 }

CfprApVnicInternalProfileEntry ::= SEQUENCE {
    cfprApVnicInternalProfileInstanceId                              CfprApManagedObjectId,
    cfprApVnicInternalProfileDn                                      CfprApManagedObjectDn,
    cfprApVnicInternalProfileRn                                      SnmpAdminString,
    cfprApVnicInternalProfileDescr                                   SnmpAdminString,
    cfprApVnicInternalProfileIntId                                   SnmpAdminString,
    cfprApVnicInternalProfileMaxPorts                                Gauge32,
    cfprApVnicInternalProfileName                                    SnmpAdminString,
    cfprApVnicInternalProfilePolicyLevel                             Gauge32,
    cfprApVnicInternalProfilePolicyOwner                             CfprApPolicyPolicyOwner
}

cfprApVnicInternalProfileInstanceId OBJECT-TYPE
    SYNTAX       CfprApManagedObjectId
    MAX-ACCESS   not-accessible
    STATUS       current
    DESCRIPTION
        "Instance identifier of the managed object."
    ::= { cfprApVnicInternalProfileEntry 1 }

cfprApVnicInternalProfileDn OBJECT-TYPE
    SYNTAX       CfprApManagedObjectDn
    MAX-ACCESS   read-only
    STATUS       current
    DESCRIPTION
        "Cisco Firepower vnic:InternalProfile:dn managed object property"
    ::= { cfprApVnicInternalProfileEntry 2 }

cfprApVnicInternalProfileRn OBJECT-TYPE
    SYNTAX       SnmpAdminString
    MAX-ACCESS   read-only
    STATUS       current
    DESCRIPTION
        "Cisco Firepower vnic:InternalProfile:rn managed object property"
    ::= { cfprApVnicInternalProfileEntry 3 }

cfprApVnicInternalProfileDescr OBJECT-TYPE
    SYNTAX       SnmpAdminString
    MAX-ACCESS   read-only
    STATUS       current
    DESCRIPTION
        "Cisco Firepower vnic:InternalProfile:descr managed
        object property"
    ::= { cfprApVnicInternalProfileEntry 4 }

cfprApVnicInternalProfileIntId OBJECT-TYPE
    SYNTAX       SnmpAdminString
    MAX-ACCESS   read-only
    STATUS       current
    DESCRIPTION
        "Cisco Firepower vnic:InternalProfile:intId managed
        object property"
    ::= { cfprApVnicInternalProfileEntry 5 }

cfprApVnicInternalProfileMaxPorts OBJECT-TYPE
    SYNTAX       Gauge32
    MAX-ACCESS   read-only
    STATUS       current
    DESCRIPTION
        "Cisco Firepower vnic:InternalProfile:maxPorts
        managed object property"
    ::= { cfprApVnicInternalProfileEntry 6 }

cfprApVnicInternalProfileName OBJECT-TYPE
    SYNTAX       SnmpAdminString
    MAX-ACCESS   read-only
    STATUS       current
    DESCRIPTION
        "Cisco Firepower vnic:InternalProfile:name managed
        object property"
    ::= { cfprApVnicInternalProfileEntry 7 }

cfprApVnicInternalProfilePolicyLevel OBJECT-TYPE
    SYNTAX       Gauge32
    MAX-ACCESS   read-only
    STATUS       current
    DESCRIPTION
        "Cisco Firepower vnic:InternalProfile:policyLevel
        managed object property"
    ::= { cfprApVnicInternalProfileEntry 8 }

cfprApVnicInternalProfilePolicyOwner OBJECT-TYPE
    SYNTAX       CfprApPolicyPolicyOwner
    MAX-ACCESS   read-only
    STATUS       current
    DESCRIPTION
        "Cisco Firepower vnic:InternalProfile:policyOwner
        managed object property"
    ::= { cfprApVnicInternalProfileEntry 9 }

cfprApVnicIpV4HistoryTable OBJECT-TYPE
    SYNTAX           SEQUENCE OF CfprApVnicIpV4HistoryEntry
    MAX-ACCESS       not-accessible
    STATUS           current
    DESCRIPTION
        "Cisco Firepower vnic:IpV4History managed object table"
    ::= { cfprApVnicObjects 35 }

cfprApVnicIpV4HistoryEntry OBJECT-TYPE
    SYNTAX           CfprApVnicIpV4HistoryEntry
    MAX-ACCESS       not-accessible
    STATUS           current
    DESCRIPTION
        "Entry for the cfprApVnicIpV4HistoryTable table."
    INDEX { cfprApVnicIpV4HistoryInstanceId }
    ::= { cfprApVnicIpV4HistoryTable 1 }

CfprApVnicIpV4HistoryEntry ::= SEQUENCE {
    cfprApVnicIpV4HistoryInstanceId                                  CfprApManagedObjectId,
    cfprApVnicIpV4HistoryDn                                          CfprApManagedObjectDn,
    cfprApVnicIpV4HistoryRn                                          SnmpAdminString,
    cfprApVnicIpV4HistoryOldIpV4Addr                                 InetAddressIPv4
}

cfprApVnicIpV4HistoryInstanceId OBJECT-TYPE
    SYNTAX       CfprApManagedObjectId
    MAX-ACCESS   not-accessible
    STATUS       current
    DESCRIPTION
        "Instance identifier of the managed object."
    ::= { cfprApVnicIpV4HistoryEntry 1 }

cfprApVnicIpV4HistoryDn OBJECT-TYPE
    SYNTAX       CfprApManagedObjectDn
    MAX-ACCESS   read-only
    STATUS       current
    DESCRIPTION
        "Cisco Firepower vnic:IpV4History:dn managed object property"
    ::= { cfprApVnicIpV4HistoryEntry 2 }

cfprApVnicIpV4HistoryRn OBJECT-TYPE
    SYNTAX       SnmpAdminString
    MAX-ACCESS   read-only
    STATUS       current
    DESCRIPTION
        "Cisco Firepower vnic:IpV4History:rn managed object property"
    ::= { cfprApVnicIpV4HistoryEntry 3 }

cfprApVnicIpV4HistoryOldIpV4Addr OBJECT-TYPE
    SYNTAX       InetAddressIPv4
    MAX-ACCESS   read-only
    STATUS       current
    DESCRIPTION
        "Cisco Firepower vnic:IpV4History:oldIpV4Addr managed
        object property"
    ::= { cfprApVnicIpV4HistoryEntry 4 }

cfprApVnicIpV4MgmtPooledAddrTable OBJECT-TYPE
    SYNTAX           SEQUENCE OF CfprApVnicIpV4MgmtPooledAddrEntry
    MAX-ACCESS       not-accessible
    STATUS           current
    DESCRIPTION
        "Cisco Firepower vnic:IpV4MgmtPooledAddr managed object table"
    ::= { cfprApVnicObjects 36 }

cfprApVnicIpV4MgmtPooledAddrEntry OBJECT-TYPE
    SYNTAX           CfprApVnicIpV4MgmtPooledAddrEntry
    MAX-ACCESS       not-accessible
    STATUS           current
    DESCRIPTION
        "Entry for the cfprApVnicIpV4MgmtPooledAddrTable table."
    INDEX { cfprApVnicIpV4MgmtPooledAddrInstanceId }
    ::= { cfprApVnicIpV4MgmtPooledAddrTable 1 }

CfprApVnicIpV4MgmtPooledAddrEntry ::= SEQUENCE {
    cfprApVnicIpV4MgmtPooledAddrInstanceId                           CfprApManagedObjectId,
    cfprApVnicIpV4MgmtPooledAddrDn                                   CfprApManagedObjectDn,
    cfprApVnicIpV4MgmtPooledAddrRn                                   SnmpAdminString,
    cfprApVnicIpV4MgmtPooledAddrAddr                                 InetAddressIPv4,
    cfprApVnicIpV4MgmtPooledAddrDefGw                                InetAddressIPv4,
    cfprApVnicIpV4MgmtPooledAddrName                                 SnmpAdminString,
    cfprApVnicIpV4MgmtPooledAddrOperName                             SnmpAdminString,
    cfprApVnicIpV4MgmtPooledAddrPrimDns                              InetAddressIPv4,
    cfprApVnicIpV4MgmtPooledAddrSecDns                               InetAddressIPv4,
    cfprApVnicIpV4MgmtPooledAddrSubnet                               InetAddressIPv4
}

cfprApVnicIpV4MgmtPooledAddrInstanceId OBJECT-TYPE
    SYNTAX       CfprApManagedObjectId
    MAX-ACCESS   not-accessible
    STATUS       current
    DESCRIPTION
        "Instance identifier of the managed object."
    ::= { cfprApVnicIpV4MgmtPooledAddrEntry 1 }

cfprApVnicIpV4MgmtPooledAddrDn OBJECT-TYPE
    SYNTAX       CfprApManagedObjectDn
    MAX-ACCESS   read-only
    STATUS       current
    DESCRIPTION
        "Cisco Firepower vnic:IpV4MgmtPooledAddr:dn managed
        object property"
    ::= { cfprApVnicIpV4MgmtPooledAddrEntry 2 }

cfprApVnicIpV4MgmtPooledAddrRn OBJECT-TYPE
    SYNTAX       SnmpAdminString
    MAX-ACCESS   read-only
    STATUS       current
    DESCRIPTION
        "Cisco Firepower vnic:IpV4MgmtPooledAddr:rn managed
        object property"
    ::= { cfprApVnicIpV4MgmtPooledAddrEntry 3 }

cfprApVnicIpV4MgmtPooledAddrAddr OBJECT-TYPE
    SYNTAX       InetAddressIPv4
    MAX-ACCESS   read-only
    STATUS       current
    DESCRIPTION
        "Cisco Firepower vnic:IpV4MgmtPooledAddr:addr managed
        object property"
    ::= { cfprApVnicIpV4MgmtPooledAddrEntry 4 }

cfprApVnicIpV4MgmtPooledAddrDefGw OBJECT-TYPE
    SYNTAX       InetAddressIPv4
    MAX-ACCESS   read-only
    STATUS       current
    DESCRIPTION
        "Cisco Firepower vnic:IpV4MgmtPooledAddr:defGw
        managed object property"
    ::= { cfprApVnicIpV4MgmtPooledAddrEntry 5 }

cfprApVnicIpV4MgmtPooledAddrName OBJECT-TYPE
    SYNTAX       SnmpAdminString
    MAX-ACCESS   read-only
    STATUS       current
    DESCRIPTION
        "Cisco Firepower vnic:IpV4MgmtPooledAddr:name managed
        object property"
    ::= { cfprApVnicIpV4MgmtPooledAddrEntry 6 }

cfprApVnicIpV4MgmtPooledAddrOperName OBJECT-TYPE
    SYNTAX       SnmpAdminString
    MAX-ACCESS   read-only
    STATUS       current
    DESCRIPTION
        "Cisco Firepower vnic:IpV4MgmtPooledAddr:operName
        managed object property"
    ::= { cfprApVnicIpV4MgmtPooledAddrEntry 7 }

cfprApVnicIpV4MgmtPooledAddrPrimDns OBJECT-TYPE
    SYNTAX       InetAddressIPv4
    MAX-ACCESS   read-only
    STATUS       current
    DESCRIPTION
        "Cisco Firepower vnic:IpV4MgmtPooledAddr:primDns
        managed object property"
    ::= { cfprApVnicIpV4MgmtPooledAddrEntry 8 }

cfprApVnicIpV4MgmtPooledAddrSecDns OBJECT-TYPE
    SYNTAX       InetAddressIPv4
    MAX-ACCESS   read-only
    STATUS       current
    DESCRIPTION
        "Cisco Firepower vnic:IpV4MgmtPooledAddr:secDns
        managed object property"
    ::= { cfprApVnicIpV4MgmtPooledAddrEntry 9 }

cfprApVnicIpV4MgmtPooledAddrSubnet OBJECT-TYPE
    SYNTAX       InetAddressIPv4
    MAX-ACCESS   read-only
    STATUS       current
    DESCRIPTION
        "Cisco Firepower vnic:IpV4MgmtPooledAddr:subnet
        managed object property"
    ::= { cfprApVnicIpV4MgmtPooledAddrEntry 10 }

cfprApVnicIpV4PooledAddrTable OBJECT-TYPE
    SYNTAX           SEQUENCE OF CfprApVnicIpV4PooledAddrEntry
    MAX-ACCESS       not-accessible
    STATUS           current
    DESCRIPTION
        "Cisco Firepower vnic:IpV4PooledAddr managed object table"
    ::= { cfprApVnicObjects 37 }

cfprApVnicIpV4PooledAddrEntry OBJECT-TYPE
    SYNTAX           CfprApVnicIpV4PooledAddrEntry
    MAX-ACCESS       not-accessible
    STATUS           current
    DESCRIPTION
        "Entry for the cfprApVnicIpV4PooledAddrTable table."
    INDEX { cfprApVnicIpV4PooledAddrInstanceId }
    ::= { cfprApVnicIpV4PooledAddrTable 1 }

CfprApVnicIpV4PooledAddrEntry ::= SEQUENCE {
    cfprApVnicIpV4PooledAddrInstanceId                               CfprApManagedObjectId,
    cfprApVnicIpV4PooledAddrDn                                       CfprApManagedObjectDn,
    cfprApVnicIpV4PooledAddrRn                                       SnmpAdminString,
    cfprApVnicIpV4PooledAddrAddr                                     InetAddressIPv4,
    cfprApVnicIpV4PooledAddrDefGw                                    InetAddressIPv4,
    cfprApVnicIpV4PooledAddrName                                     SnmpAdminString,
    cfprApVnicIpV4PooledAddrOperName                                 SnmpAdminString,
    cfprApVnicIpV4PooledAddrPrimDns                                  InetAddressIPv4,
    cfprApVnicIpV4PooledAddrSecDns                                   InetAddressIPv4,
    cfprApVnicIpV4PooledAddrSubnet                                   InetAddressIPv4
}

cfprApVnicIpV4PooledAddrInstanceId OBJECT-TYPE
    SYNTAX       CfprApManagedObjectId
    MAX-ACCESS   not-accessible
    STATUS       current
    DESCRIPTION
        "Instance identifier of the managed object."
    ::= { cfprApVnicIpV4PooledAddrEntry 1 }

cfprApVnicIpV4PooledAddrDn OBJECT-TYPE
    SYNTAX       CfprApManagedObjectDn
    MAX-ACCESS   read-only
    STATUS       current
    DESCRIPTION
        "Cisco Firepower vnic:IpV4PooledAddr:dn managed object property"
    ::= { cfprApVnicIpV4PooledAddrEntry 2 }

cfprApVnicIpV4PooledAddrRn OBJECT-TYPE
    SYNTAX       SnmpAdminString
    MAX-ACCESS   read-only
    STATUS       current
    DESCRIPTION
        "Cisco Firepower vnic:IpV4PooledAddr:rn managed object property"
    ::= { cfprApVnicIpV4PooledAddrEntry 3 }

cfprApVnicIpV4PooledAddrAddr OBJECT-TYPE
    SYNTAX       InetAddressIPv4
    MAX-ACCESS   read-only
    STATUS       current
    DESCRIPTION
        "Cisco Firepower vnic:IpV4PooledAddr:addr managed object property"
    ::= { cfprApVnicIpV4PooledAddrEntry 4 }

cfprApVnicIpV4PooledAddrDefGw OBJECT-TYPE
    SYNTAX       InetAddressIPv4
    MAX-ACCESS   read-only
    STATUS       current
    DESCRIPTION
        "Cisco Firepower vnic:IpV4PooledAddr:defGw managed
        object property"
    ::= { cfprApVnicIpV4PooledAddrEntry 5 }

cfprApVnicIpV4PooledAddrName OBJECT-TYPE
    SYNTAX       SnmpAdminString
    MAX-ACCESS   read-only
    STATUS       current
    DESCRIPTION
        "Cisco Firepower vnic:IpV4PooledAddr:name managed object property"
    ::= { cfprApVnicIpV4PooledAddrEntry 6 }

cfprApVnicIpV4PooledAddrOperName OBJECT-TYPE
    SYNTAX       SnmpAdminString
    MAX-ACCESS   read-only
    STATUS       current
    DESCRIPTION
        "Cisco Firepower vnic:IpV4PooledAddr:operName managed
        object property"
    ::= { cfprApVnicIpV4PooledAddrEntry 7 }

cfprApVnicIpV4PooledAddrPrimDns OBJECT-TYPE
    SYNTAX       InetAddressIPv4
    MAX-ACCESS   read-only
    STATUS       current
    DESCRIPTION
        "Cisco Firepower vnic:IpV4PooledAddr:primDns managed
        object property"
    ::= { cfprApVnicIpV4PooledAddrEntry 8 }

cfprApVnicIpV4PooledAddrSecDns OBJECT-TYPE
    SYNTAX       InetAddressIPv4
    MAX-ACCESS   read-only
    STATUS       current
    DESCRIPTION
        "Cisco Firepower vnic:IpV4PooledAddr:secDns managed
        object property"
    ::= { cfprApVnicIpV4PooledAddrEntry 9 }

cfprApVnicIpV4PooledAddrSubnet OBJECT-TYPE
    SYNTAX       InetAddressIPv4
    MAX-ACCESS   read-only
    STATUS       current
    DESCRIPTION
        "Cisco Firepower vnic:IpV4PooledAddr:subnet managed
        object property"
    ::= { cfprApVnicIpV4PooledAddrEntry 10 }

cfprApVnicIpV4ProfDerivedAddrTable OBJECT-TYPE
    SYNTAX           SEQUENCE OF CfprApVnicIpV4ProfDerivedAddrEntry
    MAX-ACCESS       not-accessible
    STATUS           current
    DESCRIPTION
        "Cisco Firepower vnic:IpV4ProfDerivedAddr managed object table"
    ::= { cfprApVnicObjects 38 }

cfprApVnicIpV4ProfDerivedAddrEntry OBJECT-TYPE
    SYNTAX           CfprApVnicIpV4ProfDerivedAddrEntry
    MAX-ACCESS       not-accessible
    STATUS           current
    DESCRIPTION
        "Entry for the cfprApVnicIpV4ProfDerivedAddrTable table."
    INDEX { cfprApVnicIpV4ProfDerivedAddrInstanceId }
    ::= { cfprApVnicIpV4ProfDerivedAddrTable 1 }

CfprApVnicIpV4ProfDerivedAddrEntry ::= SEQUENCE {
    cfprApVnicIpV4ProfDerivedAddrInstanceId                          CfprApManagedObjectId,
    cfprApVnicIpV4ProfDerivedAddrDn                                  CfprApManagedObjectDn,
    cfprApVnicIpV4ProfDerivedAddrRn                                  SnmpAdminString,
    cfprApVnicIpV4ProfDerivedAddrAddr                                InetAddressIPv4,
    cfprApVnicIpV4ProfDerivedAddrDefGw                               InetAddressIPv4,
    cfprApVnicIpV4ProfDerivedAddrSubnet                              InetAddressIPv4
}

cfprApVnicIpV4ProfDerivedAddrInstanceId OBJECT-TYPE
    SYNTAX       CfprApManagedObjectId
    MAX-ACCESS   not-accessible
    STATUS       current
    DESCRIPTION
        "Instance identifier of the managed object."
    ::= { cfprApVnicIpV4ProfDerivedAddrEntry 1 }

cfprApVnicIpV4ProfDerivedAddrDn OBJECT-TYPE
    SYNTAX       CfprApManagedObjectDn
    MAX-ACCESS   read-only
    STATUS       current
    DESCRIPTION
        "Cisco Firepower vnic:IpV4ProfDerivedAddr:dn managed
        object property"
    ::= { cfprApVnicIpV4ProfDerivedAddrEntry 2 }

cfprApVnicIpV4ProfDerivedAddrRn OBJECT-TYPE
    SYNTAX       SnmpAdminString
    MAX-ACCESS   read-only
    STATUS       current
    DESCRIPTION
        "Cisco Firepower vnic:IpV4ProfDerivedAddr:rn managed
        object property"
    ::= { cfprApVnicIpV4ProfDerivedAddrEntry 3 }

cfprApVnicIpV4ProfDerivedAddrAddr OBJECT-TYPE
    SYNTAX       InetAddressIPv4
    MAX-ACCESS   read-only
    STATUS       current
    DESCRIPTION
        "Cisco Firepower vnic:IpV4ProfDerivedAddr:addr
        managed object property"
    ::= { cfprApVnicIpV4ProfDerivedAddrEntry 4 }

cfprApVnicIpV4ProfDerivedAddrDefGw OBJECT-TYPE
    SYNTAX       InetAddressIPv4
    MAX-ACCESS   read-only
    STATUS       current
    DESCRIPTION
        "Cisco Firepower vnic:IpV4ProfDerivedAddr:defGw
        managed object property"
    ::= { cfprApVnicIpV4ProfDerivedAddrEntry 5 }

cfprApVnicIpV4ProfDerivedAddrSubnet OBJECT-TYPE
    SYNTAX       InetAddressIPv4
    MAX-ACCESS   read-only
    STATUS       current
    DESCRIPTION
        "Cisco Firepower vnic:IpV4ProfDerivedAddr:subnet
        managed object property"
    ::= { cfprApVnicIpV4ProfDerivedAddrEntry 6 }

cfprApVnicIpV4StaticAddrTable OBJECT-TYPE
    SYNTAX           SEQUENCE OF CfprApVnicIpV4StaticAddrEntry
    MAX-ACCESS       not-accessible
    STATUS           current
    DESCRIPTION
        "Cisco Firepower vnic:IpV4StaticAddr managed object table"
    ::= { cfprApVnicObjects 39 }

cfprApVnicIpV4StaticAddrEntry OBJECT-TYPE
    SYNTAX           CfprApVnicIpV4StaticAddrEntry
    MAX-ACCESS       not-accessible
    STATUS           current
    DESCRIPTION
        "Entry for the cfprApVnicIpV4StaticAddrTable table."
    INDEX { cfprApVnicIpV4StaticAddrInstanceId }
    ::= { cfprApVnicIpV4StaticAddrTable 1 }

CfprApVnicIpV4StaticAddrEntry ::= SEQUENCE {
    cfprApVnicIpV4StaticAddrInstanceId                               CfprApManagedObjectId,
    cfprApVnicIpV4StaticAddrDn                                       CfprApManagedObjectDn,
    cfprApVnicIpV4StaticAddrRn                                       SnmpAdminString,
    cfprApVnicIpV4StaticAddrAddr                                     InetAddressIPv4,
    cfprApVnicIpV4StaticAddrDefGw                                    InetAddressIPv4,
    cfprApVnicIpV4StaticAddrPrimDns                                  InetAddressIPv4,
    cfprApVnicIpV4StaticAddrSecDns                                   InetAddressIPv4,
    cfprApVnicIpV4StaticAddrSubnet                                   InetAddressIPv4
}

cfprApVnicIpV4StaticAddrInstanceId OBJECT-TYPE
    SYNTAX       CfprApManagedObjectId
    MAX-ACCESS   not-accessible
    STATUS       current
    DESCRIPTION
        "Instance identifier of the managed object."
    ::= { cfprApVnicIpV4StaticAddrEntry 1 }

cfprApVnicIpV4StaticAddrDn OBJECT-TYPE
    SYNTAX       CfprApManagedObjectDn
    MAX-ACCESS   read-only
    STATUS       current
    DESCRIPTION
        "Cisco Firepower vnic:IpV4StaticAddr:dn managed object property"
    ::= { cfprApVnicIpV4StaticAddrEntry 2 }

cfprApVnicIpV4StaticAddrRn OBJECT-TYPE
    SYNTAX       SnmpAdminString
    MAX-ACCESS   read-only
    STATUS       current
    DESCRIPTION
        "Cisco Firepower vnic:IpV4StaticAddr:rn managed object property"
    ::= { cfprApVnicIpV4StaticAddrEntry 3 }

cfprApVnicIpV4StaticAddrAddr OBJECT-TYPE
    SYNTAX       InetAddressIPv4
    MAX-ACCESS   read-only
    STATUS       current
    DESCRIPTION
        "Cisco Firepower vnic:IpV4StaticAddr:addr managed object property"
    ::= { cfprApVnicIpV4StaticAddrEntry 4 }

cfprApVnicIpV4StaticAddrDefGw OBJECT-TYPE
    SYNTAX       InetAddressIPv4
    MAX-ACCESS   read-only
    STATUS       current
    DESCRIPTION
        "Cisco Firepower vnic:IpV4StaticAddr:defGw managed
        object property"
    ::= { cfprApVnicIpV4StaticAddrEntry 5 }

cfprApVnicIpV4StaticAddrPrimDns OBJECT-TYPE
    SYNTAX       InetAddressIPv4
    MAX-ACCESS   read-only
    STATUS       current
    DESCRIPTION
        "Cisco Firepower vnic:IpV4StaticAddr:primDns managed
        object property"
    ::= { cfprApVnicIpV4StaticAddrEntry 6 }

cfprApVnicIpV4StaticAddrSecDns OBJECT-TYPE
    SYNTAX       InetAddressIPv4
    MAX-ACCESS   read-only
    STATUS       current
    DESCRIPTION
        "Cisco Firepower vnic:IpV4StaticAddr:secDns managed
        object property"
    ::= { cfprApVnicIpV4StaticAddrEntry 7 }

cfprApVnicIpV4StaticAddrSubnet OBJECT-TYPE
    SYNTAX       InetAddressIPv4
    MAX-ACCESS   read-only
    STATUS       current
    DESCRIPTION
        "Cisco Firepower vnic:IpV4StaticAddr:subnet managed
        object property"
    ::= { cfprApVnicIpV4StaticAddrEntry 8 }

cfprApVnicIpV6HistoryTable OBJECT-TYPE
    SYNTAX           SEQUENCE OF CfprApVnicIpV6HistoryEntry
    MAX-ACCESS       not-accessible
    STATUS           current
    DESCRIPTION
        "Cisco Firepower vnic:IpV6History managed object table"
    ::= { cfprApVnicObjects 40 }

cfprApVnicIpV6HistoryEntry OBJECT-TYPE
    SYNTAX           CfprApVnicIpV6HistoryEntry
    MAX-ACCESS       not-accessible
    STATUS           current
    DESCRIPTION
        "Entry for the cfprApVnicIpV6HistoryTable table."
    INDEX { cfprApVnicIpV6HistoryInstanceId }
    ::= { cfprApVnicIpV6HistoryTable 1 }

CfprApVnicIpV6HistoryEntry ::= SEQUENCE {
    cfprApVnicIpV6HistoryInstanceId                                  CfprApManagedObjectId,
    cfprApVnicIpV6HistoryDn                                          CfprApManagedObjectDn,
    cfprApVnicIpV6HistoryRn                                          SnmpAdminString,
    cfprApVnicIpV6HistoryOldIpV6Addr                                 InetAddressIPv6
}

cfprApVnicIpV6HistoryInstanceId OBJECT-TYPE
    SYNTAX       CfprApManagedObjectId
    MAX-ACCESS   not-accessible
    STATUS       current
    DESCRIPTION
        "Instance identifier of the managed object."
    ::= { cfprApVnicIpV6HistoryEntry 1 }

cfprApVnicIpV6HistoryDn OBJECT-TYPE
    SYNTAX       CfprApManagedObjectDn
    MAX-ACCESS   read-only
    STATUS       current
    DESCRIPTION
        "Cisco Firepower vnic:IpV6History:dn managed object property"
    ::= { cfprApVnicIpV6HistoryEntry 2 }

cfprApVnicIpV6HistoryRn OBJECT-TYPE
    SYNTAX       SnmpAdminString
    MAX-ACCESS   read-only
    STATUS       current
    DESCRIPTION
        "Cisco Firepower vnic:IpV6History:rn managed object property"
    ::= { cfprApVnicIpV6HistoryEntry 3 }

cfprApVnicIpV6HistoryOldIpV6Addr OBJECT-TYPE
    SYNTAX       InetAddressIPv6
    MAX-ACCESS   read-only
    STATUS       current
    DESCRIPTION
        "Cisco Firepower vnic:IpV6History:oldIpV6Addr managed
        object property"
    ::= { cfprApVnicIpV6HistoryEntry 4 }

cfprApVnicIpV6MgmtPooledAddrTable OBJECT-TYPE
    SYNTAX           SEQUENCE OF CfprApVnicIpV6MgmtPooledAddrEntry
    MAX-ACCESS       not-accessible
    STATUS           current
    DESCRIPTION
        "Cisco Firepower vnic:IpV6MgmtPooledAddr managed object table"
    ::= { cfprApVnicObjects 41 }

cfprApVnicIpV6MgmtPooledAddrEntry OBJECT-TYPE
    SYNTAX           CfprApVnicIpV6MgmtPooledAddrEntry
    MAX-ACCESS       not-accessible
    STATUS           current
    DESCRIPTION
        "Entry for the cfprApVnicIpV6MgmtPooledAddrTable table."
    INDEX { cfprApVnicIpV6MgmtPooledAddrInstanceId }
    ::= { cfprApVnicIpV6MgmtPooledAddrTable 1 }

CfprApVnicIpV6MgmtPooledAddrEntry ::= SEQUENCE {
    cfprApVnicIpV6MgmtPooledAddrInstanceId                           CfprApManagedObjectId,
    cfprApVnicIpV6MgmtPooledAddrDn                                   CfprApManagedObjectDn,
    cfprApVnicIpV6MgmtPooledAddrRn                                   SnmpAdminString,
    cfprApVnicIpV6MgmtPooledAddrAddr                                 InetAddressIPv6,
    cfprApVnicIpV6MgmtPooledAddrDefGw                                InetAddressIPv6,
    cfprApVnicIpV6MgmtPooledAddrName                                 SnmpAdminString,
    cfprApVnicIpV6MgmtPooledAddrOperName                             SnmpAdminString,
    cfprApVnicIpV6MgmtPooledAddrPrefix                               Gauge32,
    cfprApVnicIpV6MgmtPooledAddrPrimDns                              InetAddressIPv6,
    cfprApVnicIpV6MgmtPooledAddrSecDns                               InetAddressIPv6
}

cfprApVnicIpV6MgmtPooledAddrInstanceId OBJECT-TYPE
    SYNTAX       CfprApManagedObjectId
    MAX-ACCESS   not-accessible
    STATUS       current
    DESCRIPTION
        "Instance identifier of the managed object."
    ::= { cfprApVnicIpV6MgmtPooledAddrEntry 1 }

cfprApVnicIpV6MgmtPooledAddrDn OBJECT-TYPE
    SYNTAX       CfprApManagedObjectDn
    MAX-ACCESS   read-only
    STATUS       current
    DESCRIPTION
        "Cisco Firepower vnic:IpV6MgmtPooledAddr:dn managed
        object property"
    ::= { cfprApVnicIpV6MgmtPooledAddrEntry 2 }

cfprApVnicIpV6MgmtPooledAddrRn OBJECT-TYPE
    SYNTAX       SnmpAdminString
    MAX-ACCESS   read-only
    STATUS       current
    DESCRIPTION
        "Cisco Firepower vnic:IpV6MgmtPooledAddr:rn managed
        object property"
    ::= { cfprApVnicIpV6MgmtPooledAddrEntry 3 }

cfprApVnicIpV6MgmtPooledAddrAddr OBJECT-TYPE
    SYNTAX       InetAddressIPv6
    MAX-ACCESS   read-only
    STATUS       current
    DESCRIPTION
        "Cisco Firepower vnic:IpV6MgmtPooledAddr:addr managed
        object property"
    ::= { cfprApVnicIpV6MgmtPooledAddrEntry 4 }

cfprApVnicIpV6MgmtPooledAddrDefGw OBJECT-TYPE
    SYNTAX       InetAddressIPv6
    MAX-ACCESS   read-only
    STATUS       current
    DESCRIPTION
        "Cisco Firepower vnic:IpV6MgmtPooledAddr:defGw
        managed object property"
    ::= { cfprApVnicIpV6MgmtPooledAddrEntry 5 }

cfprApVnicIpV6MgmtPooledAddrName OBJECT-TYPE
    SYNTAX       SnmpAdminString
    MAX-ACCESS   read-only
    STATUS       current
    DESCRIPTION
        "Cisco Firepower vnic:IpV6MgmtPooledAddr:name managed
        object property"
    ::= { cfprApVnicIpV6MgmtPooledAddrEntry 6 }

cfprApVnicIpV6MgmtPooledAddrOperName OBJECT-TYPE
    SYNTAX       SnmpAdminString
    MAX-ACCESS   read-only
    STATUS       current
    DESCRIPTION
        "Cisco Firepower vnic:IpV6MgmtPooledAddr:operName
        managed object property"
    ::= { cfprApVnicIpV6MgmtPooledAddrEntry 7 }

cfprApVnicIpV6MgmtPooledAddrPrefix OBJECT-TYPE
    SYNTAX       Gauge32
    MAX-ACCESS   read-only
    STATUS       current
    DESCRIPTION
        "Cisco Firepower vnic:IpV6MgmtPooledAddr:prefix
        managed object property"
    ::= { cfprApVnicIpV6MgmtPooledAddrEntry 8 }

cfprApVnicIpV6MgmtPooledAddrPrimDns OBJECT-TYPE
    SYNTAX       InetAddressIPv6
    MAX-ACCESS   read-only
    STATUS       current
    DESCRIPTION
        "Cisco Firepower vnic:IpV6MgmtPooledAddr:primDns
        managed object property"
    ::= { cfprApVnicIpV6MgmtPooledAddrEntry 9 }

cfprApVnicIpV6MgmtPooledAddrSecDns OBJECT-TYPE
    SYNTAX       InetAddressIPv6
    MAX-ACCESS   read-only
    STATUS       current
    DESCRIPTION
        "Cisco Firepower vnic:IpV6MgmtPooledAddr:secDns
        managed object property"
    ::= { cfprApVnicIpV6MgmtPooledAddrEntry 10 }

cfprApVnicIpV6StaticAddrTable OBJECT-TYPE
    SYNTAX           SEQUENCE OF CfprApVnicIpV6StaticAddrEntry
    MAX-ACCESS       not-accessible
    STATUS           current
    DESCRIPTION
        "Cisco Firepower vnic:IpV6StaticAddr managed object table"
    ::= { cfprApVnicObjects 42 }

cfprApVnicIpV6StaticAddrEntry OBJECT-TYPE
    SYNTAX           CfprApVnicIpV6StaticAddrEntry
    MAX-ACCESS       not-accessible
    STATUS           current
    DESCRIPTION
        "Entry for the cfprApVnicIpV6StaticAddrTable table."
    INDEX { cfprApVnicIpV6StaticAddrInstanceId }
    ::= { cfprApVnicIpV6StaticAddrTable 1 }

CfprApVnicIpV6StaticAddrEntry ::= SEQUENCE {
    cfprApVnicIpV6StaticAddrInstanceId                               CfprApManagedObjectId,
    cfprApVnicIpV6StaticAddrDn                                       CfprApManagedObjectDn,
    cfprApVnicIpV6StaticAddrRn                                       SnmpAdminString,
    cfprApVnicIpV6StaticAddrAddr                                     InetAddressIPv6,
    cfprApVnicIpV6StaticAddrDefGw                                    InetAddressIPv6,
    cfprApVnicIpV6StaticAddrPrefix                                   Gauge32,
    cfprApVnicIpV6StaticAddrPrimDns                                  InetAddressIPv6,
    cfprApVnicIpV6StaticAddrSecDns                                   InetAddressIPv6
}

cfprApVnicIpV6StaticAddrInstanceId OBJECT-TYPE
    SYNTAX       CfprApManagedObjectId
    MAX-ACCESS   not-accessible
    STATUS       current
    DESCRIPTION
        "Instance identifier of the managed object."
    ::= { cfprApVnicIpV6StaticAddrEntry 1 }

cfprApVnicIpV6StaticAddrDn OBJECT-TYPE
    SYNTAX       CfprApManagedObjectDn
    MAX-ACCESS   read-only
    STATUS       current
    DESCRIPTION
        "Cisco Firepower vnic:IpV6StaticAddr:dn managed object property"
    ::= { cfprApVnicIpV6StaticAddrEntry 2 }

cfprApVnicIpV6StaticAddrRn OBJECT-TYPE
    SYNTAX       SnmpAdminString
    MAX-ACCESS   read-only
    STATUS       current
    DESCRIPTION
        "Cisco Firepower vnic:IpV6StaticAddr:rn managed object property"
    ::= { cfprApVnicIpV6StaticAddrEntry 3 }

cfprApVnicIpV6StaticAddrAddr OBJECT-TYPE
    SYNTAX       InetAddressIPv6
    MAX-ACCESS   read-only
    STATUS       current
    DESCRIPTION
        "Cisco Firepower vnic:IpV6StaticAddr:addr managed object property"
    ::= { cfprApVnicIpV6StaticAddrEntry 4 }

cfprApVnicIpV6StaticAddrDefGw OBJECT-TYPE
    SYNTAX       InetAddressIPv6
    MAX-ACCESS   read-only
    STATUS       current
    DESCRIPTION
        "Cisco Firepower vnic:IpV6StaticAddr:defGw managed
        object property"
    ::= { cfprApVnicIpV6StaticAddrEntry 5 }

cfprApVnicIpV6StaticAddrPrefix OBJECT-TYPE
    SYNTAX       Gauge32
    MAX-ACCESS   read-only
    STATUS       current
    DESCRIPTION
        "Cisco Firepower vnic:IpV6StaticAddr:prefix managed
        object property"
    ::= { cfprApVnicIpV6StaticAddrEntry 6 }

cfprApVnicIpV6StaticAddrPrimDns OBJECT-TYPE
    SYNTAX       InetAddressIPv6
    MAX-ACCESS   read-only
    STATUS       current
    DESCRIPTION
        "Cisco Firepower vnic:IpV6StaticAddr:primDns managed
        object property"
    ::= { cfprApVnicIpV6StaticAddrEntry 7 }

cfprApVnicIpV6StaticAddrSecDns OBJECT-TYPE
    SYNTAX       InetAddressIPv6
    MAX-ACCESS   read-only
    STATUS       current
    DESCRIPTION
        "Cisco Firepower vnic:IpV6StaticAddr:secDns managed
        object property"
    ::= { cfprApVnicIpV6StaticAddrEntry 8 }

cfprApVnicIpcTable OBJECT-TYPE
    SYNTAX           SEQUENCE OF CfprApVnicIpcEntry
    MAX-ACCESS       not-accessible
    STATUS           current
    DESCRIPTION
        "Cisco Firepower vnic:Ipc managed object table"
    ::= { cfprApVnicObjects 43 }

cfprApVnicIpcEntry OBJECT-TYPE
    SYNTAX           CfprApVnicIpcEntry
    MAX-ACCESS       not-accessible
    STATUS           current
    DESCRIPTION
        "Entry for the cfprApVnicIpcTable table."
    INDEX { cfprApVnicIpcInstanceId }
    ::= { cfprApVnicIpcTable 1 }

CfprApVnicIpcEntry ::= SEQUENCE {
    cfprApVnicIpcInstanceId                                          CfprApManagedObjectId,
    cfprApVnicIpcDn                                                  CfprApManagedObjectDn,
    cfprApVnicIpcRn                                                  SnmpAdminString,
    cfprApVnicIpcAdaptorProfileName                                  SnmpAdminString,
    cfprApVnicIpcAddr                                                MacAddress,
    cfprApVnicIpcAdminHostPort                                       CfprApFabricHostPortId,
    cfprApVnicIpcAdminVcon                                           SnmpAdminString,
    cfprApVnicIpcAppRole                                             CfprApVnicAppRole,
    cfprApVnicIpcBootDev                                             CfprApVnicVnicBootDev,
    cfprApVnicIpcConfigQualifier                                     CfprApVnicConfigIssues,
    cfprApVnicIpcConfigState                                         CfprApLsConfigState,
    cfprApVnicIpcEquipmentDn                                         SnmpAdminString,
    cfprApVnicIpcIdentPoolName                                       SnmpAdminString,
    cfprApVnicIpcInstType                                            CfprApVnicInstantiation,
    cfprApVnicIpcMtu                                                 Gauge32,
    cfprApVnicIpcName                                                SnmpAdminString,
    cfprApVnicIpcNwCtrlPolicyName                                    SnmpAdminString,
    cfprApVnicIpcNwTemplName                                         SnmpAdminString,
    cfprApVnicIpcOperAdaptorProfileName                              SnmpAdminString,
    cfprApVnicIpcOperHostPort                                        CfprApVnicVnicOperHostPort,
    cfprApVnicIpcOperIdentPoolName                                   SnmpAdminString,
    cfprApVnicIpcOperNwCtrlPolicyName                                SnmpAdminString,
    cfprApVnicIpcOperNwTemplName                                     SnmpAdminString,
    cfprApVnicIpcOperOrder                                           Gauge32,
    cfprApVnicIpcOperPinToGroupName                                  SnmpAdminString,
    cfprApVnicIpcOperQosPolicyName                                   SnmpAdminString,
    cfprApVnicIpcOperSpeed                                           Gauge32,
    cfprApVnicIpcOperStatsPolicyName                                 SnmpAdminString,
    cfprApVnicIpcOperVcon                                            SnmpAdminString,
    cfprApVnicIpcOrder                                               Gauge32,
    cfprApVnicIpcOwner                                               CfprApVnicConnectionOwner,
    cfprApVnicIpcPinToGroupName                                      SnmpAdminString,
    cfprApVnicIpcQosPolicyName                                       SnmpAdminString,
    cfprApVnicIpcStatsPolicyName                                     SnmpAdminString,
    cfprApVnicIpcSwitchId                                            CfprApVnicEtherBaseSwitchId,
    cfprApVnicIpcType                                                CfprApVnicIpcType
}

cfprApVnicIpcInstanceId OBJECT-TYPE
    SYNTAX       CfprApManagedObjectId
    MAX-ACCESS   not-accessible
    STATUS       current
    DESCRIPTION
        "Instance identifier of the managed object."
    ::= { cfprApVnicIpcEntry 1 }

cfprApVnicIpcDn OBJECT-TYPE
    SYNTAX       CfprApManagedObjectDn
    MAX-ACCESS   read-only
    STATUS       current
    DESCRIPTION
        "Cisco Firepower vnic:Ipc:dn managed object property"
    ::= { cfprApVnicIpcEntry 2 }

cfprApVnicIpcRn OBJECT-TYPE
    SYNTAX       SnmpAdminString
    MAX-ACCESS   read-only
    STATUS       current
    DESCRIPTION
        "Cisco Firepower vnic:Ipc:rn managed object property"
    ::= { cfprApVnicIpcEntry 3 }

cfprApVnicIpcAdaptorProfileName OBJECT-TYPE
    SYNTAX       SnmpAdminString
    MAX-ACCESS   read-only
    STATUS       current
    DESCRIPTION
        "Cisco Firepower vnic:Ipc:adaptorProfileName managed
        object property"
    ::= { cfprApVnicIpcEntry 4 }

cfprApVnicIpcAddr OBJECT-TYPE
    SYNTAX       MacAddress
    MAX-ACCESS   read-only
    STATUS       current
    DESCRIPTION
        "Cisco Firepower vnic:Ipc:addr managed object property"
    ::= { cfprApVnicIpcEntry 5 }

cfprApVnicIpcAdminHostPort OBJECT-TYPE
    SYNTAX       CfprApFabricHostPortId
    MAX-ACCESS   read-only
    STATUS       current
    DESCRIPTION
        "Cisco Firepower vnic:Ipc:adminHostPort managed object property"
    ::= { cfprApVnicIpcEntry 6 }

cfprApVnicIpcAdminVcon OBJECT-TYPE
    SYNTAX       SnmpAdminString
    MAX-ACCESS   read-only
    STATUS       current
    DESCRIPTION
        "Cisco Firepower vnic:Ipc:adminVcon managed object property"
    ::= { cfprApVnicIpcEntry 7 }

cfprApVnicIpcAppRole OBJECT-TYPE
    SYNTAX       CfprApVnicAppRole
    MAX-ACCESS   read-only
    STATUS       current
    DESCRIPTION
        "Cisco Firepower vnic:Ipc:appRole managed object property"
    ::= { cfprApVnicIpcEntry 8 }

cfprApVnicIpcBootDev OBJECT-TYPE
    SYNTAX       CfprApVnicVnicBootDev
    MAX-ACCESS   read-only
    STATUS       current
    DESCRIPTION
        "Cisco Firepower vnic:Ipc:bootDev managed object property"
    ::= { cfprApVnicIpcEntry 9 }

cfprApVnicIpcConfigQualifier OBJECT-TYPE
    SYNTAX       CfprApVnicConfigIssues
    MAX-ACCESS   read-only
    STATUS       current
    DESCRIPTION
        "Cisco Firepower vnic:Ipc:configQualifier managed object property"
    ::= { cfprApVnicIpcEntry 10 }

cfprApVnicIpcConfigState OBJECT-TYPE
    SYNTAX       CfprApLsConfigState
    MAX-ACCESS   read-only
    STATUS       current
    DESCRIPTION
        "Cisco Firepower vnic:Ipc:configState managed object property"
    ::= { cfprApVnicIpcEntry 11 }

cfprApVnicIpcEquipmentDn OBJECT-TYPE
    SYNTAX       SnmpAdminString
    MAX-ACCESS   read-only
    STATUS       current
    DESCRIPTION
        "Cisco Firepower vnic:Ipc:equipmentDn managed object property"
    ::= { cfprApVnicIpcEntry 12 }

cfprApVnicIpcIdentPoolName OBJECT-TYPE
    SYNTAX       SnmpAdminString
    MAX-ACCESS   read-only
    STATUS       current
    DESCRIPTION
        "Cisco Firepower vnic:Ipc:identPoolName managed object property"
    ::= { cfprApVnicIpcEntry 13 }

cfprApVnicIpcInstType OBJECT-TYPE
    SYNTAX       CfprApVnicInstantiation
    MAX-ACCESS   read-only
    STATUS       current
    DESCRIPTION
        "Cisco Firepower vnic:Ipc:instType managed object property"
    ::= { cfprApVnicIpcEntry 14 }

cfprApVnicIpcMtu OBJECT-TYPE
    SYNTAX       Gauge32
    MAX-ACCESS   read-only
    STATUS       current
    DESCRIPTION
        "Cisco Firepower vnic:Ipc:mtu managed object property"
    ::= { cfprApVnicIpcEntry 15 }

cfprApVnicIpcName OBJECT-TYPE
    SYNTAX       SnmpAdminString
    MAX-ACCESS   read-only
    STATUS       current
    DESCRIPTION
        "Cisco Firepower vnic:Ipc:name managed object property"
    ::= { cfprApVnicIpcEntry 16 }

cfprApVnicIpcNwCtrlPolicyName OBJECT-TYPE
    SYNTAX       SnmpAdminString
    MAX-ACCESS   read-only
    STATUS       current
    DESCRIPTION
        "Cisco Firepower vnic:Ipc:nwCtrlPolicyName managed
        object property"
    ::= { cfprApVnicIpcEntry 17 }

cfprApVnicIpcNwTemplName OBJECT-TYPE
    SYNTAX       SnmpAdminString
    MAX-ACCESS   read-only
    STATUS       current
    DESCRIPTION
        "Cisco Firepower vnic:Ipc:nwTemplName managed object property"
    ::= { cfprApVnicIpcEntry 18 }

cfprApVnicIpcOperAdaptorProfileName OBJECT-TYPE
    SYNTAX       SnmpAdminString
    MAX-ACCESS   read-only
    STATUS       current
    DESCRIPTION
        "Cisco Firepower vnic:Ipc:operAdaptorProfileName
        managed object property"
    ::= { cfprApVnicIpcEntry 19 }

cfprApVnicIpcOperHostPort OBJECT-TYPE
    SYNTAX       CfprApVnicVnicOperHostPort
    MAX-ACCESS   read-only
    STATUS       current
    DESCRIPTION
        "Cisco Firepower vnic:Ipc:operHostPort managed object property"
    ::= { cfprApVnicIpcEntry 20 }

cfprApVnicIpcOperIdentPoolName OBJECT-TYPE
    SYNTAX       SnmpAdminString
    MAX-ACCESS   read-only
    STATUS       current
    DESCRIPTION
        "Cisco Firepower vnic:Ipc:operIdentPoolName managed
        object property"
    ::= { cfprApVnicIpcEntry 21 }

cfprApVnicIpcOperNwCtrlPolicyName OBJECT-TYPE
    SYNTAX       SnmpAdminString
    MAX-ACCESS   read-only
    STATUS       current
    DESCRIPTION
        "Cisco Firepower vnic:Ipc:operNwCtrlPolicyName
        managed object property"
    ::= { cfprApVnicIpcEntry 22 }

cfprApVnicIpcOperNwTemplName OBJECT-TYPE
    SYNTAX       SnmpAdminString
    MAX-ACCESS   read-only
    STATUS       current
    DESCRIPTION
        "Cisco Firepower vnic:Ipc:operNwTemplName managed object property"
    ::= { cfprApVnicIpcEntry 23 }

cfprApVnicIpcOperOrder OBJECT-TYPE
    SYNTAX       Gauge32
    MAX-ACCESS   read-only
    STATUS       current
    DESCRIPTION
        "Cisco Firepower vnic:Ipc:operOrder managed object property"
    ::= { cfprApVnicIpcEntry 24 }

cfprApVnicIpcOperPinToGroupName OBJECT-TYPE
    SYNTAX       SnmpAdminString
    MAX-ACCESS   read-only
    STATUS       current
    DESCRIPTION
        "Cisco Firepower vnic:Ipc:operPinToGroupName managed
        object property"
    ::= { cfprApVnicIpcEntry 25 }

cfprApVnicIpcOperQosPolicyName OBJECT-TYPE
    SYNTAX       SnmpAdminString
    MAX-ACCESS   read-only
    STATUS       current
    DESCRIPTION
        "Cisco Firepower vnic:Ipc:operQosPolicyName managed
        object property"
    ::= { cfprApVnicIpcEntry 26 }

cfprApVnicIpcOperSpeed OBJECT-TYPE
    SYNTAX       Gauge32
    MAX-ACCESS   read-only
    STATUS       current
    DESCRIPTION
        "Cisco Firepower vnic:Ipc:operSpeed managed object property"
    ::= { cfprApVnicIpcEntry 27 }

cfprApVnicIpcOperStatsPolicyName OBJECT-TYPE
    SYNTAX       SnmpAdminString
    MAX-ACCESS   read-only
    STATUS       current
    DESCRIPTION
        "Cisco Firepower vnic:Ipc:operStatsPolicyName managed
        object property"
    ::= { cfprApVnicIpcEntry 28 }

cfprApVnicIpcOperVcon OBJECT-TYPE
    SYNTAX       SnmpAdminString
    MAX-ACCESS   read-only
    STATUS       current
    DESCRIPTION
        "Cisco Firepower vnic:Ipc:operVcon managed object property"
    ::= { cfprApVnicIpcEntry 29 }

cfprApVnicIpcOrder OBJECT-TYPE
    SYNTAX       Gauge32
    MAX-ACCESS   read-only
    STATUS       current
    DESCRIPTION
        "Cisco Firepower vnic:Ipc:order managed object property"
    ::= { cfprApVnicIpcEntry 30 }

cfprApVnicIpcOwner OBJECT-TYPE
    SYNTAX       CfprApVnicConnectionOwner
    MAX-ACCESS   read-only
    STATUS       current
    DESCRIPTION
        "Cisco Firepower vnic:Ipc:owner managed object property"
    ::= { cfprApVnicIpcEntry 31 }

cfprApVnicIpcPinToGroupName OBJECT-TYPE
    SYNTAX       SnmpAdminString
    MAX-ACCESS   read-only
    STATUS       current
    DESCRIPTION
        "Cisco Firepower vnic:Ipc:pinToGroupName managed object property"
    ::= { cfprApVnicIpcEntry 32 }

cfprApVnicIpcQosPolicyName OBJECT-TYPE
    SYNTAX       SnmpAdminString
    MAX-ACCESS   read-only
    STATUS       current
    DESCRIPTION
        "Cisco Firepower vnic:Ipc:qosPolicyName managed object property"
    ::= { cfprApVnicIpcEntry 33 }

cfprApVnicIpcStatsPolicyName OBJECT-TYPE
    SYNTAX       SnmpAdminString
    MAX-ACCESS   read-only
    STATUS       current
    DESCRIPTION
        "Cisco Firepower vnic:Ipc:statsPolicyName managed object property"
    ::= { cfprApVnicIpcEntry 34 }

cfprApVnicIpcSwitchId OBJECT-TYPE
    SYNTAX       CfprApVnicEtherBaseSwitchId
    MAX-ACCESS   read-only
    STATUS       current
    DESCRIPTION
        "Cisco Firepower vnic:Ipc:switchId managed object property"
    ::= { cfprApVnicIpcEntry 35 }

cfprApVnicIpcType OBJECT-TYPE
    SYNTAX       CfprApVnicIpcType
    MAX-ACCESS   read-only
    STATUS       current
    DESCRIPTION
        "Cisco Firepower vnic:Ipc:type managed object property"
    ::= { cfprApVnicIpcEntry 36 }

cfprApVnicIpcIfTable OBJECT-TYPE
    SYNTAX           SEQUENCE OF CfprApVnicIpcIfEntry
    MAX-ACCESS       not-accessible
    STATUS           current
    DESCRIPTION
        "Cisco Firepower vnic:IpcIf managed object table"
    ::= { cfprApVnicObjects 44 }

cfprApVnicIpcIfEntry OBJECT-TYPE
    SYNTAX           CfprApVnicIpcIfEntry
    MAX-ACCESS       not-accessible
    STATUS           current
    DESCRIPTION
        "Entry for the cfprApVnicIpcIfTable table."
    INDEX { cfprApVnicIpcIfInstanceId }
    ::= { cfprApVnicIpcIfTable 1 }

CfprApVnicIpcIfEntry ::= SEQUENCE {
    cfprApVnicIpcIfInstanceId                                        CfprApManagedObjectId,
    cfprApVnicIpcIfDn                                                CfprApManagedObjectDn,
    cfprApVnicIpcIfRn                                                SnmpAdminString,
    cfprApVnicIpcIfAddr                                              MacAddress,
    cfprApVnicIpcIfConfigQualifier                                   CfprApVnicConfigIssues,
    cfprApVnicIpcIfDefaultNet                                        TruthValue,
    cfprApVnicIpcIfName                                              SnmpAdminString,
    cfprApVnicIpcIfOperState                                         CfprApVnicIfOperState,
    cfprApVnicIpcIfOperVnetDn                                        SnmpAdminString,
    cfprApVnicIpcIfOperVnetName                                      SnmpAdminString,
    cfprApVnicIpcIfOwner                                             CfprApVnicConnectionOwner,
    cfprApVnicIpcIfPubNwId                                           Gauge32,
    cfprApVnicIpcIfSharing                                           CfprApFabricVlanSharingType,
    cfprApVnicIpcIfSwitchId                                          CfprApVnicL2IfSwitchId,
    cfprApVnicIpcIfType                                              CfprApVnicAIpcIfType,
    cfprApVnicIpcIfVnet                                              Gauge32
}

cfprApVnicIpcIfInstanceId OBJECT-TYPE
    SYNTAX       CfprApManagedObjectId
    MAX-ACCESS   not-accessible
    STATUS       current
    DESCRIPTION
        "Instance identifier of the managed object."
    ::= { cfprApVnicIpcIfEntry 1 }

cfprApVnicIpcIfDn OBJECT-TYPE
    SYNTAX       CfprApManagedObjectDn
    MAX-ACCESS   read-only
    STATUS       current
    DESCRIPTION
        "Cisco Firepower vnic:IpcIf:dn managed object property"
    ::= { cfprApVnicIpcIfEntry 2 }

cfprApVnicIpcIfRn OBJECT-TYPE
    SYNTAX       SnmpAdminString
    MAX-ACCESS   read-only
    STATUS       current
    DESCRIPTION
        "Cisco Firepower vnic:IpcIf:rn managed object property"
    ::= { cfprApVnicIpcIfEntry 3 }

cfprApVnicIpcIfAddr OBJECT-TYPE
    SYNTAX       MacAddress
    MAX-ACCESS   read-only
    STATUS       current
    DESCRIPTION
        "Cisco Firepower vnic:IpcIf:addr managed object property"
    ::= { cfprApVnicIpcIfEntry 4 }

cfprApVnicIpcIfConfigQualifier OBJECT-TYPE
    SYNTAX       CfprApVnicConfigIssues
    MAX-ACCESS   read-only
    STATUS       current
    DESCRIPTION
        "Cisco Firepower vnic:IpcIf:configQualifier managed
        object property"
    ::= { cfprApVnicIpcIfEntry 5 }

cfprApVnicIpcIfDefaultNet OBJECT-TYPE
    SYNTAX       TruthValue
    MAX-ACCESS   read-only
    STATUS       current
    DESCRIPTION
        "Cisco Firepower vnic:IpcIf:defaultNet managed object property"
    ::= { cfprApVnicIpcIfEntry 6 }

cfprApVnicIpcIfName OBJECT-TYPE
    SYNTAX       SnmpAdminString
    MAX-ACCESS   read-only
    STATUS       current
    DESCRIPTION
        "Cisco Firepower vnic:IpcIf:name managed object property"
    ::= { cfprApVnicIpcIfEntry 7 }

cfprApVnicIpcIfOperState OBJECT-TYPE
    SYNTAX       CfprApVnicIfOperState
    MAX-ACCESS   read-only
    STATUS       current
    DESCRIPTION
        "Cisco Firepower vnic:IpcIf:operState managed object property"
    ::= { cfprApVnicIpcIfEntry 8 }

cfprApVnicIpcIfOperVnetDn OBJECT-TYPE
    SYNTAX       SnmpAdminString
    MAX-ACCESS   read-only
    STATUS       current
    DESCRIPTION
        "Cisco Firepower vnic:IpcIf:operVnetDn managed object property"
    ::= { cfprApVnicIpcIfEntry 9 }

cfprApVnicIpcIfOperVnetName OBJECT-TYPE
    SYNTAX       SnmpAdminString
    MAX-ACCESS   read-only
    STATUS       current
    DESCRIPTION
        "Cisco Firepower vnic:IpcIf:operVnetName managed object property"
    ::= { cfprApVnicIpcIfEntry 10 }

cfprApVnicIpcIfOwner OBJECT-TYPE
    SYNTAX       CfprApVnicConnectionOwner
    MAX-ACCESS   read-only
    STATUS       current
    DESCRIPTION
        "Cisco Firepower vnic:IpcIf:owner managed object property"
    ::= { cfprApVnicIpcIfEntry 11 }

cfprApVnicIpcIfPubNwId OBJECT-TYPE
    SYNTAX       Gauge32
    MAX-ACCESS   read-only
    STATUS       current
    DESCRIPTION
        "Cisco Firepower vnic:IpcIf:pubNwId managed object property"
    ::= { cfprApVnicIpcIfEntry 12 }

cfprApVnicIpcIfSharing OBJECT-TYPE
    SYNTAX       CfprApFabricVlanSharingType
    MAX-ACCESS   read-only
    STATUS       current
    DESCRIPTION
        "Cisco Firepower vnic:IpcIf:sharing managed object property"
    ::= { cfprApVnicIpcIfEntry 13 }

cfprApVnicIpcIfSwitchId OBJECT-TYPE
    SYNTAX       CfprApVnicL2IfSwitchId
    MAX-ACCESS   read-only
    STATUS       current
    DESCRIPTION
        "Cisco Firepower vnic:IpcIf:switchId managed object property"
    ::= { cfprApVnicIpcIfEntry 14 }

cfprApVnicIpcIfType OBJECT-TYPE
    SYNTAX       CfprApVnicAIpcIfType
    MAX-ACCESS   read-only
    STATUS       current
    DESCRIPTION
        "Cisco Firepower vnic:IpcIf:type managed object property"
    ::= { cfprApVnicIpcIfEntry 15 }

cfprApVnicIpcIfVnet OBJECT-TYPE
    SYNTAX       Gauge32
    MAX-ACCESS   read-only
    STATUS       current
    DESCRIPTION
        "Cisco Firepower vnic:IpcIf:vnet managed object property"
    ::= { cfprApVnicIpcIfEntry 16 }

cfprApVnicIqnHistoryTable OBJECT-TYPE
    SYNTAX           SEQUENCE OF CfprApVnicIqnHistoryEntry
    MAX-ACCESS       not-accessible
    STATUS           current
    DESCRIPTION
        "Cisco Firepower vnic:IqnHistory managed object table"
    ::= { cfprApVnicObjects 45 }

cfprApVnicIqnHistoryEntry OBJECT-TYPE
    SYNTAX           CfprApVnicIqnHistoryEntry
    MAX-ACCESS       not-accessible
    STATUS           current
    DESCRIPTION
        "Entry for the cfprApVnicIqnHistoryTable table."
    INDEX { cfprApVnicIqnHistoryInstanceId }
    ::= { cfprApVnicIqnHistoryTable 1 }

CfprApVnicIqnHistoryEntry ::= SEQUENCE {
    cfprApVnicIqnHistoryInstanceId                                   CfprApManagedObjectId,
    cfprApVnicIqnHistoryDn                                           CfprApManagedObjectDn,
    cfprApVnicIqnHistoryRn                                           SnmpAdminString,
    cfprApVnicIqnHistoryOldInitiatorName                             SnmpAdminString
}

cfprApVnicIqnHistoryInstanceId OBJECT-TYPE
    SYNTAX       CfprApManagedObjectId
    MAX-ACCESS   not-accessible
    STATUS       current
    DESCRIPTION
        "Instance identifier of the managed object."
    ::= { cfprApVnicIqnHistoryEntry 1 }

cfprApVnicIqnHistoryDn OBJECT-TYPE
    SYNTAX       CfprApManagedObjectDn
    MAX-ACCESS   read-only
    STATUS       current
    DESCRIPTION
        "Cisco Firepower vnic:IqnHistory:dn managed object property"
    ::= { cfprApVnicIqnHistoryEntry 2 }

cfprApVnicIqnHistoryRn OBJECT-TYPE
    SYNTAX       SnmpAdminString
    MAX-ACCESS   read-only
    STATUS       current
    DESCRIPTION
        "Cisco Firepower vnic:IqnHistory:rn managed object property"
    ::= { cfprApVnicIqnHistoryEntry 3 }

cfprApVnicIqnHistoryOldInitiatorName OBJECT-TYPE
    SYNTAX       SnmpAdminString
    MAX-ACCESS   read-only
    STATUS       current
    DESCRIPTION
        "Cisco Firepower vnic:IqnHistory:oldInitiatorName
        managed object property"
    ::= { cfprApVnicIqnHistoryEntry 4 }

cfprApVnicLanConnPolicyTable OBJECT-TYPE
    SYNTAX           SEQUENCE OF CfprApVnicLanConnPolicyEntry
    MAX-ACCESS       not-accessible
    STATUS           current
    DESCRIPTION
        "Cisco Firepower vnic:LanConnPolicy managed object table"
    ::= { cfprApVnicObjects 46 }

cfprApVnicLanConnPolicyEntry OBJECT-TYPE
    SYNTAX           CfprApVnicLanConnPolicyEntry
    MAX-ACCESS       not-accessible
    STATUS           current
    DESCRIPTION
        "Entry for the cfprApVnicLanConnPolicyTable table."
    INDEX { cfprApVnicLanConnPolicyInstanceId }
    ::= { cfprApVnicLanConnPolicyTable 1 }

CfprApVnicLanConnPolicyEntry ::= SEQUENCE {
    cfprApVnicLanConnPolicyInstanceId                                CfprApManagedObjectId,
    cfprApVnicLanConnPolicyDn                                        CfprApManagedObjectDn,
    cfprApVnicLanConnPolicyRn                                        SnmpAdminString,
    cfprApVnicLanConnPolicyDescr                                     SnmpAdminString,
    cfprApVnicLanConnPolicyFltAggr                                   Unsigned64,
    cfprApVnicLanConnPolicyIntId                                     SnmpAdminString,
    cfprApVnicLanConnPolicyName                                      SnmpAdminString,
    cfprApVnicLanConnPolicyPolicyLevel                               Gauge32,
    cfprApVnicLanConnPolicyPolicyOwner                               CfprApPolicyPolicyOwner
}

cfprApVnicLanConnPolicyInstanceId OBJECT-TYPE
    SYNTAX       CfprApManagedObjectId
    MAX-ACCESS   not-accessible
    STATUS       current
    DESCRIPTION
        "Instance identifier of the managed object."
    ::= { cfprApVnicLanConnPolicyEntry 1 }

cfprApVnicLanConnPolicyDn OBJECT-TYPE
    SYNTAX       CfprApManagedObjectDn
    MAX-ACCESS   read-only
    STATUS       current
    DESCRIPTION
        "Cisco Firepower vnic:LanConnPolicy:dn managed object property"
    ::= { cfprApVnicLanConnPolicyEntry 2 }

cfprApVnicLanConnPolicyRn OBJECT-TYPE
    SYNTAX       SnmpAdminString
    MAX-ACCESS   read-only
    STATUS       current
    DESCRIPTION
        "Cisco Firepower vnic:LanConnPolicy:rn managed object property"
    ::= { cfprApVnicLanConnPolicyEntry 3 }

cfprApVnicLanConnPolicyDescr OBJECT-TYPE
    SYNTAX       SnmpAdminString
    MAX-ACCESS   read-only
    STATUS       current
    DESCRIPTION
        "Cisco Firepower vnic:LanConnPolicy:descr managed object property"
    ::= { cfprApVnicLanConnPolicyEntry 4 }

cfprApVnicLanConnPolicyFltAggr OBJECT-TYPE
    SYNTAX       Unsigned64
    MAX-ACCESS   read-only
    STATUS       current
    DESCRIPTION
        "Cisco Firepower vnic:LanConnPolicy:fltAggr managed
        object property"
    ::= { cfprApVnicLanConnPolicyEntry 5 }

cfprApVnicLanConnPolicyIntId OBJECT-TYPE
    SYNTAX       SnmpAdminString
    MAX-ACCESS   read-only
    STATUS       current
    DESCRIPTION
        "Cisco Firepower vnic:LanConnPolicy:intId managed object property"
    ::= { cfprApVnicLanConnPolicyEntry 6 }

cfprApVnicLanConnPolicyName OBJECT-TYPE
    SYNTAX       SnmpAdminString
    MAX-ACCESS   read-only
    STATUS       current
    DESCRIPTION
        "Cisco Firepower vnic:LanConnPolicy:name managed object property"
    ::= { cfprApVnicLanConnPolicyEntry 7 }

cfprApVnicLanConnPolicyPolicyLevel OBJECT-TYPE
    SYNTAX       Gauge32
    MAX-ACCESS   read-only
    STATUS       current
    DESCRIPTION
        "Cisco Firepower vnic:LanConnPolicy:policyLevel
        managed object property"
    ::= { cfprApVnicLanConnPolicyEntry 8 }

cfprApVnicLanConnPolicyPolicyOwner OBJECT-TYPE
    SYNTAX       CfprApPolicyPolicyOwner
    MAX-ACCESS   read-only
    STATUS       current
    DESCRIPTION
        "Cisco Firepower vnic:LanConnPolicy:policyOwner
        managed object property"
    ::= { cfprApVnicLanConnPolicyEntry 9 }

cfprApVnicLanConnTemplTable OBJECT-TYPE
    SYNTAX           SEQUENCE OF CfprApVnicLanConnTemplEntry
    MAX-ACCESS       not-accessible
    STATUS           current
    DESCRIPTION
        "Cisco Firepower vnic:LanConnTempl managed object table"
    ::= { cfprApVnicObjects 47 }

cfprApVnicLanConnTemplEntry OBJECT-TYPE
    SYNTAX           CfprApVnicLanConnTemplEntry
    MAX-ACCESS       not-accessible
    STATUS           current
    DESCRIPTION
        "Entry for the cfprApVnicLanConnTemplTable table."
    INDEX { cfprApVnicLanConnTemplInstanceId }
    ::= { cfprApVnicLanConnTemplTable 1 }

CfprApVnicLanConnTemplEntry ::= SEQUENCE {
    cfprApVnicLanConnTemplInstanceId                                 CfprApManagedObjectId,
    cfprApVnicLanConnTemplDn                                         CfprApManagedObjectDn,
    cfprApVnicLanConnTemplRn                                         SnmpAdminString,
    cfprApVnicLanConnTemplDescr                                      SnmpAdminString,
    cfprApVnicLanConnTemplIdentPoolName                              SnmpAdminString,
    cfprApVnicLanConnTemplIntId                                      SnmpAdminString,
    cfprApVnicLanConnTemplMtu                                        Gauge32,
    cfprApVnicLanConnTemplName                                       SnmpAdminString,
    cfprApVnicLanConnTemplNwCtrlPolicyName                           SnmpAdminString,
    cfprApVnicLanConnTemplOperIdentPoolName                          SnmpAdminString,
    cfprApVnicLanConnTemplOperNwCtrlPolicyName                       SnmpAdminString,
    cfprApVnicLanConnTemplOperQosPolicyName                          SnmpAdminString,
    cfprApVnicLanConnTemplOperStatsPolicyName                        SnmpAdminString,
    cfprApVnicLanConnTemplPinToGroupName                             SnmpAdminString,
    cfprApVnicLanConnTemplPolicyLevel                                Gauge32,
    cfprApVnicLanConnTemplPolicyOwner                                CfprApPolicyPolicyOwner,
    cfprApVnicLanConnTemplQosPolicyName                              SnmpAdminString,
    cfprApVnicLanConnTemplStatsPolicyName                            SnmpAdminString,
    cfprApVnicLanConnTemplSwitchId                                   CfprApVnicLanConnTemplSwitchId,
    cfprApVnicLanConnTemplTarget                                     CfprApVnicTemplateTarget,
    cfprApVnicLanConnTemplTemplType                                  CfprApVnicTemplateType
}

cfprApVnicLanConnTemplInstanceId OBJECT-TYPE
    SYNTAX       CfprApManagedObjectId
    MAX-ACCESS   not-accessible
    STATUS       current
    DESCRIPTION
        "Instance identifier of the managed object."
    ::= { cfprApVnicLanConnTemplEntry 1 }

cfprApVnicLanConnTemplDn OBJECT-TYPE
    SYNTAX       CfprApManagedObjectDn
    MAX-ACCESS   read-only
    STATUS       current
    DESCRIPTION
        "Cisco Firepower vnic:LanConnTempl:dn managed object property"
    ::= { cfprApVnicLanConnTemplEntry 2 }

cfprApVnicLanConnTemplRn OBJECT-TYPE
    SYNTAX       SnmpAdminString
    MAX-ACCESS   read-only
    STATUS       current
    DESCRIPTION
        "Cisco Firepower vnic:LanConnTempl:rn managed object property"
    ::= { cfprApVnicLanConnTemplEntry 3 }

cfprApVnicLanConnTemplDescr OBJECT-TYPE
    SYNTAX       SnmpAdminString
    MAX-ACCESS   read-only
    STATUS       current
    DESCRIPTION
        "Cisco Firepower vnic:LanConnTempl:descr managed object property"
    ::= { cfprApVnicLanConnTemplEntry 4 }

cfprApVnicLanConnTemplIdentPoolName OBJECT-TYPE
    SYNTAX       SnmpAdminString
    MAX-ACCESS   read-only
    STATUS       current
    DESCRIPTION
        "Cisco Firepower vnic:LanConnTempl:identPoolName
        managed object property"
    ::= { cfprApVnicLanConnTemplEntry 5 }

cfprApVnicLanConnTemplIntId OBJECT-TYPE
    SYNTAX       SnmpAdminString
    MAX-ACCESS   read-only
    STATUS       current
    DESCRIPTION
        "Cisco Firepower vnic:LanConnTempl:intId managed object property"
    ::= { cfprApVnicLanConnTemplEntry 6 }

cfprApVnicLanConnTemplMtu OBJECT-TYPE
    SYNTAX       Gauge32
    MAX-ACCESS   read-only
    STATUS       current
    DESCRIPTION
        "Cisco Firepower vnic:LanConnTempl:mtu managed object property"
    ::= { cfprApVnicLanConnTemplEntry 7 }

cfprApVnicLanConnTemplName OBJECT-TYPE
    SYNTAX       SnmpAdminString
    MAX-ACCESS   read-only
    STATUS       current
    DESCRIPTION
        "Cisco Firepower vnic:LanConnTempl:name managed object property"
    ::= { cfprApVnicLanConnTemplEntry 8 }

cfprApVnicLanConnTemplNwCtrlPolicyName OBJECT-TYPE
    SYNTAX       SnmpAdminString
    MAX-ACCESS   read-only
    STATUS       current
    DESCRIPTION
        "Cisco Firepower vnic:LanConnTempl:nwCtrlPolicyName
        managed object property"
    ::= { cfprApVnicLanConnTemplEntry 9 }

cfprApVnicLanConnTemplOperIdentPoolName OBJECT-TYPE
    SYNTAX       SnmpAdminString
    MAX-ACCESS   read-only
    STATUS       current
    DESCRIPTION
        "Cisco Firepower vnic:LanConnTempl:operIdentPoolName
        managed object property"
    ::= { cfprApVnicLanConnTemplEntry 10 }

cfprApVnicLanConnTemplOperNwCtrlPolicyName OBJECT-TYPE
    SYNTAX       SnmpAdminString
    MAX-ACCESS   read-only
    STATUS       current
    DESCRIPTION
        "Cisco Firepower vnic:LanConnTempl:operNwCtrlPolicyName
        managed object property"
    ::= { cfprApVnicLanConnTemplEntry 11 }

cfprApVnicLanConnTemplOperQosPolicyName OBJECT-TYPE
    SYNTAX       SnmpAdminString
    MAX-ACCESS   read-only
    STATUS       current
    DESCRIPTION
        "Cisco Firepower vnic:LanConnTempl:operQosPolicyName
        managed object property"
    ::= { cfprApVnicLanConnTemplEntry 12 }

cfprApVnicLanConnTemplOperStatsPolicyName OBJECT-TYPE
    SYNTAX       SnmpAdminString
    MAX-ACCESS   read-only
    STATUS       current
    DESCRIPTION
        "Cisco Firepower vnic:LanConnTempl:operStatsPolicyName
        managed object property"
    ::= { cfprApVnicLanConnTemplEntry 13 }

cfprApVnicLanConnTemplPinToGroupName OBJECT-TYPE
    SYNTAX       SnmpAdminString
    MAX-ACCESS   read-only
    STATUS       current
    DESCRIPTION
        "Cisco Firepower vnic:LanConnTempl:pinToGroupName
        managed object property"
    ::= { cfprApVnicLanConnTemplEntry 14 }

cfprApVnicLanConnTemplPolicyLevel OBJECT-TYPE
    SYNTAX       Gauge32
    MAX-ACCESS   read-only
    STATUS       current
    DESCRIPTION
        "Cisco Firepower vnic:LanConnTempl:policyLevel
        managed object property"
    ::= { cfprApVnicLanConnTemplEntry 15 }

cfprApVnicLanConnTemplPolicyOwner OBJECT-TYPE
    SYNTAX       CfprApPolicyPolicyOwner
    MAX-ACCESS   read-only
    STATUS       current
    DESCRIPTION
        "Cisco Firepower vnic:LanConnTempl:policyOwner
        managed object property"
    ::= { cfprApVnicLanConnTemplEntry 16 }

cfprApVnicLanConnTemplQosPolicyName OBJECT-TYPE
    SYNTAX       SnmpAdminString
    MAX-ACCESS   read-only
    STATUS       current
    DESCRIPTION
        "Cisco Firepower vnic:LanConnTempl:qosPolicyName
        managed object property"
    ::= { cfprApVnicLanConnTemplEntry 17 }

cfprApVnicLanConnTemplStatsPolicyName OBJECT-TYPE
    SYNTAX       SnmpAdminString
    MAX-ACCESS   read-only
    STATUS       current
    DESCRIPTION
        "Cisco Firepower vnic:LanConnTempl:statsPolicyName
        managed object property"
    ::= { cfprApVnicLanConnTemplEntry 18 }

cfprApVnicLanConnTemplSwitchId OBJECT-TYPE
    SYNTAX       CfprApVnicLanConnTemplSwitchId
    MAX-ACCESS   read-only
    STATUS       current
    DESCRIPTION
        "Cisco Firepower vnic:LanConnTempl:switchId managed
        object property"
    ::= { cfprApVnicLanConnTemplEntry 19 }

cfprApVnicLanConnTemplTarget OBJECT-TYPE
    SYNTAX       CfprApVnicTemplateTarget
    MAX-ACCESS   read-only
    STATUS       current
    DESCRIPTION
        "Cisco Firepower vnic:LanConnTempl:target managed object property"
    ::= { cfprApVnicLanConnTemplEntry 20 }

cfprApVnicLanConnTemplTemplType OBJECT-TYPE
    SYNTAX       CfprApVnicTemplateType
    MAX-ACCESS   read-only
    STATUS       current
    DESCRIPTION
        "Cisco Firepower vnic:LanConnTempl:templType managed
        object property"
    ::= { cfprApVnicLanConnTemplEntry 21 }

cfprApVnicLifVlanTable OBJECT-TYPE
    SYNTAX           SEQUENCE OF CfprApVnicLifVlanEntry
    MAX-ACCESS       not-accessible
    STATUS           current
    DESCRIPTION
        "Cisco Firepower vnic:LifVlan managed object table"
    ::= { cfprApVnicObjects 48 }

cfprApVnicLifVlanEntry OBJECT-TYPE
    SYNTAX           CfprApVnicLifVlanEntry
    MAX-ACCESS       not-accessible
    STATUS           current
    DESCRIPTION
        "Entry for the cfprApVnicLifVlanTable table."
    INDEX { cfprApVnicLifVlanInstanceId }
    ::= { cfprApVnicLifVlanTable 1 }

CfprApVnicLifVlanEntry ::= SEQUENCE {
    cfprApVnicLifVlanInstanceId                                      CfprApManagedObjectId,
    cfprApVnicLifVlanDn                                              CfprApManagedObjectDn,
    cfprApVnicLifVlanRn                                              SnmpAdminString,
    cfprApVnicLifVlanAddr                                            MacAddress,
    cfprApVnicLifVlanConfigQualifier                                 CfprApVnicConfigIssues,
    cfprApVnicLifVlanDefaultNet                                      TruthValue,
    cfprApVnicLifVlanName                                            SnmpAdminString,
    cfprApVnicLifVlanOperState                                       CfprApVnicIfOperState,
    cfprApVnicLifVlanOperVnetDn                                      SnmpAdminString,
    cfprApVnicLifVlanOperVnetName                                    SnmpAdminString,
    cfprApVnicLifVlanOwner                                           CfprApVnicConnectionOwner,
    cfprApVnicLifVlanPubNwId                                         Gauge32,
    cfprApVnicLifVlanSharing                                         CfprApFabricVlanSharingType,
    cfprApVnicLifVlanSwitchId                                        CfprApVnicL2IfSwitchId,
    cfprApVnicLifVlanType                                            CfprApVnicAEtherIfType,
    cfprApVnicLifVlanVnet                                            Gauge32
}

cfprApVnicLifVlanInstanceId OBJECT-TYPE
    SYNTAX       CfprApManagedObjectId
    MAX-ACCESS   not-accessible
    STATUS       current
    DESCRIPTION
        "Instance identifier of the managed object."
    ::= { cfprApVnicLifVlanEntry 1 }

cfprApVnicLifVlanDn OBJECT-TYPE
    SYNTAX       CfprApManagedObjectDn
    MAX-ACCESS   read-only
    STATUS       current
    DESCRIPTION
        "Cisco Firepower vnic:LifVlan:dn managed object property"
    ::= { cfprApVnicLifVlanEntry 2 }

cfprApVnicLifVlanRn OBJECT-TYPE
    SYNTAX       SnmpAdminString
    MAX-ACCESS   read-only
    STATUS       current
    DESCRIPTION
        "Cisco Firepower vnic:LifVlan:rn managed object property"
    ::= { cfprApVnicLifVlanEntry 3 }

cfprApVnicLifVlanAddr OBJECT-TYPE
    SYNTAX       MacAddress
    MAX-ACCESS   read-only
    STATUS       current
    DESCRIPTION
        "Cisco Firepower vnic:LifVlan:addr managed object property"
    ::= { cfprApVnicLifVlanEntry 4 }

cfprApVnicLifVlanConfigQualifier OBJECT-TYPE
    SYNTAX       CfprApVnicConfigIssues
    MAX-ACCESS   read-only
    STATUS       current
    DESCRIPTION
        "Cisco Firepower vnic:LifVlan:configQualifier managed
        object property"
    ::= { cfprApVnicLifVlanEntry 5 }

cfprApVnicLifVlanDefaultNet OBJECT-TYPE
    SYNTAX       TruthValue
    MAX-ACCESS   read-only
    STATUS       current
    DESCRIPTION
        "Cisco Firepower vnic:LifVlan:defaultNet managed object property"
    ::= { cfprApVnicLifVlanEntry 6 }

cfprApVnicLifVlanName OBJECT-TYPE
    SYNTAX       SnmpAdminString
    MAX-ACCESS   read-only
    STATUS       current
    DESCRIPTION
        "Cisco Firepower vnic:LifVlan:name managed object property"
    ::= { cfprApVnicLifVlanEntry 7 }

cfprApVnicLifVlanOperState OBJECT-TYPE
    SYNTAX       CfprApVnicIfOperState
    MAX-ACCESS   read-only
    STATUS       current
    DESCRIPTION
        "Cisco Firepower vnic:LifVlan:operState managed object property"
    ::= { cfprApVnicLifVlanEntry 8 }

cfprApVnicLifVlanOperVnetDn OBJECT-TYPE
    SYNTAX       SnmpAdminString
    MAX-ACCESS   read-only
    STATUS       current
    DESCRIPTION
        "Cisco Firepower vnic:LifVlan:operVnetDn managed object property"
    ::= { cfprApVnicLifVlanEntry 9 }

cfprApVnicLifVlanOperVnetName OBJECT-TYPE
    SYNTAX       SnmpAdminString
    MAX-ACCESS   read-only
    STATUS       current
    DESCRIPTION
        "Cisco Firepower vnic:LifVlan:operVnetName managed
        object property"
    ::= { cfprApVnicLifVlanEntry 10 }

cfprApVnicLifVlanOwner OBJECT-TYPE
    SYNTAX       CfprApVnicConnectionOwner
    MAX-ACCESS   read-only
    STATUS       current
    DESCRIPTION
        "Cisco Firepower vnic:LifVlan:owner managed object property"
    ::= { cfprApVnicLifVlanEntry 11 }

cfprApVnicLifVlanPubNwId OBJECT-TYPE
    SYNTAX       Gauge32
    MAX-ACCESS   read-only
    STATUS       current
    DESCRIPTION
        "Cisco Firepower vnic:LifVlan:pubNwId managed object property"
    ::= { cfprApVnicLifVlanEntry 12 }

cfprApVnicLifVlanSharing OBJECT-TYPE
    SYNTAX       CfprApFabricVlanSharingType
    MAX-ACCESS   read-only
    STATUS       current
    DESCRIPTION
        "Cisco Firepower vnic:LifVlan:sharing managed object property"
    ::= { cfprApVnicLifVlanEntry 13 }

cfprApVnicLifVlanSwitchId OBJECT-TYPE
    SYNTAX       CfprApVnicL2IfSwitchId
    MAX-ACCESS   read-only
    STATUS       current
    DESCRIPTION
        "Cisco Firepower vnic:LifVlan:switchId managed object property"
    ::= { cfprApVnicLifVlanEntry 14 }

cfprApVnicLifVlanType OBJECT-TYPE
    SYNTAX       CfprApVnicAEtherIfType
    MAX-ACCESS   read-only
    STATUS       current
    DESCRIPTION
        "Cisco Firepower vnic:LifVlan:type managed object property"
    ::= { cfprApVnicLifVlanEntry 15 }

cfprApVnicLifVlanVnet OBJECT-TYPE
    SYNTAX       Gauge32
    MAX-ACCESS   read-only
    STATUS       current
    DESCRIPTION
        "Cisco Firepower vnic:LifVlan:vnet managed object property"
    ::= { cfprApVnicLifVlanEntry 16 }

cfprApVnicLifVsanTable OBJECT-TYPE
    SYNTAX           SEQUENCE OF CfprApVnicLifVsanEntry
    MAX-ACCESS       not-accessible
    STATUS           current
    DESCRIPTION
        "Cisco Firepower vnic:LifVsan managed object table"
    ::= { cfprApVnicObjects 49 }

cfprApVnicLifVsanEntry OBJECT-TYPE
    SYNTAX           CfprApVnicLifVsanEntry
    MAX-ACCESS       not-accessible
    STATUS           current
    DESCRIPTION
        "Entry for the cfprApVnicLifVsanTable table."
    INDEX { cfprApVnicLifVsanInstanceId }
    ::= { cfprApVnicLifVsanTable 1 }

CfprApVnicLifVsanEntry ::= SEQUENCE {
    cfprApVnicLifVsanInstanceId                                      CfprApManagedObjectId,
    cfprApVnicLifVsanDn                                              CfprApManagedObjectDn,
    cfprApVnicLifVsanRn                                              SnmpAdminString,
    cfprApVnicLifVsanConfigQualifier                                 CfprApVnicConfigIssues,
    cfprApVnicLifVsanInitiator                                       Unsigned64,
    cfprApVnicLifVsanName                                            SnmpAdminString,
    cfprApVnicLifVsanOperState                                       CfprApVnicIfOperState,
    cfprApVnicLifVsanOperVnetDn                                      SnmpAdminString,
    cfprApVnicLifVsanOperVnetName                                    SnmpAdminString,
    cfprApVnicLifVsanOwner                                           CfprApVnicConnectionOwner,
    cfprApVnicLifVsanPubNwId                                         Gauge32,
    cfprApVnicLifVsanSharing                                         CfprApFabricVlanSharingType,
    cfprApVnicLifVsanSwitchId                                        CfprApVnicL2IfSwitchId,
    cfprApVnicLifVsanType                                            CfprApVnicAFcIfType,
    cfprApVnicLifVsanVnet                                            Gauge32
}

cfprApVnicLifVsanInstanceId OBJECT-TYPE
    SYNTAX       CfprApManagedObjectId
    MAX-ACCESS   not-accessible
    STATUS       current
    DESCRIPTION
        "Instance identifier of the managed object."
    ::= { cfprApVnicLifVsanEntry 1 }

cfprApVnicLifVsanDn OBJECT-TYPE
    SYNTAX       CfprApManagedObjectDn
    MAX-ACCESS   read-only
    STATUS       current
    DESCRIPTION
        "Cisco Firepower vnic:LifVsan:dn managed object property"
    ::= { cfprApVnicLifVsanEntry 2 }

cfprApVnicLifVsanRn OBJECT-TYPE
    SYNTAX       SnmpAdminString
    MAX-ACCESS   read-only
    STATUS       current
    DESCRIPTION
        "Cisco Firepower vnic:LifVsan:rn managed object property"
    ::= { cfprApVnicLifVsanEntry 3 }

cfprApVnicLifVsanConfigQualifier OBJECT-TYPE
    SYNTAX       CfprApVnicConfigIssues
    MAX-ACCESS   read-only
    STATUS       current
    DESCRIPTION
        "Cisco Firepower vnic:LifVsan:configQualifier managed
        object property"
    ::= { cfprApVnicLifVsanEntry 4 }

cfprApVnicLifVsanInitiator OBJECT-TYPE
    SYNTAX       Unsigned64
    MAX-ACCESS   read-only
    STATUS       current
    DESCRIPTION
        "Cisco Firepower vnic:LifVsan:initiator managed object property"
    ::= { cfprApVnicLifVsanEntry 5 }

cfprApVnicLifVsanName OBJECT-TYPE
    SYNTAX       SnmpAdminString
    MAX-ACCESS   read-only
    STATUS       current
    DESCRIPTION
        "Cisco Firepower vnic:LifVsan:name managed object property"
    ::= { cfprApVnicLifVsanEntry 6 }

cfprApVnicLifVsanOperState OBJECT-TYPE
    SYNTAX       CfprApVnicIfOperState
    MAX-ACCESS   read-only
    STATUS       current
    DESCRIPTION
        "Cisco Firepower vnic:LifVsan:operState managed object property"
    ::= { cfprApVnicLifVsanEntry 7 }

cfprApVnicLifVsanOperVnetDn OBJECT-TYPE
    SYNTAX       SnmpAdminString
    MAX-ACCESS   read-only
    STATUS       current
    DESCRIPTION
        "Cisco Firepower vnic:LifVsan:operVnetDn managed object property"
    ::= { cfprApVnicLifVsanEntry 8 }

cfprApVnicLifVsanOperVnetName OBJECT-TYPE
    SYNTAX       SnmpAdminString
    MAX-ACCESS   read-only
    STATUS       current
    DESCRIPTION
        "Cisco Firepower vnic:LifVsan:operVnetName managed
        object property"
    ::= { cfprApVnicLifVsanEntry 9 }

cfprApVnicLifVsanOwner OBJECT-TYPE
    SYNTAX       CfprApVnicConnectionOwner
    MAX-ACCESS   read-only
    STATUS       current
    DESCRIPTION
        "Cisco Firepower vnic:LifVsan:owner managed object property"
    ::= { cfprApVnicLifVsanEntry 10 }

cfprApVnicLifVsanPubNwId OBJECT-TYPE
    SYNTAX       Gauge32
    MAX-ACCESS   read-only
    STATUS       current
    DESCRIPTION
        "Cisco Firepower vnic:LifVsan:pubNwId managed object property"
    ::= { cfprApVnicLifVsanEntry 11 }

cfprApVnicLifVsanSharing OBJECT-TYPE
    SYNTAX       CfprApFabricVlanSharingType
    MAX-ACCESS   read-only
    STATUS       current
    DESCRIPTION
        "Cisco Firepower vnic:LifVsan:sharing managed object property"
    ::= { cfprApVnicLifVsanEntry 12 }

cfprApVnicLifVsanSwitchId OBJECT-TYPE
    SYNTAX       CfprApVnicL2IfSwitchId
    MAX-ACCESS   read-only
    STATUS       current
    DESCRIPTION
        "Cisco Firepower vnic:LifVsan:switchId managed object property"
    ::= { cfprApVnicLifVsanEntry 13 }

cfprApVnicLifVsanType OBJECT-TYPE
    SYNTAX       CfprApVnicAFcIfType
    MAX-ACCESS   read-only
    STATUS       current
    DESCRIPTION
        "Cisco Firepower vnic:LifVsan:type managed object property"
    ::= { cfprApVnicLifVsanEntry 14 }

cfprApVnicLifVsanVnet OBJECT-TYPE
    SYNTAX       Gauge32
    MAX-ACCESS   read-only
    STATUS       current
    DESCRIPTION
        "Cisco Firepower vnic:LifVsan:vnet managed object property"
    ::= { cfprApVnicLifVsanEntry 15 }

cfprApVnicLunTable OBJECT-TYPE
    SYNTAX           SEQUENCE OF CfprApVnicLunEntry
    MAX-ACCESS       not-accessible
    STATUS           current
    DESCRIPTION
        "Cisco Firepower vnic:Lun managed object table"
    ::= { cfprApVnicObjects 50 }

cfprApVnicLunEntry OBJECT-TYPE
    SYNTAX           CfprApVnicLunEntry
    MAX-ACCESS       not-accessible
    STATUS           current
    DESCRIPTION
        "Entry for the cfprApVnicLunTable table."
    INDEX { cfprApVnicLunInstanceId }
    ::= { cfprApVnicLunTable 1 }

CfprApVnicLunEntry ::= SEQUENCE {
    cfprApVnicLunInstanceId                                          CfprApManagedObjectId,
    cfprApVnicLunDn                                                  CfprApManagedObjectDn,
    cfprApVnicLunRn                                                  SnmpAdminString,
    cfprApVnicLunBootable                                            TruthValue,
    cfprApVnicLunId                                                  CfprApVnicLunId
}

cfprApVnicLunInstanceId OBJECT-TYPE
    SYNTAX       CfprApManagedObjectId
    MAX-ACCESS   not-accessible
    STATUS       current
    DESCRIPTION
        "Instance identifier of the managed object."
    ::= { cfprApVnicLunEntry 1 }

cfprApVnicLunDn OBJECT-TYPE
    SYNTAX       CfprApManagedObjectDn
    MAX-ACCESS   read-only
    STATUS       current
    DESCRIPTION
        "Cisco Firepower vnic:Lun:dn managed object property"
    ::= { cfprApVnicLunEntry 2 }

cfprApVnicLunRn OBJECT-TYPE
    SYNTAX       SnmpAdminString
    MAX-ACCESS   read-only
    STATUS       current
    DESCRIPTION
        "Cisco Firepower vnic:Lun:rn managed object property"
    ::= { cfprApVnicLunEntry 3 }

cfprApVnicLunBootable OBJECT-TYPE
    SYNTAX       TruthValue
    MAX-ACCESS   read-only
    STATUS       current
    DESCRIPTION
        "Cisco Firepower vnic:Lun:bootable managed object property"
    ::= { cfprApVnicLunEntry 4 }

cfprApVnicLunId OBJECT-TYPE
    SYNTAX       CfprApVnicLunId
    MAX-ACCESS   read-only
    STATUS       current
    DESCRIPTION
        "Cisco Firepower vnic:Lun:id managed object property"
    ::= { cfprApVnicLunEntry 5 }

cfprApVnicMacHistoryTable OBJECT-TYPE
    SYNTAX           SEQUENCE OF CfprApVnicMacHistoryEntry
    MAX-ACCESS       not-accessible
    STATUS           current
    DESCRIPTION
        "Cisco Firepower vnic:MacHistory managed object table"
    ::= { cfprApVnicObjects 51 }

cfprApVnicMacHistoryEntry OBJECT-TYPE
    SYNTAX           CfprApVnicMacHistoryEntry
    MAX-ACCESS       not-accessible
    STATUS           current
    DESCRIPTION
        "Entry for the cfprApVnicMacHistoryTable table."
    INDEX { cfprApVnicMacHistoryInstanceId }
    ::= { cfprApVnicMacHistoryTable 1 }

CfprApVnicMacHistoryEntry ::= SEQUENCE {
    cfprApVnicMacHistoryInstanceId                                   CfprApManagedObjectId,
    cfprApVnicMacHistoryDn                                           CfprApManagedObjectDn,
    cfprApVnicMacHistoryRn                                           SnmpAdminString,
    cfprApVnicMacHistoryOldaddr                                      MacAddress
}

cfprApVnicMacHistoryInstanceId OBJECT-TYPE
    SYNTAX       CfprApManagedObjectId
    MAX-ACCESS   not-accessible
    STATUS       current
    DESCRIPTION
        "Instance identifier of the managed object."
    ::= { cfprApVnicMacHistoryEntry 1 }

cfprApVnicMacHistoryDn OBJECT-TYPE
    SYNTAX       CfprApManagedObjectDn
    MAX-ACCESS   read-only
    STATUS       current
    DESCRIPTION
        "Cisco Firepower vnic:MacHistory:dn managed object property"
    ::= { cfprApVnicMacHistoryEntry 2 }

cfprApVnicMacHistoryRn OBJECT-TYPE
    SYNTAX       SnmpAdminString
    MAX-ACCESS   read-only
    STATUS       current
    DESCRIPTION
        "Cisco Firepower vnic:MacHistory:rn managed object property"
    ::= { cfprApVnicMacHistoryEntry 3 }

cfprApVnicMacHistoryOldaddr OBJECT-TYPE
    SYNTAX       MacAddress
    MAX-ACCESS   read-only
    STATUS       current
    DESCRIPTION
        "Cisco Firepower vnic:MacHistory:oldaddr managed object property"
    ::= { cfprApVnicMacHistoryEntry 4 }

cfprApVnicOProfileAliasTable OBJECT-TYPE
    SYNTAX           SEQUENCE OF CfprApVnicOProfileAliasEntry
    MAX-ACCESS       not-accessible
    STATUS           current
    DESCRIPTION
        "Cisco Firepower vnic:OProfileAlias managed object table"
    ::= { cfprApVnicObjects 52 }

cfprApVnicOProfileAliasEntry OBJECT-TYPE
    SYNTAX           CfprApVnicOProfileAliasEntry
    MAX-ACCESS       not-accessible
    STATUS           current
    DESCRIPTION
        "Entry for the cfprApVnicOProfileAliasTable table."
    INDEX { cfprApVnicOProfileAliasInstanceId }
    ::= { cfprApVnicOProfileAliasTable 1 }

CfprApVnicOProfileAliasEntry ::= SEQUENCE {
    cfprApVnicOProfileAliasInstanceId                                CfprApManagedObjectId,
    cfprApVnicOProfileAliasDn                                        CfprApManagedObjectDn,
    cfprApVnicOProfileAliasRn                                        SnmpAdminString,
    cfprApVnicOProfileAliasAlias                                     SnmpAdminString,
    cfprApVnicOProfileAliasMgmtPlane                                 CfprApVmMgmtPlane,
    cfprApVnicOProfileAliasVSwitchId                                 SnmpAdminString,
    cfprApVnicOProfileAliasVSwitchName                               SnmpAdminString
}

cfprApVnicOProfileAliasInstanceId OBJECT-TYPE
    SYNTAX       CfprApManagedObjectId
    MAX-ACCESS   not-accessible
    STATUS       current
    DESCRIPTION
        "Instance identifier of the managed object."
    ::= { cfprApVnicOProfileAliasEntry 1 }

cfprApVnicOProfileAliasDn OBJECT-TYPE
    SYNTAX       CfprApManagedObjectDn
    MAX-ACCESS   read-only
    STATUS       current
    DESCRIPTION
        "Cisco Firepower vnic:OProfileAlias:dn managed object property"
    ::= { cfprApVnicOProfileAliasEntry 2 }

cfprApVnicOProfileAliasRn OBJECT-TYPE
    SYNTAX       SnmpAdminString
    MAX-ACCESS   read-only
    STATUS       current
    DESCRIPTION
        "Cisco Firepower vnic:OProfileAlias:rn managed object property"
    ::= { cfprApVnicOProfileAliasEntry 3 }

cfprApVnicOProfileAliasAlias OBJECT-TYPE
    SYNTAX       SnmpAdminString
    MAX-ACCESS   read-only
    STATUS       current
    DESCRIPTION
        "Cisco Firepower vnic:OProfileAlias:alias managed object property"
    ::= { cfprApVnicOProfileAliasEntry 4 }

cfprApVnicOProfileAliasMgmtPlane OBJECT-TYPE
    SYNTAX       CfprApVmMgmtPlane
    MAX-ACCESS   read-only
    STATUS       current
    DESCRIPTION
        "Cisco Firepower vnic:OProfileAlias:mgmtPlane managed
        object property"
    ::= { cfprApVnicOProfileAliasEntry 5 }

cfprApVnicOProfileAliasVSwitchId OBJECT-TYPE
    SYNTAX       SnmpAdminString
    MAX-ACCESS   read-only
    STATUS       current
    DESCRIPTION
        "Cisco Firepower vnic:OProfileAlias:vSwitchId managed
        object property"
    ::= { cfprApVnicOProfileAliasEntry 6 }

cfprApVnicOProfileAliasVSwitchName OBJECT-TYPE
    SYNTAX       SnmpAdminString
    MAX-ACCESS   read-only
    STATUS       current
    DESCRIPTION
        "Cisco Firepower vnic:OProfileAlias:vSwitchName
        managed object property"
    ::= { cfprApVnicOProfileAliasEntry 7 }

cfprApVnicProfileTable OBJECT-TYPE
    SYNTAX           SEQUENCE OF CfprApVnicProfileEntry
    MAX-ACCESS       not-accessible
    STATUS           current
    DESCRIPTION
        "Cisco Firepower vnic:Profile managed object table"
    ::= { cfprApVnicObjects 53 }

cfprApVnicProfileEntry OBJECT-TYPE
    SYNTAX           CfprApVnicProfileEntry
    MAX-ACCESS       not-accessible
    STATUS           current
    DESCRIPTION
        "Entry for the cfprApVnicProfileTable table."
    INDEX { cfprApVnicProfileInstanceId }
    ::= { cfprApVnicProfileTable 1 }

CfprApVnicProfileEntry ::= SEQUENCE {
    cfprApVnicProfileInstanceId                                      CfprApManagedObjectId,
    cfprApVnicProfileDn                                              CfprApManagedObjectDn,
    cfprApVnicProfileRn                                              SnmpAdminString,
    cfprApVnicProfileCdp                                             CfprApNwctrlAdminState,
    cfprApVnicProfileConfigQualifier                                 CfprApVnicProfileConfigQualifier,
    cfprApVnicProfileCos                                             Gauge32,
    cfprApVnicProfileDescr                                           SnmpAdminString,
    cfprApVnicProfileForgeMac                                        CfprApDpsecForgedTransmit,
    cfprApVnicProfileHostNwIOPerf                                    CfprApVnicHostNwIOPerfPref,
    cfprApVnicProfileIntId                                           SnmpAdminString,
    cfprApVnicProfileMacRegisterMode                                 CfprApNwctrlRegistrationMode,
    cfprApVnicProfileMaxPorts                                        Gauge32,
    cfprApVnicProfileName                                            SnmpAdminString,
    cfprApVnicProfileNwCtrlPolicyName                                SnmpAdminString,
    cfprApVnicProfileOperNwCtrlPolicyName                            SnmpAdminString,
    cfprApVnicProfileOperQosPolicyName                               SnmpAdminString,
    cfprApVnicProfilePinToGroupName                                  SnmpAdminString,
    cfprApVnicProfilePolicyLevel                                     Gauge32,
    cfprApVnicProfilePolicyOwner                                     CfprApPolicyPolicyOwner,
    cfprApVnicProfilePortProfileUuid                                 SnmpAdminString,
    cfprApVnicProfilePrimaryVlanId                                   Gauge32,
    cfprApVnicProfileQosPolicyDn                                     SnmpAdminString,
    cfprApVnicProfileQosPolicyId                                     SnmpAdminString,
    cfprApVnicProfileQosPolicyName                                   SnmpAdminString,
    cfprApVnicProfileSwABorderAggrPort                               Gauge32,
    cfprApVnicProfileSwABorderPort                                   Gauge32,
    cfprApVnicProfileSwABorderSlot                                   Gauge32,
    cfprApVnicProfileSwBBorderAggrPort                               Gauge32,
    cfprApVnicProfileSwBBorderPort                                   Gauge32,
    cfprApVnicProfileSwBBorderSlot                                   Gauge32,
    cfprApVnicProfileType                                            CfprApVnicPortProfileType,
    cfprApVnicProfileUplinkFailAction                                CfprApNwctrlLinkFailAction
}

cfprApVnicProfileInstanceId OBJECT-TYPE
    SYNTAX       CfprApManagedObjectId
    MAX-ACCESS   not-accessible
    STATUS       current
    DESCRIPTION
        "Instance identifier of the managed object."
    ::= { cfprApVnicProfileEntry 1 }

cfprApVnicProfileDn OBJECT-TYPE
    SYNTAX       CfprApManagedObjectDn
    MAX-ACCESS   read-only
    STATUS       current
    DESCRIPTION
        "Cisco Firepower vnic:Profile:dn managed object property"
    ::= { cfprApVnicProfileEntry 2 }

cfprApVnicProfileRn OBJECT-TYPE
    SYNTAX       SnmpAdminString
    MAX-ACCESS   read-only
    STATUS       current
    DESCRIPTION
        "Cisco Firepower vnic:Profile:rn managed object property"
    ::= { cfprApVnicProfileEntry 3 }

cfprApVnicProfileCdp OBJECT-TYPE
    SYNTAX       CfprApNwctrlAdminState
    MAX-ACCESS   read-only
    STATUS       current
    DESCRIPTION
        "Cisco Firepower vnic:Profile:cdp managed object property"
    ::= { cfprApVnicProfileEntry 4 }

cfprApVnicProfileConfigQualifier OBJECT-TYPE
    SYNTAX       CfprApVnicProfileConfigQualifier
    MAX-ACCESS   read-only
    STATUS       current
    DESCRIPTION
        "Cisco Firepower vnic:Profile:configQualifier managed
        object property"
    ::= { cfprApVnicProfileEntry 5 }

cfprApVnicProfileCos OBJECT-TYPE
    SYNTAX       Gauge32
    MAX-ACCESS   read-only
    STATUS       current
    DESCRIPTION
        "Cisco Firepower vnic:Profile:cos managed object property"
    ::= { cfprApVnicProfileEntry 6 }

cfprApVnicProfileDescr OBJECT-TYPE
    SYNTAX       SnmpAdminString
    MAX-ACCESS   read-only
    STATUS       current
    DESCRIPTION
        "Cisco Firepower vnic:Profile:descr managed object property"
    ::= { cfprApVnicProfileEntry 7 }

cfprApVnicProfileForgeMac OBJECT-TYPE
    SYNTAX       CfprApDpsecForgedTransmit
    MAX-ACCESS   read-only
    STATUS       current
    DESCRIPTION
        "Cisco Firepower vnic:Profile:forgeMac managed object property"
    ::= { cfprApVnicProfileEntry 8 }

cfprApVnicProfileHostNwIOPerf OBJECT-TYPE
    SYNTAX       CfprApVnicHostNwIOPerfPref
    MAX-ACCESS   read-only
    STATUS       current
    DESCRIPTION
        "Cisco Firepower vnic:Profile:hostNwIOPerf managed
        object property"
    ::= { cfprApVnicProfileEntry 9 }

cfprApVnicProfileIntId OBJECT-TYPE
    SYNTAX       SnmpAdminString
    MAX-ACCESS   read-only
    STATUS       current
    DESCRIPTION
        "Cisco Firepower vnic:Profile:intId managed object property"
    ::= { cfprApVnicProfileEntry 10 }

cfprApVnicProfileMacRegisterMode OBJECT-TYPE
    SYNTAX       CfprApNwctrlRegistrationMode
    MAX-ACCESS   read-only
    STATUS       current
    DESCRIPTION
        "Cisco Firepower vnic:Profile:macRegisterMode managed
        object property"
    ::= { cfprApVnicProfileEntry 11 }

cfprApVnicProfileMaxPorts OBJECT-TYPE
    SYNTAX       Gauge32
    MAX-ACCESS   read-only
    STATUS       current
    DESCRIPTION
        "Cisco Firepower vnic:Profile:maxPorts managed object property"
    ::= { cfprApVnicProfileEntry 12 }

cfprApVnicProfileName OBJECT-TYPE
    SYNTAX       SnmpAdminString
    MAX-ACCESS   read-only
    STATUS       current
    DESCRIPTION
        "Cisco Firepower vnic:Profile:name managed object property"
    ::= { cfprApVnicProfileEntry 13 }

cfprApVnicProfileNwCtrlPolicyName OBJECT-TYPE
    SYNTAX       SnmpAdminString
    MAX-ACCESS   read-only
    STATUS       current
    DESCRIPTION
        "Cisco Firepower vnic:Profile:nwCtrlPolicyName
        managed object property"
    ::= { cfprApVnicProfileEntry 14 }

cfprApVnicProfileOperNwCtrlPolicyName OBJECT-TYPE
    SYNTAX       SnmpAdminString
    MAX-ACCESS   read-only
    STATUS       current
    DESCRIPTION
        "Cisco Firepower vnic:Profile:operNwCtrlPolicyName
        managed object property"
    ::= { cfprApVnicProfileEntry 15 }

cfprApVnicProfileOperQosPolicyName OBJECT-TYPE
    SYNTAX       SnmpAdminString
    MAX-ACCESS   read-only
    STATUS       current
    DESCRIPTION
        "Cisco Firepower vnic:Profile:operQosPolicyName
        managed object property"
    ::= { cfprApVnicProfileEntry 16 }

cfprApVnicProfilePinToGroupName OBJECT-TYPE
    SYNTAX       SnmpAdminString
    MAX-ACCESS   read-only
    STATUS       current
    DESCRIPTION
        "Cisco Firepower vnic:Profile:pinToGroupName managed
        object property"
    ::= { cfprApVnicProfileEntry 17 }

cfprApVnicProfilePolicyLevel OBJECT-TYPE
    SYNTAX       Gauge32
    MAX-ACCESS   read-only
    STATUS       current
    DESCRIPTION
        "Cisco Firepower vnic:Profile:policyLevel managed object property"
    ::= { cfprApVnicProfileEntry 18 }

cfprApVnicProfilePolicyOwner OBJECT-TYPE
    SYNTAX       CfprApPolicyPolicyOwner
    MAX-ACCESS   read-only
    STATUS       current
    DESCRIPTION
        "Cisco Firepower vnic:Profile:policyOwner managed object property"
    ::= { cfprApVnicProfileEntry 19 }

cfprApVnicProfilePortProfileUuid OBJECT-TYPE
    SYNTAX       SnmpAdminString
    MAX-ACCESS   read-only
    STATUS       current
    DESCRIPTION
        "Cisco Firepower vnic:Profile:portProfileUuid managed
        object property"
    ::= { cfprApVnicProfileEntry 20 }

cfprApVnicProfilePrimaryVlanId OBJECT-TYPE
    SYNTAX       Gauge32
    MAX-ACCESS   read-only
    STATUS       current
    DESCRIPTION
        "Cisco Firepower vnic:Profile:primaryVlanId managed
        object property"
    ::= { cfprApVnicProfileEntry 21 }

cfprApVnicProfileQosPolicyDn OBJECT-TYPE
    SYNTAX       SnmpAdminString
    MAX-ACCESS   read-only
    STATUS       current
    DESCRIPTION
        "Cisco Firepower vnic:Profile:qosPolicyDn managed object property"
    ::= { cfprApVnicProfileEntry 22 }

cfprApVnicProfileQosPolicyId OBJECT-TYPE
    SYNTAX       SnmpAdminString
    MAX-ACCESS   read-only
    STATUS       current
    DESCRIPTION
        "Cisco Firepower vnic:Profile:qosPolicyId managed object property"
    ::= { cfprApVnicProfileEntry 23 }

cfprApVnicProfileQosPolicyName OBJECT-TYPE
    SYNTAX       SnmpAdminString
    MAX-ACCESS   read-only
    STATUS       current
    DESCRIPTION
        "Cisco Firepower vnic:Profile:qosPolicyName managed
        object property"
    ::= { cfprApVnicProfileEntry 24 }

cfprApVnicProfileSwABorderAggrPort OBJECT-TYPE
    SYNTAX       Gauge32
    MAX-ACCESS   read-only
    STATUS       current
    DESCRIPTION
        "Cisco Firepower vnic:Profile:swABorderAggrPort
        managed object property"
    ::= { cfprApVnicProfileEntry 25 }

cfprApVnicProfileSwABorderPort OBJECT-TYPE
    SYNTAX       Gauge32
    MAX-ACCESS   read-only
    STATUS       current
    DESCRIPTION
        "Cisco Firepower vnic:Profile:swABorderPort managed
        object property"
    ::= { cfprApVnicProfileEntry 26 }

cfprApVnicProfileSwABorderSlot OBJECT-TYPE
    SYNTAX       Gauge32
    MAX-ACCESS   read-only
    STATUS       current
    DESCRIPTION
        "Cisco Firepower vnic:Profile:swABorderSlot managed
        object property"
    ::= { cfprApVnicProfileEntry 27 }

cfprApVnicProfileSwBBorderAggrPort OBJECT-TYPE
    SYNTAX       Gauge32
    MAX-ACCESS   read-only
    STATUS       current
    DESCRIPTION
        "Cisco Firepower vnic:Profile:swBBorderAggrPort
        managed object property"
    ::= { cfprApVnicProfileEntry 28 }

cfprApVnicProfileSwBBorderPort OBJECT-TYPE
    SYNTAX       Gauge32
    MAX-ACCESS   read-only
    STATUS       current
    DESCRIPTION
        "Cisco Firepower vnic:Profile:swBBorderPort managed
        object property"
    ::= { cfprApVnicProfileEntry 29 }

cfprApVnicProfileSwBBorderSlot OBJECT-TYPE
    SYNTAX       Gauge32
    MAX-ACCESS   read-only
    STATUS       current
    DESCRIPTION
        "Cisco Firepower vnic:Profile:swBBorderSlot managed
        object property"
    ::= { cfprApVnicProfileEntry 30 }

cfprApVnicProfileType OBJECT-TYPE
    SYNTAX       CfprApVnicPortProfileType
    MAX-ACCESS   read-only
    STATUS       current
    DESCRIPTION
        "Cisco Firepower vnic:Profile:type managed object property"
    ::= { cfprApVnicProfileEntry 31 }

cfprApVnicProfileUplinkFailAction OBJECT-TYPE
    SYNTAX       CfprApNwctrlLinkFailAction
    MAX-ACCESS   read-only
    STATUS       current
    DESCRIPTION
        "Cisco Firepower vnic:Profile:uplinkFailAction
        managed object property"
    ::= { cfprApVnicProfileEntry 32 }

cfprApVnicProfileAliasTable OBJECT-TYPE
    SYNTAX           SEQUENCE OF CfprApVnicProfileAliasEntry
    MAX-ACCESS       not-accessible
    STATUS           current
    DESCRIPTION
        "Cisco Firepower vnic:ProfileAlias managed object table"
    ::= { cfprApVnicObjects 54 }

cfprApVnicProfileAliasEntry OBJECT-TYPE
    SYNTAX           CfprApVnicProfileAliasEntry
    MAX-ACCESS       not-accessible
    STATUS           current
    DESCRIPTION
        "Entry for the cfprApVnicProfileAliasTable table."
    INDEX { cfprApVnicProfileAliasInstanceId }
    ::= { cfprApVnicProfileAliasTable 1 }

CfprApVnicProfileAliasEntry ::= SEQUENCE {
    cfprApVnicProfileAliasInstanceId                                 CfprApManagedObjectId,
    cfprApVnicProfileAliasDn                                         CfprApManagedObjectDn,
    cfprApVnicProfileAliasRn                                         SnmpAdminString,
    cfprApVnicProfileAliasAlias                                      SnmpAdminString,
    cfprApVnicProfileAliasSwUuid                                     SnmpAdminString
}

cfprApVnicProfileAliasInstanceId OBJECT-TYPE
    SYNTAX       CfprApManagedObjectId
    MAX-ACCESS   not-accessible
    STATUS       current
    DESCRIPTION
        "Instance identifier of the managed object."
    ::= { cfprApVnicProfileAliasEntry 1 }

cfprApVnicProfileAliasDn OBJECT-TYPE
    SYNTAX       CfprApManagedObjectDn
    MAX-ACCESS   read-only
    STATUS       current
    DESCRIPTION
        "Cisco Firepower vnic:ProfileAlias:dn managed object property"
    ::= { cfprApVnicProfileAliasEntry 2 }

cfprApVnicProfileAliasRn OBJECT-TYPE
    SYNTAX       SnmpAdminString
    MAX-ACCESS   read-only
    STATUS       current
    DESCRIPTION
        "Cisco Firepower vnic:ProfileAlias:rn managed object property"
    ::= { cfprApVnicProfileAliasEntry 3 }

cfprApVnicProfileAliasAlias OBJECT-TYPE
    SYNTAX       SnmpAdminString
    MAX-ACCESS   read-only
    STATUS       current
    DESCRIPTION
        "Cisco Firepower vnic:ProfileAlias:alias managed object property"
    ::= { cfprApVnicProfileAliasEntry 4 }

cfprApVnicProfileAliasSwUuid OBJECT-TYPE
    SYNTAX       SnmpAdminString
    MAX-ACCESS   read-only
    STATUS       current
    DESCRIPTION
        "Cisco Firepower vnic:ProfileAlias:swUuid managed object property"
    ::= { cfprApVnicProfileAliasEntry 5 }

cfprApVnicProfileRefTable OBJECT-TYPE
    SYNTAX           SEQUENCE OF CfprApVnicProfileRefEntry
    MAX-ACCESS       not-accessible
    STATUS           current
    DESCRIPTION
        "Cisco Firepower vnic:ProfileRef managed object table"
    ::= { cfprApVnicObjects 55 }

cfprApVnicProfileRefEntry OBJECT-TYPE
    SYNTAX           CfprApVnicProfileRefEntry
    MAX-ACCESS       not-accessible
    STATUS           current
    DESCRIPTION
        "Entry for the cfprApVnicProfileRefTable table."
    INDEX { cfprApVnicProfileRefInstanceId }
    ::= { cfprApVnicProfileRefTable 1 }

CfprApVnicProfileRefEntry ::= SEQUENCE {
    cfprApVnicProfileRefInstanceId                                   CfprApManagedObjectId,
    cfprApVnicProfileRefDn                                           CfprApManagedObjectDn,
    cfprApVnicProfileRefRn                                           SnmpAdminString,
    cfprApVnicProfileRefName                                         SnmpAdminString,
    cfprApVnicProfileRefSourceDn                                     SnmpAdminString
}

cfprApVnicProfileRefInstanceId OBJECT-TYPE
    SYNTAX       CfprApManagedObjectId
    MAX-ACCESS   not-accessible
    STATUS       current
    DESCRIPTION
        "Instance identifier of the managed object."
    ::= { cfprApVnicProfileRefEntry 1 }

cfprApVnicProfileRefDn OBJECT-TYPE
    SYNTAX       CfprApManagedObjectDn
    MAX-ACCESS   read-only
    STATUS       current
    DESCRIPTION
        "Cisco Firepower vnic:ProfileRef:dn managed object property"
    ::= { cfprApVnicProfileRefEntry 2 }

cfprApVnicProfileRefRn OBJECT-TYPE
    SYNTAX       SnmpAdminString
    MAX-ACCESS   read-only
    STATUS       current
    DESCRIPTION
        "Cisco Firepower vnic:ProfileRef:rn managed object property"
    ::= { cfprApVnicProfileRefEntry 3 }

cfprApVnicProfileRefName OBJECT-TYPE
    SYNTAX       SnmpAdminString
    MAX-ACCESS   read-only
    STATUS       current
    DESCRIPTION
        "Cisco Firepower vnic:ProfileRef:name managed object property"
    ::= { cfprApVnicProfileRefEntry 4 }

cfprApVnicProfileRefSourceDn OBJECT-TYPE
    SYNTAX       SnmpAdminString
    MAX-ACCESS   read-only
    STATUS       current
    DESCRIPTION
        "Cisco Firepower vnic:ProfileRef:sourceDn managed object property"
    ::= { cfprApVnicProfileRefEntry 5 }

cfprApVnicProfileSetTable OBJECT-TYPE
    SYNTAX           SEQUENCE OF CfprApVnicProfileSetEntry
    MAX-ACCESS       not-accessible
    STATUS           current
    DESCRIPTION
        "Cisco Firepower vnic:ProfileSet managed object table"
    ::= { cfprApVnicObjects 56 }

cfprApVnicProfileSetEntry OBJECT-TYPE
    SYNTAX           CfprApVnicProfileSetEntry
    MAX-ACCESS       not-accessible
    STATUS           current
    DESCRIPTION
        "Entry for the cfprApVnicProfileSetTable table."
    INDEX { cfprApVnicProfileSetInstanceId }
    ::= { cfprApVnicProfileSetTable 1 }

CfprApVnicProfileSetEntry ::= SEQUENCE {
    cfprApVnicProfileSetInstanceId                                   CfprApManagedObjectId,
    cfprApVnicProfileSetDn                                           CfprApManagedObjectDn,
    cfprApVnicProfileSetRn                                           SnmpAdminString,
    cfprApVnicProfileSetFltAggr                                      Unsigned64,
    cfprApVnicProfileSetGenNum                                       Gauge32
}

cfprApVnicProfileSetInstanceId OBJECT-TYPE
    SYNTAX       CfprApManagedObjectId
    MAX-ACCESS   not-accessible
    STATUS       current
    DESCRIPTION
        "Instance identifier of the managed object."
    ::= { cfprApVnicProfileSetEntry 1 }

cfprApVnicProfileSetDn OBJECT-TYPE
    SYNTAX       CfprApManagedObjectDn
    MAX-ACCESS   read-only
    STATUS       current
    DESCRIPTION
        "Cisco Firepower vnic:ProfileSet:dn managed object property"
    ::= { cfprApVnicProfileSetEntry 2 }

cfprApVnicProfileSetRn OBJECT-TYPE
    SYNTAX       SnmpAdminString
    MAX-ACCESS   read-only
    STATUS       current
    DESCRIPTION
        "Cisco Firepower vnic:ProfileSet:rn managed object property"
    ::= { cfprApVnicProfileSetEntry 3 }

cfprApVnicProfileSetFltAggr OBJECT-TYPE
    SYNTAX       Unsigned64
    MAX-ACCESS   read-only
    STATUS       current
    DESCRIPTION
        "Cisco Firepower vnic:ProfileSet:fltAggr managed object property"
    ::= { cfprApVnicProfileSetEntry 4 }

cfprApVnicProfileSetGenNum OBJECT-TYPE
    SYNTAX       Gauge32
    MAX-ACCESS   read-only
    STATUS       current
    DESCRIPTION
        "Cisco Firepower vnic:ProfileSet:genNum managed object property"
    ::= { cfprApVnicProfileSetEntry 5 }

cfprApVnicRackServerDiscoveryProfileTable OBJECT-TYPE
    SYNTAX           SEQUENCE OF CfprApVnicRackServerDiscoveryProfileEntry
    MAX-ACCESS       not-accessible
    STATUS           current
    DESCRIPTION
        "Cisco Firepower vnic:RackServerDiscoveryProfile
        managed object table"
    ::= { cfprApVnicObjects 57 }

cfprApVnicRackServerDiscoveryProfileEntry OBJECT-TYPE
    SYNTAX           CfprApVnicRackServerDiscoveryProfileEntry
    MAX-ACCESS       not-accessible
    STATUS           current
    DESCRIPTION
        "Entry for the cfprApVnicRackServerDiscoveryProfileTable table."
    INDEX { cfprApVnicRackServerDiscoveryProfileInstanceId }
    ::= { cfprApVnicRackServerDiscoveryProfileTable 1 }

CfprApVnicRackServerDiscoveryProfileEntry ::= SEQUENCE {
    cfprApVnicRackServerDiscoveryProfileInstanceId                   CfprApManagedObjectId,
    cfprApVnicRackServerDiscoveryProfileDn                           CfprApManagedObjectDn,
    cfprApVnicRackServerDiscoveryProfileRn                           SnmpAdminString,
    cfprApVnicRackServerDiscoveryProfileDescr                        SnmpAdminString,
    cfprApVnicRackServerDiscoveryProfileIntId                        SnmpAdminString,
    cfprApVnicRackServerDiscoveryProfileMaxPorts                     Gauge32,
    cfprApVnicRackServerDiscoveryProfileName                         SnmpAdminString,
    cfprApVnicRackServerDiscoveryProfilePolicyLevel                  Gauge32,
    cfprApVnicRackServerDiscoveryProfilePolicyOwner                  CfprApPolicyPolicyOwner
}

cfprApVnicRackServerDiscoveryProfileInstanceId OBJECT-TYPE
    SYNTAX       CfprApManagedObjectId
    MAX-ACCESS   not-accessible
    STATUS       current
    DESCRIPTION
        "Instance identifier of the managed object."
    ::= { cfprApVnicRackServerDiscoveryProfileEntry 1 }

cfprApVnicRackServerDiscoveryProfileDn OBJECT-TYPE
    SYNTAX       CfprApManagedObjectDn
    MAX-ACCESS   read-only
    STATUS       current
    DESCRIPTION
        "Cisco Firepower vnic:RackServerDiscoveryProfile:dn
        managed object property"
    ::= { cfprApVnicRackServerDiscoveryProfileEntry 2 }

cfprApVnicRackServerDiscoveryProfileRn OBJECT-TYPE
    SYNTAX       SnmpAdminString
    MAX-ACCESS   read-only
    STATUS       current
    DESCRIPTION
        "Cisco Firepower vnic:RackServerDiscoveryProfile:rn
        managed object property"
    ::= { cfprApVnicRackServerDiscoveryProfileEntry 3 }

cfprApVnicRackServerDiscoveryProfileDescr OBJECT-TYPE
    SYNTAX       SnmpAdminString
    MAX-ACCESS   read-only
    STATUS       current
    DESCRIPTION
        "Cisco Firepower vnic:RackServerDiscoveryProfile:descr
        managed object property"
    ::= { cfprApVnicRackServerDiscoveryProfileEntry 4 }

cfprApVnicRackServerDiscoveryProfileIntId OBJECT-TYPE
    SYNTAX       SnmpAdminString
    MAX-ACCESS   read-only
    STATUS       current
    DESCRIPTION
        "Cisco Firepower vnic:RackServerDiscoveryProfile:intId
        managed object property"
    ::= { cfprApVnicRackServerDiscoveryProfileEntry 5 }

cfprApVnicRackServerDiscoveryProfileMaxPorts OBJECT-TYPE
    SYNTAX       Gauge32
    MAX-ACCESS   read-only
    STATUS       current
    DESCRIPTION
        "Cisco Firepower vnic:RackServerDiscoveryProfile:maxPorts
        managed object property"
    ::= { cfprApVnicRackServerDiscoveryProfileEntry 6 }

cfprApVnicRackServerDiscoveryProfileName OBJECT-TYPE
    SYNTAX       SnmpAdminString
    MAX-ACCESS   read-only
    STATUS       current
    DESCRIPTION
        "Cisco Firepower vnic:RackServerDiscoveryProfile:name
        managed object property"
    ::= { cfprApVnicRackServerDiscoveryProfileEntry 7 }

cfprApVnicRackServerDiscoveryProfilePolicyLevel OBJECT-TYPE
    SYNTAX       Gauge32
    MAX-ACCESS   read-only
    STATUS       current
    DESCRIPTION
        "Cisco Firepower vnic:RackServerDiscoveryProfile:policyLevel
        managed object property"
    ::= { cfprApVnicRackServerDiscoveryProfileEntry 8 }

cfprApVnicRackServerDiscoveryProfilePolicyOwner OBJECT-TYPE
    SYNTAX       CfprApPolicyPolicyOwner
    MAX-ACCESS   read-only
    STATUS       current
    DESCRIPTION
        "Cisco Firepower vnic:RackServerDiscoveryProfile:policyOwner
        managed object property"
    ::= { cfprApVnicRackServerDiscoveryProfileEntry 9 }

cfprApVnicSanConnTemplTable OBJECT-TYPE
    SYNTAX           SEQUENCE OF CfprApVnicSanConnTemplEntry
    MAX-ACCESS       not-accessible
    STATUS           current
    DESCRIPTION
        "Cisco Firepower vnic:SanConnTempl managed object table"
    ::= { cfprApVnicObjects 59 }

cfprApVnicSanConnTemplEntry OBJECT-TYPE
    SYNTAX           CfprApVnicSanConnTemplEntry
    MAX-ACCESS       not-accessible
    STATUS           current
    DESCRIPTION
        "Entry for the cfprApVnicSanConnTemplTable table."
    INDEX { cfprApVnicSanConnTemplInstanceId }
    ::= { cfprApVnicSanConnTemplTable 1 }

CfprApVnicSanConnTemplEntry ::= SEQUENCE {
    cfprApVnicSanConnTemplInstanceId                                 CfprApManagedObjectId,
    cfprApVnicSanConnTemplDn                                         CfprApManagedObjectDn,
    cfprApVnicSanConnTemplRn                                         SnmpAdminString,
    cfprApVnicSanConnTemplDescr                                      SnmpAdminString,
    cfprApVnicSanConnTemplIdentPoolName                              SnmpAdminString,
    cfprApVnicSanConnTemplIntId                                      SnmpAdminString,
    cfprApVnicSanConnTemplMaxDataFieldSize                           Gauge32,
    cfprApVnicSanConnTemplName                                       SnmpAdminString,
    cfprApVnicSanConnTemplNwCtrlPolicyName                           SnmpAdminString,
    cfprApVnicSanConnTemplOperIdentPoolName                          SnmpAdminString,
    cfprApVnicSanConnTemplOperQosPolicyName                          SnmpAdminString,
    cfprApVnicSanConnTemplOperStatsPolicyName                        SnmpAdminString,
    cfprApVnicSanConnTemplPinToGroupName                             SnmpAdminString,
    cfprApVnicSanConnTemplPolicyLevel                                Gauge32,
    cfprApVnicSanConnTemplPolicyOwner                                CfprApPolicyPolicyOwner,
    cfprApVnicSanConnTemplQosPolicyName                              SnmpAdminString,
    cfprApVnicSanConnTemplStatsPolicyName                            SnmpAdminString,
    cfprApVnicSanConnTemplSwitchId                                   CfprApNetworkSwitchId,
    cfprApVnicSanConnTemplTarget                                     CfprApVnicSanConnTemplTarget,
    cfprApVnicSanConnTemplTemplType                                  CfprApVnicTemplateType
}

cfprApVnicSanConnTemplInstanceId OBJECT-TYPE
    SYNTAX       CfprApManagedObjectId
    MAX-ACCESS   not-accessible
    STATUS       current
    DESCRIPTION
        "Instance identifier of the managed object."
    ::= { cfprApVnicSanConnTemplEntry 1 }

cfprApVnicSanConnTemplDn OBJECT-TYPE
    SYNTAX       CfprApManagedObjectDn
    MAX-ACCESS   read-only
    STATUS       current
    DESCRIPTION
        "Cisco Firepower vnic:SanConnTempl:dn managed object property"
    ::= { cfprApVnicSanConnTemplEntry 2 }

cfprApVnicSanConnTemplRn OBJECT-TYPE
    SYNTAX       SnmpAdminString
    MAX-ACCESS   read-only
    STATUS       current
    DESCRIPTION
        "Cisco Firepower vnic:SanConnTempl:rn managed object property"
    ::= { cfprApVnicSanConnTemplEntry 3 }

cfprApVnicSanConnTemplDescr OBJECT-TYPE
    SYNTAX       SnmpAdminString
    MAX-ACCESS   read-only
    STATUS       current
    DESCRIPTION
        "Cisco Firepower vnic:SanConnTempl:descr managed object property"
    ::= { cfprApVnicSanConnTemplEntry 4 }

cfprApVnicSanConnTemplIdentPoolName OBJECT-TYPE
    SYNTAX       SnmpAdminString
    MAX-ACCESS   read-only
    STATUS       current
    DESCRIPTION
        "Cisco Firepower vnic:SanConnTempl:identPoolName
        managed object property"
    ::= { cfprApVnicSanConnTemplEntry 5 }

cfprApVnicSanConnTemplIntId OBJECT-TYPE
    SYNTAX       SnmpAdminString
    MAX-ACCESS   read-only
    STATUS       current
    DESCRIPTION
        "Cisco Firepower vnic:SanConnTempl:intId managed object property"
    ::= { cfprApVnicSanConnTemplEntry 6 }

cfprApVnicSanConnTemplMaxDataFieldSize OBJECT-TYPE
    SYNTAX       Gauge32
    MAX-ACCESS   read-only
    STATUS       current
    DESCRIPTION
        "Cisco Firepower vnic:SanConnTempl:maxDataFieldSize
        managed object property"
    ::= { cfprApVnicSanConnTemplEntry 7 }

cfprApVnicSanConnTemplName OBJECT-TYPE
    SYNTAX       SnmpAdminString
    MAX-ACCESS   read-only
    STATUS       current
    DESCRIPTION
        "Cisco Firepower vnic:SanConnTempl:name managed object property"
    ::= { cfprApVnicSanConnTemplEntry 8 }

cfprApVnicSanConnTemplNwCtrlPolicyName OBJECT-TYPE
    SYNTAX       SnmpAdminString
    MAX-ACCESS   read-only
    STATUS       current
    DESCRIPTION
        "Cisco Firepower vnic:SanConnTempl:nwCtrlPolicyName
        managed object property"
    ::= { cfprApVnicSanConnTemplEntry 9 }

cfprApVnicSanConnTemplOperIdentPoolName OBJECT-TYPE
    SYNTAX       SnmpAdminString
    MAX-ACCESS   read-only
    STATUS       current
    DESCRIPTION
        "Cisco Firepower vnic:SanConnTempl:operIdentPoolName
        managed object property"
    ::= { cfprApVnicSanConnTemplEntry 10 }

cfprApVnicSanConnTemplOperQosPolicyName OBJECT-TYPE
    SYNTAX       SnmpAdminString
    MAX-ACCESS   read-only
    STATUS       current
    DESCRIPTION
        "Cisco Firepower vnic:SanConnTempl:operQosPolicyName
        managed object property"
    ::= { cfprApVnicSanConnTemplEntry 11 }

cfprApVnicSanConnTemplOperStatsPolicyName OBJECT-TYPE
    SYNTAX       SnmpAdminString
    MAX-ACCESS   read-only
    STATUS       current
    DESCRIPTION
        "Cisco Firepower vnic:SanConnTempl:operStatsPolicyName
        managed object property"
    ::= { cfprApVnicSanConnTemplEntry 12 }

cfprApVnicSanConnTemplPinToGroupName OBJECT-TYPE
    SYNTAX       SnmpAdminString
    MAX-ACCESS   read-only
    STATUS       current
    DESCRIPTION
        "Cisco Firepower vnic:SanConnTempl:pinToGroupName
        managed object property"
    ::= { cfprApVnicSanConnTemplEntry 13 }

cfprApVnicSanConnTemplPolicyLevel OBJECT-TYPE
    SYNTAX       Gauge32
    MAX-ACCESS   read-only
    STATUS       current
    DESCRIPTION
        "Cisco Firepower vnic:SanConnTempl:policyLevel
        managed object property"
    ::= { cfprApVnicSanConnTemplEntry 14 }

cfprApVnicSanConnTemplPolicyOwner OBJECT-TYPE
    SYNTAX       CfprApPolicyPolicyOwner
    MAX-ACCESS   read-only
    STATUS       current
    DESCRIPTION
        "Cisco Firepower vnic:SanConnTempl:policyOwner
        managed object property"
    ::= { cfprApVnicSanConnTemplEntry 15 }

cfprApVnicSanConnTemplQosPolicyName OBJECT-TYPE
    SYNTAX       SnmpAdminString
    MAX-ACCESS   read-only
    STATUS       current
    DESCRIPTION
        "Cisco Firepower vnic:SanConnTempl:qosPolicyName
        managed object property"
    ::= { cfprApVnicSanConnTemplEntry 16 }

cfprApVnicSanConnTemplStatsPolicyName OBJECT-TYPE
    SYNTAX       SnmpAdminString
    MAX-ACCESS   read-only
    STATUS       current
    DESCRIPTION
        "Cisco Firepower vnic:SanConnTempl:statsPolicyName
        managed object property"
    ::= { cfprApVnicSanConnTemplEntry 17 }

cfprApVnicSanConnTemplSwitchId OBJECT-TYPE
    SYNTAX       CfprApNetworkSwitchId
    MAX-ACCESS   read-only
    STATUS       current
    DESCRIPTION
        "Cisco Firepower vnic:SanConnTempl:switchId managed
        object property"
    ::= { cfprApVnicSanConnTemplEntry 18 }

cfprApVnicSanConnTemplTarget OBJECT-TYPE
    SYNTAX       CfprApVnicSanConnTemplTarget
    MAX-ACCESS   read-only
    STATUS       current
    DESCRIPTION
        "Cisco Firepower vnic:SanConnTempl:target managed object property"
    ::= { cfprApVnicSanConnTemplEntry 19 }

cfprApVnicSanConnTemplTemplType OBJECT-TYPE
    SYNTAX       CfprApVnicTemplateType
    MAX-ACCESS   read-only
    STATUS       current
    DESCRIPTION
        "Cisco Firepower vnic:SanConnTempl:templType managed
        object property"
    ::= { cfprApVnicSanConnTemplEntry 20 }

cfprApVnicScsiTable OBJECT-TYPE
    SYNTAX           SEQUENCE OF CfprApVnicScsiEntry
    MAX-ACCESS       not-accessible
    STATUS           current
    DESCRIPTION
        "Cisco Firepower vnic:Scsi managed object table"
    ::= { cfprApVnicObjects 60 }

cfprApVnicScsiEntry OBJECT-TYPE
    SYNTAX           CfprApVnicScsiEntry
    MAX-ACCESS       not-accessible
    STATUS           current
    DESCRIPTION
        "Entry for the cfprApVnicScsiTable table."
    INDEX { cfprApVnicScsiInstanceId }
    ::= { cfprApVnicScsiTable 1 }

CfprApVnicScsiEntry ::= SEQUENCE {
    cfprApVnicScsiInstanceId                                         CfprApManagedObjectId,
    cfprApVnicScsiDn                                                 CfprApManagedObjectDn,
    cfprApVnicScsiRn                                                 SnmpAdminString,
    cfprApVnicScsiAdaptorProfileName                                 SnmpAdminString,
    cfprApVnicScsiAdminHostPort                                      CfprApFabricHostPortId,
    cfprApVnicScsiAdminVcon                                          SnmpAdminString,
    cfprApVnicScsiAppRole                                            CfprApVnicAppRole,
    cfprApVnicScsiBootDev                                            CfprApVnicVnicBootDev,
    cfprApVnicScsiConfigQualifier                                    CfprApVnicConfigIssues,
    cfprApVnicScsiConfigState                                        CfprApLsConfigState,
    cfprApVnicScsiEquipmentDn                                        SnmpAdminString,
    cfprApVnicScsiIdentPoolName                                      SnmpAdminString,
    cfprApVnicScsiInstType                                           CfprApVnicInstantiation,
    cfprApVnicScsiName                                               SnmpAdminString,
    cfprApVnicScsiNwTemplName                                        SnmpAdminString,
    cfprApVnicScsiOperHostPort                                       CfprApVnicVnicOperHostPort,
    cfprApVnicScsiOperOrder                                          Gauge32,
    cfprApVnicScsiOperSpeed                                          Gauge32,
    cfprApVnicScsiOperStatsPolicyName                                SnmpAdminString,
    cfprApVnicScsiOperVcon                                           SnmpAdminString,
    cfprApVnicScsiOrder                                              Gauge32,
    cfprApVnicScsiOwner                                              CfprApVnicConnectionOwner,
    cfprApVnicScsiPinToGroupName                                     SnmpAdminString,
    cfprApVnicScsiQosPolicyName                                      SnmpAdminString,
    cfprApVnicScsiStatsPolicyName                                    SnmpAdminString,
    cfprApVnicScsiSwitchId                                           CfprApNetworkSwitchId,
    cfprApVnicScsiType                                               CfprApVnicScsiType
}

cfprApVnicScsiInstanceId OBJECT-TYPE
    SYNTAX       CfprApManagedObjectId
    MAX-ACCESS   not-accessible
    STATUS       current
    DESCRIPTION
        "Instance identifier of the managed object."
    ::= { cfprApVnicScsiEntry 1 }

cfprApVnicScsiDn OBJECT-TYPE
    SYNTAX       CfprApManagedObjectDn
    MAX-ACCESS   read-only
    STATUS       current
    DESCRIPTION
        "Cisco Firepower vnic:Scsi:dn managed object property"
    ::= { cfprApVnicScsiEntry 2 }

cfprApVnicScsiRn OBJECT-TYPE
    SYNTAX       SnmpAdminString
    MAX-ACCESS   read-only
    STATUS       current
    DESCRIPTION
        "Cisco Firepower vnic:Scsi:rn managed object property"
    ::= { cfprApVnicScsiEntry 3 }

cfprApVnicScsiAdaptorProfileName OBJECT-TYPE
    SYNTAX       SnmpAdminString
    MAX-ACCESS   read-only
    STATUS       current
    DESCRIPTION
        "Cisco Firepower vnic:Scsi:adaptorProfileName managed
        object property"
    ::= { cfprApVnicScsiEntry 4 }

cfprApVnicScsiAdminHostPort OBJECT-TYPE
    SYNTAX       CfprApFabricHostPortId
    MAX-ACCESS   read-only
    STATUS       current
    DESCRIPTION
        "Cisco Firepower vnic:Scsi:adminHostPort managed object property"
    ::= { cfprApVnicScsiEntry 5 }

cfprApVnicScsiAdminVcon OBJECT-TYPE
    SYNTAX       SnmpAdminString
    MAX-ACCESS   read-only
    STATUS       current
    DESCRIPTION
        "Cisco Firepower vnic:Scsi:adminVcon managed object property"
    ::= { cfprApVnicScsiEntry 6 }

cfprApVnicScsiAppRole OBJECT-TYPE
    SYNTAX       CfprApVnicAppRole
    MAX-ACCESS   read-only
    STATUS       current
    DESCRIPTION
        "Cisco Firepower vnic:Scsi:appRole managed object property"
    ::= { cfprApVnicScsiEntry 7 }

cfprApVnicScsiBootDev OBJECT-TYPE
    SYNTAX       CfprApVnicVnicBootDev
    MAX-ACCESS   read-only
    STATUS       current
    DESCRIPTION
        "Cisco Firepower vnic:Scsi:bootDev managed object property"
    ::= { cfprApVnicScsiEntry 8 }

cfprApVnicScsiConfigQualifier OBJECT-TYPE
    SYNTAX       CfprApVnicConfigIssues
    MAX-ACCESS   read-only
    STATUS       current
    DESCRIPTION
        "Cisco Firepower vnic:Scsi:configQualifier managed
        object property"
    ::= { cfprApVnicScsiEntry 9 }

cfprApVnicScsiConfigState OBJECT-TYPE
    SYNTAX       CfprApLsConfigState
    MAX-ACCESS   read-only
    STATUS       current
    DESCRIPTION
        "Cisco Firepower vnic:Scsi:configState managed object property"
    ::= { cfprApVnicScsiEntry 10 }

cfprApVnicScsiEquipmentDn OBJECT-TYPE
    SYNTAX       SnmpAdminString
    MAX-ACCESS   read-only
    STATUS       current
    DESCRIPTION
        "Cisco Firepower vnic:Scsi:equipmentDn managed object property"
    ::= { cfprApVnicScsiEntry 11 }

cfprApVnicScsiIdentPoolName OBJECT-TYPE
    SYNTAX       SnmpAdminString
    MAX-ACCESS   read-only
    STATUS       current
    DESCRIPTION
        "Cisco Firepower vnic:Scsi:identPoolName managed object property"
    ::= { cfprApVnicScsiEntry 12 }

cfprApVnicScsiInstType OBJECT-TYPE
    SYNTAX       CfprApVnicInstantiation
    MAX-ACCESS   read-only
    STATUS       current
    DESCRIPTION
        "Cisco Firepower vnic:Scsi:instType managed object property"
    ::= { cfprApVnicScsiEntry 13 }

cfprApVnicScsiName OBJECT-TYPE
    SYNTAX       SnmpAdminString
    MAX-ACCESS   read-only
    STATUS       current
    DESCRIPTION
        "Cisco Firepower vnic:Scsi:name managed object property"
    ::= { cfprApVnicScsiEntry 14 }

cfprApVnicScsiNwTemplName OBJECT-TYPE
    SYNTAX       SnmpAdminString
    MAX-ACCESS   read-only
    STATUS       current
    DESCRIPTION
        "Cisco Firepower vnic:Scsi:nwTemplName managed object property"
    ::= { cfprApVnicScsiEntry 15 }

cfprApVnicScsiOperHostPort OBJECT-TYPE
    SYNTAX       CfprApVnicVnicOperHostPort
    MAX-ACCESS   read-only
    STATUS       current
    DESCRIPTION
        "Cisco Firepower vnic:Scsi:operHostPort managed object property"
    ::= { cfprApVnicScsiEntry 16 }

cfprApVnicScsiOperOrder OBJECT-TYPE
    SYNTAX       Gauge32
    MAX-ACCESS   read-only
    STATUS       current
    DESCRIPTION
        "Cisco Firepower vnic:Scsi:operOrder managed object property"
    ::= { cfprApVnicScsiEntry 17 }

cfprApVnicScsiOperSpeed OBJECT-TYPE
    SYNTAX       Gauge32
    MAX-ACCESS   read-only
    STATUS       current
    DESCRIPTION
        "Cisco Firepower vnic:Scsi:operSpeed managed object property"
    ::= { cfprApVnicScsiEntry 18 }

cfprApVnicScsiOperStatsPolicyName OBJECT-TYPE
    SYNTAX       SnmpAdminString
    MAX-ACCESS   read-only
    STATUS       current
    DESCRIPTION
        "Cisco Firepower vnic:Scsi:operStatsPolicyName
        managed object property"
    ::= { cfprApVnicScsiEntry 19 }

cfprApVnicScsiOperVcon OBJECT-TYPE
    SYNTAX       SnmpAdminString
    MAX-ACCESS   read-only
    STATUS       current
    DESCRIPTION
        "Cisco Firepower vnic:Scsi:operVcon managed object property"
    ::= { cfprApVnicScsiEntry 20 }

cfprApVnicScsiOrder OBJECT-TYPE
    SYNTAX       Gauge32
    MAX-ACCESS   read-only
    STATUS       current
    DESCRIPTION
        "Cisco Firepower vnic:Scsi:order managed object property"
    ::= { cfprApVnicScsiEntry 21 }

cfprApVnicScsiOwner OBJECT-TYPE
    SYNTAX       CfprApVnicConnectionOwner
    MAX-ACCESS   read-only
    STATUS       current
    DESCRIPTION
        "Cisco Firepower vnic:Scsi:owner managed object property"
    ::= { cfprApVnicScsiEntry 22 }

cfprApVnicScsiPinToGroupName OBJECT-TYPE
    SYNTAX       SnmpAdminString
    MAX-ACCESS   read-only
    STATUS       current
    DESCRIPTION
        "Cisco Firepower vnic:Scsi:pinToGroupName managed object property"
    ::= { cfprApVnicScsiEntry 23 }

cfprApVnicScsiQosPolicyName OBJECT-TYPE
    SYNTAX       SnmpAdminString
    MAX-ACCESS   read-only
    STATUS       current
    DESCRIPTION
        "Cisco Firepower vnic:Scsi:qosPolicyName managed object property"
    ::= { cfprApVnicScsiEntry 24 }

cfprApVnicScsiStatsPolicyName OBJECT-TYPE
    SYNTAX       SnmpAdminString
    MAX-ACCESS   read-only
    STATUS       current
    DESCRIPTION
        "Cisco Firepower vnic:Scsi:statsPolicyName managed
        object property"
    ::= { cfprApVnicScsiEntry 25 }

cfprApVnicScsiSwitchId OBJECT-TYPE
    SYNTAX       CfprApNetworkSwitchId
    MAX-ACCESS   read-only
    STATUS       current
    DESCRIPTION
        "Cisco Firepower vnic:Scsi:switchId managed object property"
    ::= { cfprApVnicScsiEntry 26 }

cfprApVnicScsiType OBJECT-TYPE
    SYNTAX       CfprApVnicScsiType
    MAX-ACCESS   read-only
    STATUS       current
    DESCRIPTION
        "Cisco Firepower vnic:Scsi:type managed object property"
    ::= { cfprApVnicScsiEntry 27 }

cfprApVnicScsiIfTable OBJECT-TYPE
    SYNTAX           SEQUENCE OF CfprApVnicScsiIfEntry
    MAX-ACCESS       not-accessible
    STATUS           current
    DESCRIPTION
        "Cisco Firepower vnic:ScsiIf managed object table"
    ::= { cfprApVnicObjects 61 }

cfprApVnicScsiIfEntry OBJECT-TYPE
    SYNTAX           CfprApVnicScsiIfEntry
    MAX-ACCESS       not-accessible
    STATUS           current
    DESCRIPTION
        "Entry for the cfprApVnicScsiIfTable table."
    INDEX { cfprApVnicScsiIfInstanceId }
    ::= { cfprApVnicScsiIfTable 1 }

CfprApVnicScsiIfEntry ::= SEQUENCE {
    cfprApVnicScsiIfInstanceId                                       CfprApManagedObjectId,
    cfprApVnicScsiIfDn                                               CfprApManagedObjectDn,
    cfprApVnicScsiIfRn                                               SnmpAdminString,
    cfprApVnicScsiIfAddr                                             Unsigned64,
    cfprApVnicScsiIfConfigQualifier                                  CfprApVnicConfigIssues,
    cfprApVnicScsiIfName                                             SnmpAdminString,
    cfprApVnicScsiIfOperState                                        CfprApVnicIfOperState,
    cfprApVnicScsiIfOperVnetDn                                       SnmpAdminString,
    cfprApVnicScsiIfOperVnetName                                     SnmpAdminString,
    cfprApVnicScsiIfOwner                                            CfprApVnicConnectionOwner,
    cfprApVnicScsiIfPubNwId                                          Gauge32,
    cfprApVnicScsiIfSharing                                          CfprApFabricVlanSharingType,
    cfprApVnicScsiIfSwitchId                                         CfprApNetworkSwitchId,
    cfprApVnicScsiIfType                                             CfprApVnicAScsiIfType,
    cfprApVnicScsiIfVnet                                             Gauge32
}

cfprApVnicScsiIfInstanceId OBJECT-TYPE
    SYNTAX       CfprApManagedObjectId
    MAX-ACCESS   not-accessible
    STATUS       current
    DESCRIPTION
        "Instance identifier of the managed object."
    ::= { cfprApVnicScsiIfEntry 1 }

cfprApVnicScsiIfDn OBJECT-TYPE
    SYNTAX       CfprApManagedObjectDn
    MAX-ACCESS   read-only
    STATUS       current
    DESCRIPTION
        "Cisco Firepower vnic:ScsiIf:dn managed object property"
    ::= { cfprApVnicScsiIfEntry 2 }

cfprApVnicScsiIfRn OBJECT-TYPE
    SYNTAX       SnmpAdminString
    MAX-ACCESS   read-only
    STATUS       current
    DESCRIPTION
        "Cisco Firepower vnic:ScsiIf:rn managed object property"
    ::= { cfprApVnicScsiIfEntry 3 }

cfprApVnicScsiIfAddr OBJECT-TYPE
    SYNTAX       Unsigned64
    MAX-ACCESS   read-only
    STATUS       current
    DESCRIPTION
        "Cisco Firepower vnic:ScsiIf:addr managed object property"
    ::= { cfprApVnicScsiIfEntry 4 }

cfprApVnicScsiIfConfigQualifier OBJECT-TYPE
    SYNTAX       CfprApVnicConfigIssues
    MAX-ACCESS   read-only
    STATUS       current
    DESCRIPTION
        "Cisco Firepower vnic:ScsiIf:configQualifier managed
        object property"
    ::= { cfprApVnicScsiIfEntry 5 }

cfprApVnicScsiIfName OBJECT-TYPE
    SYNTAX       SnmpAdminString
    MAX-ACCESS   read-only
    STATUS       current
    DESCRIPTION
        "Cisco Firepower vnic:ScsiIf:name managed object property"
    ::= { cfprApVnicScsiIfEntry 6 }

cfprApVnicScsiIfOperState OBJECT-TYPE
    SYNTAX       CfprApVnicIfOperState
    MAX-ACCESS   read-only
    STATUS       current
    DESCRIPTION
        "Cisco Firepower vnic:ScsiIf:operState managed object property"
    ::= { cfprApVnicScsiIfEntry 7 }

cfprApVnicScsiIfOperVnetDn OBJECT-TYPE
    SYNTAX       SnmpAdminString
    MAX-ACCESS   read-only
    STATUS       current
    DESCRIPTION
        "Cisco Firepower vnic:ScsiIf:operVnetDn managed object property"
    ::= { cfprApVnicScsiIfEntry 8 }

cfprApVnicScsiIfOperVnetName OBJECT-TYPE
    SYNTAX       SnmpAdminString
    MAX-ACCESS   read-only
    STATUS       current
    DESCRIPTION
        "Cisco Firepower vnic:ScsiIf:operVnetName managed object property"
    ::= { cfprApVnicScsiIfEntry 9 }

cfprApVnicScsiIfOwner OBJECT-TYPE
    SYNTAX       CfprApVnicConnectionOwner
    MAX-ACCESS   read-only
    STATUS       current
    DESCRIPTION
        "Cisco Firepower vnic:ScsiIf:owner managed object property"
    ::= { cfprApVnicScsiIfEntry 10 }

cfprApVnicScsiIfPubNwId OBJECT-TYPE
    SYNTAX       Gauge32
    MAX-ACCESS   read-only
    STATUS       current
    DESCRIPTION
        "Cisco Firepower vnic:ScsiIf:pubNwId managed object property"
    ::= { cfprApVnicScsiIfEntry 11 }

cfprApVnicScsiIfSharing OBJECT-TYPE
    SYNTAX       CfprApFabricVlanSharingType
    MAX-ACCESS   read-only
    STATUS       current
    DESCRIPTION
        "Cisco Firepower vnic:ScsiIf:sharing managed object property"
    ::= { cfprApVnicScsiIfEntry 12 }

cfprApVnicScsiIfSwitchId OBJECT-TYPE
    SYNTAX       CfprApNetworkSwitchId
    MAX-ACCESS   read-only
    STATUS       current
    DESCRIPTION
        "Cisco Firepower vnic:ScsiIf:switchId managed object property"
    ::= { cfprApVnicScsiIfEntry 13 }

cfprApVnicScsiIfType OBJECT-TYPE
    SYNTAX       CfprApVnicAScsiIfType
    MAX-ACCESS   read-only
    STATUS       current
    DESCRIPTION
        "Cisco Firepower vnic:ScsiIf:type managed object property"
    ::= { cfprApVnicScsiIfEntry 14 }

cfprApVnicScsiIfVnet OBJECT-TYPE
    SYNTAX       Gauge32
    MAX-ACCESS   read-only
    STATUS       current
    DESCRIPTION
        "Cisco Firepower vnic:ScsiIf:vnet managed object property"
    ::= { cfprApVnicScsiIfEntry 15 }

cfprApVnicUsnicConPolicyTable OBJECT-TYPE
    SYNTAX           SEQUENCE OF CfprApVnicUsnicConPolicyEntry
    MAX-ACCESS       not-accessible
    STATUS           current
    DESCRIPTION
        "Cisco Firepower vnic:UsnicConPolicy managed object table"
    ::= { cfprApVnicObjects 62 }

cfprApVnicUsnicConPolicyEntry OBJECT-TYPE
    SYNTAX           CfprApVnicUsnicConPolicyEntry
    MAX-ACCESS       not-accessible
    STATUS           current
    DESCRIPTION
        "Entry for the cfprApVnicUsnicConPolicyTable table."
    INDEX { cfprApVnicUsnicConPolicyInstanceId }
    ::= { cfprApVnicUsnicConPolicyTable 1 }

CfprApVnicUsnicConPolicyEntry ::= SEQUENCE {
    cfprApVnicUsnicConPolicyInstanceId                               CfprApManagedObjectId,
    cfprApVnicUsnicConPolicyDn                                       CfprApManagedObjectDn,
    cfprApVnicUsnicConPolicyRn                                       SnmpAdminString,
    cfprApVnicUsnicConPolicyAdaptorProfileName                       SnmpAdminString,
    cfprApVnicUsnicConPolicyDescr                                    SnmpAdminString,
    cfprApVnicUsnicConPolicyIntId                                    SnmpAdminString,
    cfprApVnicUsnicConPolicyName                                     SnmpAdminString,
    cfprApVnicUsnicConPolicyPolicyLevel                              Gauge32,
    cfprApVnicUsnicConPolicyPolicyOwner                              CfprApPolicyPolicyOwner,
    cfprApVnicUsnicConPolicyUsnicCount                               Gauge32
}

cfprApVnicUsnicConPolicyInstanceId OBJECT-TYPE
    SYNTAX       CfprApManagedObjectId
    MAX-ACCESS   not-accessible
    STATUS       current
    DESCRIPTION
        "Instance identifier of the managed object."
    ::= { cfprApVnicUsnicConPolicyEntry 1 }

cfprApVnicUsnicConPolicyDn OBJECT-TYPE
    SYNTAX       CfprApManagedObjectDn
    MAX-ACCESS   read-only
    STATUS       current
    DESCRIPTION
        "Cisco Firepower vnic:UsnicConPolicy:dn managed object property"
    ::= { cfprApVnicUsnicConPolicyEntry 2 }

cfprApVnicUsnicConPolicyRn OBJECT-TYPE
    SYNTAX       SnmpAdminString
    MAX-ACCESS   read-only
    STATUS       current
    DESCRIPTION
        "Cisco Firepower vnic:UsnicConPolicy:rn managed object property"
    ::= { cfprApVnicUsnicConPolicyEntry 3 }

cfprApVnicUsnicConPolicyAdaptorProfileName OBJECT-TYPE
    SYNTAX       SnmpAdminString
    MAX-ACCESS   read-only
    STATUS       current
    DESCRIPTION
        "Cisco Firepower vnic:UsnicConPolicy:adaptorProfileName
        managed object property"
    ::= { cfprApVnicUsnicConPolicyEntry 4 }

cfprApVnicUsnicConPolicyDescr OBJECT-TYPE
    SYNTAX       SnmpAdminString
    MAX-ACCESS   read-only
    STATUS       current
    DESCRIPTION
        "Cisco Firepower vnic:UsnicConPolicy:descr managed
        object property"
    ::= { cfprApVnicUsnicConPolicyEntry 5 }

cfprApVnicUsnicConPolicyIntId OBJECT-TYPE
    SYNTAX       SnmpAdminString
    MAX-ACCESS   read-only
    STATUS       current
    DESCRIPTION
        "Cisco Firepower vnic:UsnicConPolicy:intId managed
        object property"
    ::= { cfprApVnicUsnicConPolicyEntry 6 }

cfprApVnicUsnicConPolicyName OBJECT-TYPE
    SYNTAX       SnmpAdminString
    MAX-ACCESS   read-only
    STATUS       current
    DESCRIPTION
        "Cisco Firepower vnic:UsnicConPolicy:name managed object property"
    ::= { cfprApVnicUsnicConPolicyEntry 7 }

cfprApVnicUsnicConPolicyPolicyLevel OBJECT-TYPE
    SYNTAX       Gauge32
    MAX-ACCESS   read-only
    STATUS       current
    DESCRIPTION
        "Cisco Firepower vnic:UsnicConPolicy:policyLevel
        managed object property"
    ::= { cfprApVnicUsnicConPolicyEntry 8 }

cfprApVnicUsnicConPolicyPolicyOwner OBJECT-TYPE
    SYNTAX       CfprApPolicyPolicyOwner
    MAX-ACCESS   read-only
    STATUS       current
    DESCRIPTION
        "Cisco Firepower vnic:UsnicConPolicy:policyOwner
        managed object property"
    ::= { cfprApVnicUsnicConPolicyEntry 9 }

cfprApVnicUsnicConPolicyUsnicCount OBJECT-TYPE
    SYNTAX       Gauge32
    MAX-ACCESS   read-only
    STATUS       current
    DESCRIPTION
        "Cisco Firepower vnic:UsnicConPolicy:usnicCount
        managed object property"
    ::= { cfprApVnicUsnicConPolicyEntry 10 }

cfprApVnicUsnicConPolicyRefTable OBJECT-TYPE
    SYNTAX           SEQUENCE OF CfprApVnicUsnicConPolicyRefEntry
    MAX-ACCESS       not-accessible
    STATUS           current
    DESCRIPTION
        "Cisco Firepower vnic:UsnicConPolicyRef managed object table"
    ::= { cfprApVnicObjects 63 }

cfprApVnicUsnicConPolicyRefEntry OBJECT-TYPE
    SYNTAX           CfprApVnicUsnicConPolicyRefEntry
    MAX-ACCESS       not-accessible
    STATUS           current
    DESCRIPTION
        "Entry for the cfprApVnicUsnicConPolicyRefTable table."
    INDEX { cfprApVnicUsnicConPolicyRefInstanceId }
    ::= { cfprApVnicUsnicConPolicyRefTable 1 }

CfprApVnicUsnicConPolicyRefEntry ::= SEQUENCE {
    cfprApVnicUsnicConPolicyRefInstanceId                            CfprApManagedObjectId,
    cfprApVnicUsnicConPolicyRefDn                                    CfprApManagedObjectDn,
    cfprApVnicUsnicConPolicyRefRn                                    SnmpAdminString,
    cfprApVnicUsnicConPolicyRefConPolicyName                         SnmpAdminString,
    cfprApVnicUsnicConPolicyRefOperConPolicyName                     SnmpAdminString
}

cfprApVnicUsnicConPolicyRefInstanceId OBJECT-TYPE
    SYNTAX       CfprApManagedObjectId
    MAX-ACCESS   not-accessible
    STATUS       current
    DESCRIPTION
        "Instance identifier of the managed object."
    ::= { cfprApVnicUsnicConPolicyRefEntry 1 }

cfprApVnicUsnicConPolicyRefDn OBJECT-TYPE
    SYNTAX       CfprApManagedObjectDn
    MAX-ACCESS   read-only
    STATUS       current
    DESCRIPTION
        "Cisco Firepower vnic:UsnicConPolicyRef:dn managed
        object property"
    ::= { cfprApVnicUsnicConPolicyRefEntry 2 }

cfprApVnicUsnicConPolicyRefRn OBJECT-TYPE
    SYNTAX       SnmpAdminString
    MAX-ACCESS   read-only
    STATUS       current
    DESCRIPTION
        "Cisco Firepower vnic:UsnicConPolicyRef:rn managed
        object property"
    ::= { cfprApVnicUsnicConPolicyRefEntry 3 }

cfprApVnicUsnicConPolicyRefConPolicyName OBJECT-TYPE
    SYNTAX       SnmpAdminString
    MAX-ACCESS   read-only
    STATUS       current
    DESCRIPTION
        "Cisco Firepower vnic:UsnicConPolicyRef:conPolicyName
        managed object property"
    ::= { cfprApVnicUsnicConPolicyRefEntry 4 }

cfprApVnicUsnicConPolicyRefOperConPolicyName OBJECT-TYPE
    SYNTAX       SnmpAdminString
    MAX-ACCESS   read-only
    STATUS       current
    DESCRIPTION
        "Cisco Firepower vnic:UsnicConPolicyRef:operConPolicyName
        managed object property"
    ::= { cfprApVnicUsnicConPolicyRefEntry 5 }

cfprApVnicVhbaBehPolicyTable OBJECT-TYPE
    SYNTAX           SEQUENCE OF CfprApVnicVhbaBehPolicyEntry
    MAX-ACCESS       not-accessible
    STATUS           current
    DESCRIPTION
        "Cisco Firepower vnic:VhbaBehPolicy managed object table"
    ::= { cfprApVnicObjects 64 }

cfprApVnicVhbaBehPolicyEntry OBJECT-TYPE
    SYNTAX           CfprApVnicVhbaBehPolicyEntry
    MAX-ACCESS       not-accessible
    STATUS           current
    DESCRIPTION
        "Entry for the cfprApVnicVhbaBehPolicyTable table."
    INDEX { cfprApVnicVhbaBehPolicyInstanceId }
    ::= { cfprApVnicVhbaBehPolicyTable 1 }

CfprApVnicVhbaBehPolicyEntry ::= SEQUENCE {
    cfprApVnicVhbaBehPolicyInstanceId                                CfprApManagedObjectId,
    cfprApVnicVhbaBehPolicyDn                                        CfprApManagedObjectDn,
    cfprApVnicVhbaBehPolicyRn                                        SnmpAdminString,
    cfprApVnicVhbaBehPolicyAction                                    CfprApVnicDefaultAction,
    cfprApVnicVhbaBehPolicyDescr                                     SnmpAdminString,
    cfprApVnicVhbaBehPolicyIntId                                     SnmpAdminString,
    cfprApVnicVhbaBehPolicyName                                      SnmpAdminString,
    cfprApVnicVhbaBehPolicyNwTemplName                               SnmpAdminString,
    cfprApVnicVhbaBehPolicyPolicyLevel                               Gauge32,
    cfprApVnicVhbaBehPolicyPolicyOwner                               CfprApPolicyPolicyOwner,
    cfprApVnicVhbaBehPolicyType                                      CfprApVnicVhbaBehPolicyType
}

cfprApVnicVhbaBehPolicyInstanceId OBJECT-TYPE
    SYNTAX       CfprApManagedObjectId
    MAX-ACCESS   not-accessible
    STATUS       current
    DESCRIPTION
        "Instance identifier of the managed object."
    ::= { cfprApVnicVhbaBehPolicyEntry 1 }

cfprApVnicVhbaBehPolicyDn OBJECT-TYPE
    SYNTAX       CfprApManagedObjectDn
    MAX-ACCESS   read-only
    STATUS       current
    DESCRIPTION
        "Cisco Firepower vnic:VhbaBehPolicy:dn managed object property"
    ::= { cfprApVnicVhbaBehPolicyEntry 2 }

cfprApVnicVhbaBehPolicyRn OBJECT-TYPE
    SYNTAX       SnmpAdminString
    MAX-ACCESS   read-only
    STATUS       current
    DESCRIPTION
        "Cisco Firepower vnic:VhbaBehPolicy:rn managed object property"
    ::= { cfprApVnicVhbaBehPolicyEntry 3 }

cfprApVnicVhbaBehPolicyAction OBJECT-TYPE
    SYNTAX       CfprApVnicDefaultAction
    MAX-ACCESS   read-only
    STATUS       current
    DESCRIPTION
        "Cisco Firepower vnic:VhbaBehPolicy:action managed
        object property"
    ::= { cfprApVnicVhbaBehPolicyEntry 4 }

cfprApVnicVhbaBehPolicyDescr OBJECT-TYPE
    SYNTAX       SnmpAdminString
    MAX-ACCESS   read-only
    STATUS       current
    DESCRIPTION
        "Cisco Firepower vnic:VhbaBehPolicy:descr managed object property"
    ::= { cfprApVnicVhbaBehPolicyEntry 5 }

cfprApVnicVhbaBehPolicyIntId OBJECT-TYPE
    SYNTAX       SnmpAdminString
    MAX-ACCESS   read-only
    STATUS       current
    DESCRIPTION
        "Cisco Firepower vnic:VhbaBehPolicy:intId managed object property"
    ::= { cfprApVnicVhbaBehPolicyEntry 6 }

cfprApVnicVhbaBehPolicyName OBJECT-TYPE
    SYNTAX       SnmpAdminString
    MAX-ACCESS   read-only
    STATUS       current
    DESCRIPTION
        "Cisco Firepower vnic:VhbaBehPolicy:name managed object property"
    ::= { cfprApVnicVhbaBehPolicyEntry 7 }

cfprApVnicVhbaBehPolicyNwTemplName OBJECT-TYPE
    SYNTAX       SnmpAdminString
    MAX-ACCESS   read-only
    STATUS       current
    DESCRIPTION
        "Cisco Firepower vnic:VhbaBehPolicy:nwTemplName
        managed object property"
    ::= { cfprApVnicVhbaBehPolicyEntry 8 }

cfprApVnicVhbaBehPolicyPolicyLevel OBJECT-TYPE
    SYNTAX       Gauge32
    MAX-ACCESS   read-only
    STATUS       current
    DESCRIPTION
        "Cisco Firepower vnic:VhbaBehPolicy:policyLevel
        managed object property"
    ::= { cfprApVnicVhbaBehPolicyEntry 9 }

cfprApVnicVhbaBehPolicyPolicyOwner OBJECT-TYPE
    SYNTAX       CfprApPolicyPolicyOwner
    MAX-ACCESS   read-only
    STATUS       current
    DESCRIPTION
        "Cisco Firepower vnic:VhbaBehPolicy:policyOwner
        managed object property"
    ::= { cfprApVnicVhbaBehPolicyEntry 10 }

cfprApVnicVhbaBehPolicyType OBJECT-TYPE
    SYNTAX       CfprApVnicVhbaBehPolicyType
    MAX-ACCESS   read-only
    STATUS       current
    DESCRIPTION
        "Cisco Firepower vnic:VhbaBehPolicy:type managed object property"
    ::= { cfprApVnicVhbaBehPolicyEntry 11 }

cfprApVnicVlanTable OBJECT-TYPE
    SYNTAX           SEQUENCE OF CfprApVnicVlanEntry
    MAX-ACCESS       not-accessible
    STATUS           current
    DESCRIPTION
        "Cisco Firepower vnic:Vlan managed object table"
    ::= { cfprApVnicObjects 65 }

cfprApVnicVlanEntry OBJECT-TYPE
    SYNTAX           CfprApVnicVlanEntry
    MAX-ACCESS       not-accessible
    STATUS           current
    DESCRIPTION
        "Entry for the cfprApVnicVlanTable table."
    INDEX { cfprApVnicVlanInstanceId }
    ::= { cfprApVnicVlanTable 1 }

CfprApVnicVlanEntry ::= SEQUENCE {
    cfprApVnicVlanInstanceId                                         CfprApManagedObjectId,
    cfprApVnicVlanDn                                                 CfprApManagedObjectDn,
    cfprApVnicVlanRn                                                 SnmpAdminString,
    cfprApVnicVlanConfigQualifier                                    CfprApVnicConfigIssues,
    cfprApVnicVlanFltAggr                                            Unsigned64,
    cfprApVnicVlanName                                               SnmpAdminString,
    cfprApVnicVlanOperState                                          CfprApVnicIfOperState,
    cfprApVnicVlanOperVnetDn                                         SnmpAdminString,
    cfprApVnicVlanOperVnetName                                       SnmpAdminString,
    cfprApVnicVlanOwner                                              CfprApVnicConnectionOwner,
    cfprApVnicVlanPubNwId                                            Gauge32,
    cfprApVnicVlanSharing                                            CfprApFabricVlanSharingType,
    cfprApVnicVlanSwitchId                                           CfprApNetworkSwitchId,
    cfprApVnicVlanType                                               CfprApVnicConnectionType,
    cfprApVnicVlanVlanName                                           SnmpAdminString,
    cfprApVnicVlanVnet                                               Gauge32
}

cfprApVnicVlanInstanceId OBJECT-TYPE
    SYNTAX       CfprApManagedObjectId
    MAX-ACCESS   not-accessible
    STATUS       current
    DESCRIPTION
        "Instance identifier of the managed object."
    ::= { cfprApVnicVlanEntry 1 }

cfprApVnicVlanDn OBJECT-TYPE
    SYNTAX       CfprApManagedObjectDn
    MAX-ACCESS   read-only
    STATUS       current
    DESCRIPTION
        "Cisco Firepower vnic:Vlan:dn managed object property"
    ::= { cfprApVnicVlanEntry 2 }

cfprApVnicVlanRn OBJECT-TYPE
    SYNTAX       SnmpAdminString
    MAX-ACCESS   read-only
    STATUS       current
    DESCRIPTION
        "Cisco Firepower vnic:Vlan:rn managed object property"
    ::= { cfprApVnicVlanEntry 3 }

cfprApVnicVlanConfigQualifier OBJECT-TYPE
    SYNTAX       CfprApVnicConfigIssues
    MAX-ACCESS   read-only
    STATUS       current
    DESCRIPTION
        "Cisco Firepower vnic:Vlan:configQualifier managed
        object property"
    ::= { cfprApVnicVlanEntry 4 }

cfprApVnicVlanFltAggr OBJECT-TYPE
    SYNTAX       Unsigned64
    MAX-ACCESS   read-only
    STATUS       current
    DESCRIPTION
        "Cisco Firepower vnic:Vlan:fltAggr managed object property"
    ::= { cfprApVnicVlanEntry 5 }

cfprApVnicVlanName OBJECT-TYPE
    SYNTAX       SnmpAdminString
    MAX-ACCESS   read-only
    STATUS       current
    DESCRIPTION
        "Cisco Firepower vnic:Vlan:name managed object property"
    ::= { cfprApVnicVlanEntry 6 }

cfprApVnicVlanOperState OBJECT-TYPE
    SYNTAX       CfprApVnicIfOperState
    MAX-ACCESS   read-only
    STATUS       current
    DESCRIPTION
        "Cisco Firepower vnic:Vlan:operState managed object property"
    ::= { cfprApVnicVlanEntry 7 }

cfprApVnicVlanOperVnetDn OBJECT-TYPE
    SYNTAX       SnmpAdminString
    MAX-ACCESS   read-only
    STATUS       current
    DESCRIPTION
        "Cisco Firepower vnic:Vlan:operVnetDn managed object property"
    ::= { cfprApVnicVlanEntry 8 }

cfprApVnicVlanOperVnetName OBJECT-TYPE
    SYNTAX       SnmpAdminString
    MAX-ACCESS   read-only
    STATUS       current
    DESCRIPTION
        "Cisco Firepower vnic:Vlan:operVnetName managed object property"
    ::= { cfprApVnicVlanEntry 9 }

cfprApVnicVlanOwner OBJECT-TYPE
    SYNTAX       CfprApVnicConnectionOwner
    MAX-ACCESS   read-only
    STATUS       current
    DESCRIPTION
        "Cisco Firepower vnic:Vlan:owner managed object property"
    ::= { cfprApVnicVlanEntry 10 }

cfprApVnicVlanPubNwId OBJECT-TYPE
    SYNTAX       Gauge32
    MAX-ACCESS   read-only
    STATUS       current
    DESCRIPTION
        "Cisco Firepower vnic:Vlan:pubNwId managed object property"
    ::= { cfprApVnicVlanEntry 11 }

cfprApVnicVlanSharing OBJECT-TYPE
    SYNTAX       CfprApFabricVlanSharingType
    MAX-ACCESS   read-only
    STATUS       current
    DESCRIPTION
        "Cisco Firepower vnic:Vlan:sharing managed object property"
    ::= { cfprApVnicVlanEntry 12 }

cfprApVnicVlanSwitchId OBJECT-TYPE
    SYNTAX       CfprApNetworkSwitchId
    MAX-ACCESS   read-only
    STATUS       current
    DESCRIPTION
        "Cisco Firepower vnic:Vlan:switchId managed object property"
    ::= { cfprApVnicVlanEntry 13 }

cfprApVnicVlanType OBJECT-TYPE
    SYNTAX       CfprApVnicConnectionType
    MAX-ACCESS   read-only
    STATUS       current
    DESCRIPTION
        "Cisco Firepower vnic:Vlan:type managed object property"
    ::= { cfprApVnicVlanEntry 14 }

cfprApVnicVlanVlanName OBJECT-TYPE
    SYNTAX       SnmpAdminString
    MAX-ACCESS   read-only
    STATUS       current
    DESCRIPTION
        "Cisco Firepower vnic:Vlan:vlanName managed object property"
    ::= { cfprApVnicVlanEntry 15 }

cfprApVnicVlanVnet OBJECT-TYPE
    SYNTAX       Gauge32
    MAX-ACCESS   read-only
    STATUS       current
    DESCRIPTION
        "Cisco Firepower vnic:Vlan:vnet managed object property"
    ::= { cfprApVnicVlanEntry 16 }

cfprApVnicVmqConPolicyTable OBJECT-TYPE
    SYNTAX           SEQUENCE OF CfprApVnicVmqConPolicyEntry
    MAX-ACCESS       not-accessible
    STATUS           current
    DESCRIPTION
        "Cisco Firepower vnic:VmqConPolicy managed object table"
    ::= { cfprApVnicObjects 66 }

cfprApVnicVmqConPolicyEntry OBJECT-TYPE
    SYNTAX           CfprApVnicVmqConPolicyEntry
    MAX-ACCESS       not-accessible
    STATUS           current
    DESCRIPTION
        "Entry for the cfprApVnicVmqConPolicyTable table."
    INDEX { cfprApVnicVmqConPolicyInstanceId }
    ::= { cfprApVnicVmqConPolicyTable 1 }

CfprApVnicVmqConPolicyEntry ::= SEQUENCE {
    cfprApVnicVmqConPolicyInstanceId                                 CfprApManagedObjectId,
    cfprApVnicVmqConPolicyDn                                         CfprApManagedObjectDn,
    cfprApVnicVmqConPolicyRn                                         SnmpAdminString,
    cfprApVnicVmqConPolicyDescr                                      SnmpAdminString,
    cfprApVnicVmqConPolicyIntId                                      SnmpAdminString,
    cfprApVnicVmqConPolicyIntrCount                                  Gauge32,
    cfprApVnicVmqConPolicyName                                       SnmpAdminString,
    cfprApVnicVmqConPolicyPolicyLevel                                Gauge32,
    cfprApVnicVmqConPolicyPolicyOwner                                CfprApPolicyPolicyOwner,
    cfprApVnicVmqConPolicyVmqCount                                   Gauge32
}

cfprApVnicVmqConPolicyInstanceId OBJECT-TYPE
    SYNTAX       CfprApManagedObjectId
    MAX-ACCESS   not-accessible
    STATUS       current
    DESCRIPTION
        "Instance identifier of the managed object."
    ::= { cfprApVnicVmqConPolicyEntry 1 }

cfprApVnicVmqConPolicyDn OBJECT-TYPE
    SYNTAX       CfprApManagedObjectDn
    MAX-ACCESS   read-only
    STATUS       current
    DESCRIPTION
        "Cisco Firepower vnic:VmqConPolicy:dn managed object property"
    ::= { cfprApVnicVmqConPolicyEntry 2 }

cfprApVnicVmqConPolicyRn OBJECT-TYPE
    SYNTAX       SnmpAdminString
    MAX-ACCESS   read-only
    STATUS       current
    DESCRIPTION
        "Cisco Firepower vnic:VmqConPolicy:rn managed object property"
    ::= { cfprApVnicVmqConPolicyEntry 3 }

cfprApVnicVmqConPolicyDescr OBJECT-TYPE
    SYNTAX       SnmpAdminString
    MAX-ACCESS   read-only
    STATUS       current
    DESCRIPTION
        "Cisco Firepower vnic:VmqConPolicy:descr managed object property"
    ::= { cfprApVnicVmqConPolicyEntry 4 }

cfprApVnicVmqConPolicyIntId OBJECT-TYPE
    SYNTAX       SnmpAdminString
    MAX-ACCESS   read-only
    STATUS       current
    DESCRIPTION
        "Cisco Firepower vnic:VmqConPolicy:intId managed object property"
    ::= { cfprApVnicVmqConPolicyEntry 5 }

cfprApVnicVmqConPolicyIntrCount OBJECT-TYPE
    SYNTAX       Gauge32
    MAX-ACCESS   read-only
    STATUS       current
    DESCRIPTION
        "Cisco Firepower vnic:VmqConPolicy:intrCount managed
        object property"
    ::= { cfprApVnicVmqConPolicyEntry 6 }

cfprApVnicVmqConPolicyName OBJECT-TYPE
    SYNTAX       SnmpAdminString
    MAX-ACCESS   read-only
    STATUS       current
    DESCRIPTION
        "Cisco Firepower vnic:VmqConPolicy:name managed object property"
    ::= { cfprApVnicVmqConPolicyEntry 7 }

cfprApVnicVmqConPolicyPolicyLevel OBJECT-TYPE
    SYNTAX       Gauge32
    MAX-ACCESS   read-only
    STATUS       current
    DESCRIPTION
        "Cisco Firepower vnic:VmqConPolicy:policyLevel
        managed object property"
    ::= { cfprApVnicVmqConPolicyEntry 8 }

cfprApVnicVmqConPolicyPolicyOwner OBJECT-TYPE
    SYNTAX       CfprApPolicyPolicyOwner
    MAX-ACCESS   read-only
    STATUS       current
    DESCRIPTION
        "Cisco Firepower vnic:VmqConPolicy:policyOwner
        managed object property"
    ::= { cfprApVnicVmqConPolicyEntry 9 }

cfprApVnicVmqConPolicyVmqCount OBJECT-TYPE
    SYNTAX       Gauge32
    MAX-ACCESS   read-only
    STATUS       current
    DESCRIPTION
        "Cisco Firepower vnic:VmqConPolicy:vmqCount managed
        object property"
    ::= { cfprApVnicVmqConPolicyEntry 10 }

cfprApVnicVmqConPolicyRefTable OBJECT-TYPE
    SYNTAX           SEQUENCE OF CfprApVnicVmqConPolicyRefEntry
    MAX-ACCESS       not-accessible
    STATUS           current
    DESCRIPTION
        "Cisco Firepower vnic:VmqConPolicyRef managed object table"
    ::= { cfprApVnicObjects 67 }

cfprApVnicVmqConPolicyRefEntry OBJECT-TYPE
    SYNTAX           CfprApVnicVmqConPolicyRefEntry
    MAX-ACCESS       not-accessible
    STATUS           current
    DESCRIPTION
        "Entry for the cfprApVnicVmqConPolicyRefTable table."
    INDEX { cfprApVnicVmqConPolicyRefInstanceId }
    ::= { cfprApVnicVmqConPolicyRefTable 1 }

CfprApVnicVmqConPolicyRefEntry ::= SEQUENCE {
    cfprApVnicVmqConPolicyRefInstanceId                              CfprApManagedObjectId,
    cfprApVnicVmqConPolicyRefDn                                      CfprApManagedObjectDn,
    cfprApVnicVmqConPolicyRefRn                                      SnmpAdminString,
    cfprApVnicVmqConPolicyRefConPolicyName                           SnmpAdminString,
    cfprApVnicVmqConPolicyRefOperConPolicyName                       SnmpAdminString
}

cfprApVnicVmqConPolicyRefInstanceId OBJECT-TYPE
    SYNTAX       CfprApManagedObjectId
    MAX-ACCESS   not-accessible
    STATUS       current
    DESCRIPTION
        "Instance identifier of the managed object."
    ::= { cfprApVnicVmqConPolicyRefEntry 1 }

cfprApVnicVmqConPolicyRefDn OBJECT-TYPE
    SYNTAX       CfprApManagedObjectDn
    MAX-ACCESS   read-only
    STATUS       current
    DESCRIPTION
        "Cisco Firepower vnic:VmqConPolicyRef:dn managed object property"
    ::= { cfprApVnicVmqConPolicyRefEntry 2 }

cfprApVnicVmqConPolicyRefRn OBJECT-TYPE
    SYNTAX       SnmpAdminString
    MAX-ACCESS   read-only
    STATUS       current
    DESCRIPTION
        "Cisco Firepower vnic:VmqConPolicyRef:rn managed object property"
    ::= { cfprApVnicVmqConPolicyRefEntry 3 }

cfprApVnicVmqConPolicyRefConPolicyName OBJECT-TYPE
    SYNTAX       SnmpAdminString
    MAX-ACCESS   read-only
    STATUS       current
    DESCRIPTION
        "Cisco Firepower vnic:VmqConPolicyRef:conPolicyName
        managed object property"
    ::= { cfprApVnicVmqConPolicyRefEntry 4 }

cfprApVnicVmqConPolicyRefOperConPolicyName OBJECT-TYPE
    SYNTAX       SnmpAdminString
    MAX-ACCESS   read-only
    STATUS       current
    DESCRIPTION
        "Cisco Firepower vnic:VmqConPolicyRef:operConPolicyName
        managed object property"
    ::= { cfprApVnicVmqConPolicyRefEntry 5 }

cfprApVnicVnicBehPolicyTable OBJECT-TYPE
    SYNTAX           SEQUENCE OF CfprApVnicVnicBehPolicyEntry
    MAX-ACCESS       not-accessible
    STATUS           current
    DESCRIPTION
        "Cisco Firepower vnic:VnicBehPolicy managed object table"
    ::= { cfprApVnicObjects 68 }

cfprApVnicVnicBehPolicyEntry OBJECT-TYPE
    SYNTAX           CfprApVnicVnicBehPolicyEntry
    MAX-ACCESS       not-accessible
    STATUS           current
    DESCRIPTION
        "Entry for the cfprApVnicVnicBehPolicyTable table."
    INDEX { cfprApVnicVnicBehPolicyInstanceId }
    ::= { cfprApVnicVnicBehPolicyTable 1 }

CfprApVnicVnicBehPolicyEntry ::= SEQUENCE {
    cfprApVnicVnicBehPolicyInstanceId                                CfprApManagedObjectId,
    cfprApVnicVnicBehPolicyDn                                        CfprApManagedObjectDn,
    cfprApVnicVnicBehPolicyRn                                        SnmpAdminString,
    cfprApVnicVnicBehPolicyAction                                    CfprApVnicDefaultAction,
    cfprApVnicVnicBehPolicyDescr                                     SnmpAdminString,
    cfprApVnicVnicBehPolicyIntId                                     SnmpAdminString,
    cfprApVnicVnicBehPolicyName                                      SnmpAdminString,
    cfprApVnicVnicBehPolicyNwTemplName                               SnmpAdminString,
    cfprApVnicVnicBehPolicyPolicyLevel                               Gauge32,
    cfprApVnicVnicBehPolicyPolicyOwner                               CfprApPolicyPolicyOwner,
    cfprApVnicVnicBehPolicyType                                      CfprApVnicVnicBehPolicyType
}

cfprApVnicVnicBehPolicyInstanceId OBJECT-TYPE
    SYNTAX       CfprApManagedObjectId
    MAX-ACCESS   not-accessible
    STATUS       current
    DESCRIPTION
        "Instance identifier of the managed object."
    ::= { cfprApVnicVnicBehPolicyEntry 1 }

cfprApVnicVnicBehPolicyDn OBJECT-TYPE
    SYNTAX       CfprApManagedObjectDn
    MAX-ACCESS   read-only
    STATUS       current
    DESCRIPTION
        "Cisco Firepower vnic:VnicBehPolicy:dn managed object property"
    ::= { cfprApVnicVnicBehPolicyEntry 2 }

cfprApVnicVnicBehPolicyRn OBJECT-TYPE
    SYNTAX       SnmpAdminString
    MAX-ACCESS   read-only
    STATUS       current
    DESCRIPTION
        "Cisco Firepower vnic:VnicBehPolicy:rn managed object property"
    ::= { cfprApVnicVnicBehPolicyEntry 3 }

cfprApVnicVnicBehPolicyAction OBJECT-TYPE
    SYNTAX       CfprApVnicDefaultAction
    MAX-ACCESS   read-only
    STATUS       current
    DESCRIPTION
        "Cisco Firepower vnic:VnicBehPolicy:action managed
        object property"
    ::= { cfprApVnicVnicBehPolicyEntry 4 }

cfprApVnicVnicBehPolicyDescr OBJECT-TYPE
    SYNTAX       SnmpAdminString
    MAX-ACCESS   read-only
    STATUS       current
    DESCRIPTION
        "Cisco Firepower vnic:VnicBehPolicy:descr managed object property"
    ::= { cfprApVnicVnicBehPolicyEntry 5 }

cfprApVnicVnicBehPolicyIntId OBJECT-TYPE
    SYNTAX       SnmpAdminString
    MAX-ACCESS   read-only
    STATUS       current
    DESCRIPTION
        "Cisco Firepower vnic:VnicBehPolicy:intId managed object property"
    ::= { cfprApVnicVnicBehPolicyEntry 6 }

cfprApVnicVnicBehPolicyName OBJECT-TYPE
    SYNTAX       SnmpAdminString
    MAX-ACCESS   read-only
    STATUS       current
    DESCRIPTION
        "Cisco Firepower vnic:VnicBehPolicy:name managed object property"
    ::= { cfprApVnicVnicBehPolicyEntry 7 }

cfprApVnicVnicBehPolicyNwTemplName OBJECT-TYPE
    SYNTAX       SnmpAdminString
    MAX-ACCESS   read-only
    STATUS       current
    DESCRIPTION
        "Cisco Firepower vnic:VnicBehPolicy:nwTemplName
        managed object property"
    ::= { cfprApVnicVnicBehPolicyEntry 8 }

cfprApVnicVnicBehPolicyPolicyLevel OBJECT-TYPE
    SYNTAX       Gauge32
    MAX-ACCESS   read-only
    STATUS       current
    DESCRIPTION
        "Cisco Firepower vnic:VnicBehPolicy:policyLevel
        managed object property"
    ::= { cfprApVnicVnicBehPolicyEntry 9 }

cfprApVnicVnicBehPolicyPolicyOwner OBJECT-TYPE
    SYNTAX       CfprApPolicyPolicyOwner
    MAX-ACCESS   read-only
    STATUS       current
    DESCRIPTION
        "Cisco Firepower vnic:VnicBehPolicy:policyOwner
        managed object property"
    ::= { cfprApVnicVnicBehPolicyEntry 10 }

cfprApVnicVnicBehPolicyType OBJECT-TYPE
    SYNTAX       CfprApVnicVnicBehPolicyType
    MAX-ACCESS   read-only
    STATUS       current
    DESCRIPTION
        "Cisco Firepower vnic:VnicBehPolicy:type managed object property"
    ::= { cfprApVnicVnicBehPolicyEntry 11 }

cfprApVnicWwpnHistoryTable OBJECT-TYPE
    SYNTAX           SEQUENCE OF CfprApVnicWwpnHistoryEntry
    MAX-ACCESS       not-accessible
    STATUS           current
    DESCRIPTION
        "Cisco Firepower vnic:WwpnHistory managed object table"
    ::= { cfprApVnicObjects 70 }

cfprApVnicWwpnHistoryEntry OBJECT-TYPE
    SYNTAX           CfprApVnicWwpnHistoryEntry
    MAX-ACCESS       not-accessible
    STATUS           current
    DESCRIPTION
        "Entry for the cfprApVnicWwpnHistoryTable table."
    INDEX { cfprApVnicWwpnHistoryInstanceId }
    ::= { cfprApVnicWwpnHistoryTable 1 }

CfprApVnicWwpnHistoryEntry ::= SEQUENCE {
    cfprApVnicWwpnHistoryInstanceId                                  CfprApManagedObjectId,
    cfprApVnicWwpnHistoryDn                                          CfprApManagedObjectDn,
    cfprApVnicWwpnHistoryRn                                          SnmpAdminString,
    cfprApVnicWwpnHistoryOldaddr                                     Unsigned64
}

cfprApVnicWwpnHistoryInstanceId OBJECT-TYPE
    SYNTAX       CfprApManagedObjectId
    MAX-ACCESS   not-accessible
    STATUS       current
    DESCRIPTION
        "Instance identifier of the managed object."
    ::= { cfprApVnicWwpnHistoryEntry 1 }

cfprApVnicWwpnHistoryDn OBJECT-TYPE
    SYNTAX       CfprApManagedObjectDn
    MAX-ACCESS   read-only
    STATUS       current
    DESCRIPTION
        "Cisco Firepower vnic:WwpnHistory:dn managed object property"
    ::= { cfprApVnicWwpnHistoryEntry 2 }

cfprApVnicWwpnHistoryRn OBJECT-TYPE
    SYNTAX       SnmpAdminString
    MAX-ACCESS   read-only
    STATUS       current
    DESCRIPTION
        "Cisco Firepower vnic:WwpnHistory:rn managed object property"
    ::= { cfprApVnicWwpnHistoryEntry 3 }

cfprApVnicWwpnHistoryOldaddr OBJECT-TYPE
    SYNTAX       Unsigned64
    MAX-ACCESS   read-only
    STATUS       current
    DESCRIPTION
        "Cisco Firepower vnic:WwpnHistory:oldaddr managed object property"
    ::= { cfprApVnicWwpnHistoryEntry 4 }

END
