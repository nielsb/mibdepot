-- *********************************************************************
-- CISCO-FIREPOWER-AP-FIRMWARE-MIB.my
-- 
-- MIB representation of the Cisco Firepower
-- FIRMWARE management information model package
-- 
-- Created July 2022 by Charles Bullis
-- 
-- Copyright (c) 2005-2022 Cisco Systems, Inc. All rights reserved.
-- 
-- *********************************************************************

CISCO-FIREPOWER-AP-FIRMWARE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApConditionRemoteInvRslt,
    CfprApExtpolConnProtocol,
    CfprApFirmwareAdminState,
    CfprApFirmwareAutoSyncConfigIssue,
    CfprApFirmwareAutoSyncState,
    CfprApFirmwareBootUnitImage,
    CfprApFirmwareBootUnitMode,
    CfprApFirmwareCatalogPackConfigState,
    CfprApFirmwareCompleteness,
    CfprApFirmwareComponentType,
    CfprApFirmwareDependencyRelationship,
    CfprApFirmwareDependencyScope,
    CfprApFirmwareDependencySensitivity,
    CfprApFirmwareDistributableFsmCurrentFsm,
    CfprApFirmwareDistributableFsmStageName,
    CfprApFirmwareDistributableFsmTaskItem,
    CfprApFirmwareDistributableType,
    CfprApFirmwareDownloadActivity,
    CfprApFirmwareDownloaderFsmCurrentFsm,
    CfprApFirmwareDownloaderFsmStageName,
    CfprApFirmwareDownloaderFsmTaskItem,
    CfprApFirmwareEquipmentType,
    CfprApFirmwareFirmwareState,
    CfprApFirmwareFwState,
    CfprApFirmwareFwUpgradeState,
    CfprApFirmwareHostPackConfigQualifier,
    CfprApFirmwareImageDeleted,
    CfprApFirmwareImageError,
    CfprApFirmwareImageFsmCurrentFsm,
    CfprApFirmwareImageFsmStageName,
    CfprApFirmwareImageFsmTaskItem,
    CfprApFirmwareImagePresence,
    CfprApFirmwareImageState,
    CfprApFirmwareImpactType,
    CfprApFirmwareInfraPackFsmCurrentFsm,
    CfprApFirmwareInfraPackFsmStageName,
    CfprApFirmwareInfraPackFsmTaskFlags,
    CfprApFirmwareInfraPackFsmTaskItem,
    CfprApFirmwareInstallState,
    CfprApFirmwareItemType,
    CfprApFirmwarePackItemPresence,
    CfprApFirmwarePackMode,
    CfprApFirmwarePlatformPackFsmCurrentFsm,
    CfprApFirmwarePlatformPackFsmStageName,
    CfprApFirmwarePlatformPackFsmTaskFlags,
    CfprApFirmwarePlatformPackFsmTaskItem,
    CfprApFirmwarePlatformType,
    CfprApFirmwareRunningDeployment,
    CfprApFirmwareSupFirmwareFsmCurrentFsm,
    CfprApFirmwareSupFirmwareFsmStageName,
    CfprApFirmwareSupFirmwareFsmTaskFlags,
    CfprApFirmwareSupFirmwareFsmTaskItem,
    CfprApFirmwareSystemFsmCurrentFsm,
    CfprApFirmwareSystemFsmStageName,
    CfprApFirmwareSystemFsmTaskFlags,
    CfprApFirmwareSystemFsmTaskItem,
    CfprApFirmwareTransferState,
    CfprApFirmwareTransport,
    CfprApFirmwareTriggerState,
    CfprApFirmwareType,
    CfprApFirmwareUpdatableDeployment,
    CfprApFirmwareUpgradeCategory,
    CfprApFirmwareUpgradeSeverity,
    CfprApFirmwareUpgradeState,
    CfprApFirmwareUpgradeStatus,
    CfprApFsmCompletion,
    CfprApFsmFlags,
    CfprApFsmFsmStageStatus,
    CfprApPolicyPolicyOwner,
    CfprApTrigAckChangeDetails,
    CfprApTrigAckChanges,
    CfprApTrigAckDisr,
    CfprApTrigAckOperState,
    CfprApTrigAckPrevOperState,
    CfprApTrigAdminState,
    CfprApTrigTrigOperState
        FROM CISCO-FIREPOWER-AP-TC-MIB;

cfprApFirmwareObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FIRMWARE management information model package"
    ::= { ciscoFirepowerApMIBObjects 30 }

cfprApFirmwareAckTable OBJECT-TYPE
    SYNTAX           SEQUENCE OF CfprApFirmwareAckEntry
    MAX-ACCESS       not-accessible
    STATUS           current
    DESCRIPTION
        "Cisco Firepower firmware:Ack managed object table"
    ::= { cfprApFirmwareObjects 1 }

cfprApFirmwareAckEntry OBJECT-TYPE
    SYNTAX           CfprApFirmwareAckEntry
    MAX-ACCESS       not-accessible
    STATUS           current
    DESCRIPTION
        "Entry for the cfprApFirmwareAckTable table."
    INDEX { cfprApFirmwareAckInstanceId }
    ::= { cfprApFirmwareAckTable 1 }

CfprApFirmwareAckEntry ::= SEQUENCE {
    cfprApFirmwareAckInstanceId                                      CfprApManagedObjectId,
    cfprApFirmwareAckDn                                              CfprApManagedObjectDn,
    cfprApFirmwareAckRn                                              SnmpAdminString,
    cfprApFirmwareAckAcked                                           DateAndTime,
    cfprApFirmwareAckAckedBy                                         SnmpAdminString,
    cfprApFirmwareAckAdminState                                      CfprApTrigAdminState,
    cfprApFirmwareAckAutoDelete                                      TruthValue,
    cfprApFirmwareAckChangeBy                                        SnmpAdminString,
    cfprApFirmwareAckChangeDetails                                   CfprApTrigAckChangeDetails,
    cfprApFirmwareAckChanges                                         CfprApTrigAckChanges,
    cfprApFirmwareAckDescr                                           SnmpAdminString,
    cfprApFirmwareAckDisr                                            CfprApTrigAckDisr,
    cfprApFirmwareAckIgnoreCap                                       TruthValue,
    cfprApFirmwareAckIntId                                           SnmpAdminString,
    cfprApFirmwareAckModified                                        DateAndTime,
    cfprApFirmwareAckName                                            SnmpAdminString,
    cfprApFirmwareAckOperScheduler                                   SnmpAdminString,
    cfprApFirmwareAckOperState                                       CfprApTrigAckOperState,
    cfprApFirmwareAckPolicyLevel                                     Gauge32,
    cfprApFirmwareAckPolicyOwner                                     CfprApPolicyPolicyOwner,
    cfprApFirmwareAckPrevOperState                                   CfprApTrigAckPrevOperState,
    cfprApFirmwareAckScheduler                                       SnmpAdminString
}

cfprApFirmwareAckInstanceId OBJECT-TYPE
    SYNTAX       CfprApManagedObjectId
    MAX-ACCESS   not-accessible
    STATUS       current
    DESCRIPTION
        "Instance identifier of the managed object."
    ::= { cfprApFirmwareAckEntry 1 }

cfprApFirmwareAckDn OBJECT-TYPE
    SYNTAX       CfprApManagedObjectDn
    MAX-ACCESS   read-only
    STATUS       current
    DESCRIPTION
        "Cisco Firepower firmware:Ack:dn managed object property"
    ::= { cfprApFirmwareAckEntry 2 }

cfprApFirmwareAckRn OBJECT-TYPE
    SYNTAX       SnmpAdminString
    MAX-ACCESS   read-only
    STATUS       current
    DESCRIPTION
        "Cisco Firepower firmware:Ack:rn managed object property"
    ::= { cfprApFirmwareAckEntry 3 }

cfprApFirmwareAckAcked OBJECT-TYPE
    SYNTAX       DateAndTime
    MAX-ACCESS   read-only
    STATUS       current
    DESCRIPTION
        "Cisco Firepower firmware:Ack:acked managed object property"
    ::= { cfprApFirmwareAckEntry 4 }

cfprApFirmwareAckAckedBy OBJECT-TYPE
    SYNTAX       SnmpAdminString
    MAX-ACCESS   read-only
    STATUS       current
    DESCRIPTION
        "Cisco Firepower firmware:Ack:ackedBy managed object property"
    ::= { cfprApFirmwareAckEntry 5 }

cfprApFirmwareAckAdminState OBJECT-TYPE
    SYNTAX       CfprApTrigAdminState
    MAX-ACCESS   read-only
    STATUS       current
    DESCRIPTION
        "Cisco Firepower firmware:Ack:adminState managed object property"
    ::= { cfprApFirmwareAckEntry 6 }

cfprApFirmwareAckAutoDelete OBJECT-TYPE
    SYNTAX       TruthValue
    MAX-ACCESS   read-only
    STATUS       current
    DESCRIPTION
        "Cisco Firepower firmware:Ack:autoDelete managed object property"
    ::= { cfprApFirmwareAckEntry 7 }

cfprApFirmwareAckChangeBy OBJECT-TYPE
    SYNTAX       SnmpAdminString
    MAX-ACCESS   read-only
    STATUS       current
    DESCRIPTION
        "Cisco Firepower firmware:Ack:changeBy managed object property"
    ::= { cfprApFirmwareAckEntry 8 }

cfprApFirmwareAckChangeDetails OBJECT-TYPE
    SYNTAX       CfprApTrigAckChangeDetails
    MAX-ACCESS   read-only
    STATUS       current
    DESCRIPTION
        "Cisco Firepower firmware:Ack:changeDetails managed
        object property"
    ::= { cfprApFirmwareAckEntry 9 }

cfprApFirmwareAckChanges OBJECT-TYPE
    SYNTAX       CfprApTrigAckChanges
    MAX-ACCESS   read-only
    STATUS       current
    DESCRIPTION
        "Cisco Firepower firmware:Ack:changes managed object property"
    ::= { cfprApFirmwareAckEntry 10 }

cfprApFirmwareAckDescr OBJECT-TYPE
    SYNTAX       SnmpAdminString
    MAX-ACCESS   read-only
    STATUS       current
    DESCRIPTION
        "Cisco Firepower firmware:Ack:descr managed object property"
    ::= { cfprApFirmwareAckEntry 11 }

cfprApFirmwareAckDisr OBJECT-TYPE
    SYNTAX       CfprApTrigAckDisr
    MAX-ACCESS   read-only
    STATUS       current
    DESCRIPTION
        "Cisco Firepower firmware:Ack:disr managed object property"
    ::= { cfprApFirmwareAckEntry 12 }

cfprApFirmwareAckIgnoreCap OBJECT-TYPE
    SYNTAX       TruthValue
    MAX-ACCESS   read-only
    STATUS       current
    DESCRIPTION
        "Cisco Firepower firmware:Ack:ignoreCap managed object property"
    ::= { cfprApFirmwareAckEntry 13 }

cfprApFirmwareAckIntId OBJECT-TYPE
    SYNTAX       SnmpAdminString
    MAX-ACCESS   read-only
    STATUS       current
    DESCRIPTION
        "Cisco Firepower firmware:Ack:intId managed object property"
    ::= { cfprApFirmwareAckEntry 14 }

cfprApFirmwareAckModified OBJECT-TYPE
    SYNTAX       DateAndTime
    MAX-ACCESS   read-only
    STATUS       current
    DESCRIPTION
        "Cisco Firepower firmware:Ack:modified managed object property"
    ::= { cfprApFirmwareAckEntry 15 }

cfprApFirmwareAckName OBJECT-TYPE
    SYNTAX       SnmpAdminString
    MAX-ACCESS   read-only
    STATUS       current
    DESCRIPTION
        "Cisco Firepower firmware:Ack:name managed object property"
    ::= { cfprApFirmwareAckEntry 16 }

cfprApFirmwareAckOperScheduler OBJECT-TYPE
    SYNTAX       SnmpAdminString
    MAX-ACCESS   read-only
    STATUS       current
    DESCRIPTION
        "Cisco Firepower firmware:Ack:operScheduler managed
        object property"
    ::= { cfprApFirmwareAckEntry 17 }

cfprApFirmwareAckOperState OBJECT-TYPE
    SYNTAX       CfprApTrigAckOperState
    MAX-ACCESS   read-only
    STATUS       current
    DESCRIPTION
        "Cisco Firepower firmware:Ack:operState managed object property"
    ::= { cfprApFirmwareAckEntry 18 }

cfprApFirmwareAckPolicyLevel OBJECT-TYPE
    SYNTAX       Gauge32
    MAX-ACCESS   read-only
    STATUS       current
    DESCRIPTION
        "Cisco Firepower firmware:Ack:policyLevel managed object property"
    ::= { cfprApFirmwareAckEntry 19 }

cfprApFirmwareAckPolicyOwner OBJECT-TYPE
    SYNTAX       CfprApPolicyPolicyOwner
    MAX-ACCESS   read-only
    STATUS       current
    DESCRIPTION
        "Cisco Firepower firmware:Ack:policyOwner managed object property"
    ::= { cfprApFirmwareAckEntry 20 }

cfprApFirmwareAckPrevOperState OBJECT-TYPE
    SYNTAX       CfprApTrigAckPrevOperState
    MAX-ACCESS   read-only
    STATUS       current
    DESCRIPTION
        "Cisco Firepower firmware:Ack:prevOperState managed
        object property"
    ::= { cfprApFirmwareAckEntry 21 }

cfprApFirmwareAckScheduler OBJECT-TYPE
    SYNTAX       SnmpAdminString
    MAX-ACCESS   read-only
    STATUS       current
    DESCRIPTION
        "Cisco Firepower firmware:Ack:scheduler managed object property"
    ::= { cfprApFirmwareAckEntry 22 }

cfprApFirmwareAutoSyncPolicyTable OBJECT-TYPE
    SYNTAX           SEQUENCE OF CfprApFirmwareAutoSyncPolicyEntry
    MAX-ACCESS       not-accessible
    STATUS           current
    DESCRIPTION
        "Cisco Firepower firmware:AutoSyncPolicy managed object table"
    ::= { cfprApFirmwareObjects 2 }

cfprApFirmwareAutoSyncPolicyEntry OBJECT-TYPE
    SYNTAX           CfprApFirmwareAutoSyncPolicyEntry
    MAX-ACCESS       not-accessible
    STATUS           current
    DESCRIPTION
        "Entry for the cfprApFirmwareAutoSyncPolicyTable table."
    INDEX { cfprApFirmwareAutoSyncPolicyInstanceId }
    ::= { cfprApFirmwareAutoSyncPolicyTable 1 }

CfprApFirmwareAutoSyncPolicyEntry ::= SEQUENCE {
    cfprApFirmwareAutoSyncPolicyInstanceId                           CfprApManagedObjectId,
    cfprApFirmwareAutoSyncPolicyDn                                   CfprApManagedObjectDn,
    cfprApFirmwareAutoSyncPolicyRn                                   SnmpAdminString,
    cfprApFirmwareAutoSyncPolicyConfigIssue                          CfprApFirmwareAutoSyncConfigIssue,
    cfprApFirmwareAutoSyncPolicyDescr                                SnmpAdminString,
    cfprApFirmwareAutoSyncPolicyIntId                                SnmpAdminString,
    cfprApFirmwareAutoSyncPolicyName                                 SnmpAdminString,
    cfprApFirmwareAutoSyncPolicyPolicyLevel                          Gauge32,
    cfprApFirmwareAutoSyncPolicyPolicyOwner                          CfprApPolicyPolicyOwner,
    cfprApFirmwareAutoSyncPolicySyncState                            CfprApFirmwareAutoSyncState
}

cfprApFirmwareAutoSyncPolicyInstanceId OBJECT-TYPE
    SYNTAX       CfprApManagedObjectId
    MAX-ACCESS   not-accessible
    STATUS       current
    DESCRIPTION
        "Instance identifier of the managed object."
    ::= { cfprApFirmwareAutoSyncPolicyEntry 1 }

cfprApFirmwareAutoSyncPolicyDn OBJECT-TYPE
    SYNTAX       CfprApManagedObjectDn
    MAX-ACCESS   read-only
    STATUS       current
    DESCRIPTION
        "Cisco Firepower firmware:AutoSyncPolicy:dn managed
        object property"
    ::= { cfprApFirmwareAutoSyncPolicyEntry 2 }

cfprApFirmwareAutoSyncPolicyRn OBJECT-TYPE
    SYNTAX       SnmpAdminString
    MAX-ACCESS   read-only
    STATUS       current
    DESCRIPTION
        "Cisco Firepower firmware:AutoSyncPolicy:rn managed
        object property"
    ::= { cfprApFirmwareAutoSyncPolicyEntry 3 }

cfprApFirmwareAutoSyncPolicyConfigIssue OBJECT-TYPE
    SYNTAX       CfprApFirmwareAutoSyncConfigIssue
    MAX-ACCESS   read-only
    STATUS       current
    DESCRIPTION
        "Cisco Firepower firmware:AutoSyncPolicy:configIssue
        managed object property"
    ::= { cfprApFirmwareAutoSyncPolicyEntry 4 }

cfprApFirmwareAutoSyncPolicyDescr OBJECT-TYPE
    SYNTAX       SnmpAdminString
    MAX-ACCESS   read-only
    STATUS       current
    DESCRIPTION
        "Cisco Firepower firmware:AutoSyncPolicy:descr
        managed object property"
    ::= { cfprApFirmwareAutoSyncPolicyEntry 5 }

cfprApFirmwareAutoSyncPolicyIntId OBJECT-TYPE
    SYNTAX       SnmpAdminString
    MAX-ACCESS   read-only
    STATUS       current
    DESCRIPTION
        "Cisco Firepower firmware:AutoSyncPolicy:intId
        managed object property"
    ::= { cfprApFirmwareAutoSyncPolicyEntry 6 }

cfprApFirmwareAutoSyncPolicyName OBJECT-TYPE
    SYNTAX       SnmpAdminString
    MAX-ACCESS   read-only
    STATUS       current
    DESCRIPTION
        "Cisco Firepower firmware:AutoSyncPolicy:name managed
        object property"
    ::= { cfprApFirmwareAutoSyncPolicyEntry 7 }

cfprApFirmwareAutoSyncPolicyPolicyLevel OBJECT-TYPE
    SYNTAX       Gauge32
    MAX-ACCESS   read-only
    STATUS       current
    DESCRIPTION
        "Cisco Firepower firmware:AutoSyncPolicy:policyLevel
        managed object property"
    ::= { cfprApFirmwareAutoSyncPolicyEntry 8 }

cfprApFirmwareAutoSyncPolicyPolicyOwner OBJECT-TYPE
    SYNTAX       CfprApPolicyPolicyOwner
    MAX-ACCESS   read-only
    STATUS       current
    DESCRIPTION
        "Cisco Firepower firmware:AutoSyncPolicy:policyOwner
        managed object property"
    ::= { cfprApFirmwareAutoSyncPolicyEntry 9 }

cfprApFirmwareAutoSyncPolicySyncState OBJECT-TYPE
    SYNTAX       CfprApFirmwareAutoSyncState
    MAX-ACCESS   read-only
    STATUS       current
    DESCRIPTION
        "Cisco Firepower firmware:AutoSyncPolicy:syncState
        managed object property"
    ::= { cfprApFirmwareAutoSyncPolicyEntry 10 }

cfprApFirmwareBladeTable OBJECT-TYPE
    SYNTAX           SEQUENCE OF CfprApFirmwareBladeEntry
    MAX-ACCESS       not-accessible
    STATUS           current
    DESCRIPTION
        "Cisco Firepower firmware:Blade managed object table"
    ::= { cfprApFirmwareObjects 3 }

cfprApFirmwareBladeEntry OBJECT-TYPE
    SYNTAX           CfprApFirmwareBladeEntry
    MAX-ACCESS       not-accessible
    STATUS           current
    DESCRIPTION
        "Entry for the cfprApFirmwareBladeTable table."
    INDEX { cfprApFirmwareBladeInstanceId }
    ::= { cfprApFirmwareBladeTable 1 }

CfprApFirmwareBladeEntry ::= SEQUENCE {
    cfprApFirmwareBladeInstanceId                                    CfprApManagedObjectId,
    cfprApFirmwareBladeDn                                            CfprApManagedObjectDn,
    cfprApFirmwareBladeRn                                            SnmpAdminString,
    cfprApFirmwareBladeOperVersion                                   SnmpAdminString
}

cfprApFirmwareBladeInstanceId OBJECT-TYPE
    SYNTAX       CfprApManagedObjectId
    MAX-ACCESS   not-accessible
    STATUS       current
    DESCRIPTION
        "Instance identifier of the managed object."
    ::= { cfprApFirmwareBladeEntry 1 }

cfprApFirmwareBladeDn OBJECT-TYPE
    SYNTAX       CfprApManagedObjectDn
    MAX-ACCESS   read-only
    STATUS       current
    DESCRIPTION
        "Cisco Firepower firmware:Blade:dn managed object property"
    ::= { cfprApFirmwareBladeEntry 2 }

cfprApFirmwareBladeRn OBJECT-TYPE
    SYNTAX       SnmpAdminString
    MAX-ACCESS   read-only
    STATUS       current
    DESCRIPTION
        "Cisco Firepower firmware:Blade:rn managed object property"
    ::= { cfprApFirmwareBladeEntry 3 }

cfprApFirmwareBladeOperVersion OBJECT-TYPE
    SYNTAX       SnmpAdminString
    MAX-ACCESS   read-only
    STATUS       current
    DESCRIPTION
        "Cisco Firepower firmware:Blade:operVersion managed
        object property"
    ::= { cfprApFirmwareBladeEntry 4 }

cfprApFirmwareBootDefinitionTable OBJECT-TYPE
    SYNTAX           SEQUENCE OF CfprApFirmwareBootDefinitionEntry
    MAX-ACCESS       not-accessible
    STATUS           current
    DESCRIPTION
        "Cisco Firepower firmware:BootDefinition managed object table"
    ::= { cfprApFirmwareObjects 4 }

cfprApFirmwareBootDefinitionEntry OBJECT-TYPE
    SYNTAX           CfprApFirmwareBootDefinitionEntry
    MAX-ACCESS       not-accessible
    STATUS           current
    DESCRIPTION
        "Entry for the cfprApFirmwareBootDefinitionTable table."
    INDEX { cfprApFirmwareBootDefinitionInstanceId }
    ::= { cfprApFirmwareBootDefinitionTable 1 }

CfprApFirmwareBootDefinitionEntry ::= SEQUENCE {
    cfprApFirmwareBootDefinitionInstanceId                           CfprApManagedObjectId,
    cfprApFirmwareBootDefinitionDn                                   CfprApManagedObjectDn,
    cfprApFirmwareBootDefinitionRn                                   SnmpAdminString,
    cfprApFirmwareBootDefinitionType                                 CfprApFirmwareType
}

cfprApFirmwareBootDefinitionInstanceId OBJECT-TYPE
    SYNTAX       CfprApManagedObjectId
    MAX-ACCESS   not-accessible
    STATUS       current
    DESCRIPTION
        "Instance identifier of the managed object."
    ::= { cfprApFirmwareBootDefinitionEntry 1 }

cfprApFirmwareBootDefinitionDn OBJECT-TYPE
    SYNTAX       CfprApManagedObjectDn
    MAX-ACCESS   read-only
    STATUS       current
    DESCRIPTION
        "Cisco Firepower firmware:BootDefinition:dn managed
        object property"
    ::= { cfprApFirmwareBootDefinitionEntry 2 }

cfprApFirmwareBootDefinitionRn OBJECT-TYPE
    SYNTAX       SnmpAdminString
    MAX-ACCESS   read-only
    STATUS       current
    DESCRIPTION
        "Cisco Firepower firmware:BootDefinition:rn managed
        object property"
    ::= { cfprApFirmwareBootDefinitionEntry 3 }

cfprApFirmwareBootDefinitionType OBJECT-TYPE
    SYNTAX       CfprApFirmwareType
    MAX-ACCESS   read-only
    STATUS       current
    DESCRIPTION
        "Cisco Firepower firmware:BootDefinition:type managed
        object property"
    ::= { cfprApFirmwareBootDefinitionEntry 4 }

cfprApFirmwareBootUnitTable OBJECT-TYPE
    SYNTAX           SEQUENCE OF CfprApFirmwareBootUnitEntry
    MAX-ACCESS       not-accessible
    STATUS           current
    DESCRIPTION
        "Cisco Firepower firmware:BootUnit managed object table"
    ::= { cfprApFirmwareObjects 5 }

cfprApFirmwareBootUnitEntry OBJECT-TYPE
    SYNTAX           CfprApFirmwareBootUnitEntry
    MAX-ACCESS       not-accessible
    STATUS           current
    DESCRIPTION
        "Entry for the cfprApFirmwareBootUnitTable table."
    INDEX { cfprApFirmwareBootUnitInstanceId }
    ::= { cfprApFirmwareBootUnitTable 1 }

CfprApFirmwareBootUnitEntry ::= SEQUENCE {
    cfprApFirmwareBootUnitInstanceId                                 CfprApManagedObjectId,
    cfprApFirmwareBootUnitDn                                         CfprApManagedObjectDn,
    cfprApFirmwareBootUnitRn                                         SnmpAdminString,
    cfprApFirmwareBootUnitAdminState                                 CfprApFirmwareTriggerState,
    cfprApFirmwareBootUnitIgnoreCompCheck                            TruthValue,
    cfprApFirmwareBootUnitImage                                      CfprApFirmwareBootUnitImage,
    cfprApFirmwareBootUnitInvTag                                     SnmpAdminString,
    cfprApFirmwareBootUnitMode                                       CfprApFirmwareBootUnitMode,
    cfprApFirmwareBootUnitOperState                                  CfprApFirmwareImageState,
    cfprApFirmwareBootUnitPrevVersion                                SnmpAdminString,
    cfprApFirmwareBootUnitResetOnActivate                            TruthValue,
    cfprApFirmwareBootUnitSkipValidation                             TruthValue,
    cfprApFirmwareBootUnitType                                       CfprApFirmwareComponentType,
    cfprApFirmwareBootUnitVersion                                    SnmpAdminString
}

cfprApFirmwareBootUnitInstanceId OBJECT-TYPE
    SYNTAX       CfprApManagedObjectId
    MAX-ACCESS   not-accessible
    STATUS       current
    DESCRIPTION
        "Instance identifier of the managed object."
    ::= { cfprApFirmwareBootUnitEntry 1 }

cfprApFirmwareBootUnitDn OBJECT-TYPE
    SYNTAX       CfprApManagedObjectDn
    MAX-ACCESS   read-only
    STATUS       current
    DESCRIPTION
        "Cisco Firepower firmware:BootUnit:dn managed object property"
    ::= { cfprApFirmwareBootUnitEntry 2 }

cfprApFirmwareBootUnitRn OBJECT-TYPE
    SYNTAX       SnmpAdminString
    MAX-ACCESS   read-only
    STATUS       current
    DESCRIPTION
        "Cisco Firepower firmware:BootUnit:rn managed object property"
    ::= { cfprApFirmwareBootUnitEntry 3 }

cfprApFirmwareBootUnitAdminState OBJECT-TYPE
    SYNTAX       CfprApFirmwareTriggerState
    MAX-ACCESS   read-only
    STATUS       current
    DESCRIPTION
        "Cisco Firepower firmware:BootUnit:adminState managed
        object property"
    ::= { cfprApFirmwareBootUnitEntry 4 }

cfprApFirmwareBootUnitIgnoreCompCheck OBJECT-TYPE
    SYNTAX       TruthValue
    MAX-ACCESS   read-only
    STATUS       current
    DESCRIPTION
        "Cisco Firepower firmware:BootUnit:ignoreCompCheck
        managed object property"
    ::= { cfprApFirmwareBootUnitEntry 5 }

cfprApFirmwareBootUnitImage OBJECT-TYPE
    SYNTAX       CfprApFirmwareBootUnitImage
    MAX-ACCESS   read-only
    STATUS       current
    DESCRIPTION
        "Cisco Firepower firmware:BootUnit:image managed object property"
    ::= { cfprApFirmwareBootUnitEntry 6 }

cfprApFirmwareBootUnitInvTag OBJECT-TYPE
    SYNTAX       SnmpAdminString
    MAX-ACCESS   read-only
    STATUS       current
    DESCRIPTION
        "Cisco Firepower firmware:BootUnit:invTag managed object property"
    ::= { cfprApFirmwareBootUnitEntry 7 }

cfprApFirmwareBootUnitMode OBJECT-TYPE
    SYNTAX       CfprApFirmwareBootUnitMode
    MAX-ACCESS   read-only
    STATUS       current
    DESCRIPTION
        "Cisco Firepower firmware:BootUnit:mode managed object property"
    ::= { cfprApFirmwareBootUnitEntry 8 }

cfprApFirmwareBootUnitOperState OBJECT-TYPE
    SYNTAX       CfprApFirmwareImageState
    MAX-ACCESS   read-only
    STATUS       current
    DESCRIPTION
        "Cisco Firepower firmware:BootUnit:operState managed
        object property"
    ::= { cfprApFirmwareBootUnitEntry 9 }

cfprApFirmwareBootUnitPrevVersion OBJECT-TYPE
    SYNTAX       SnmpAdminString
    MAX-ACCESS   read-only
    STATUS       current
    DESCRIPTION
        "Cisco Firepower firmware:BootUnit:prevVersion
        managed object property"
    ::= { cfprApFirmwareBootUnitEntry 10 }

cfprApFirmwareBootUnitResetOnActivate OBJECT-TYPE
    SYNTAX       TruthValue
    MAX-ACCESS   read-only
    STATUS       current
    DESCRIPTION
        "Cisco Firepower firmware:BootUnit:resetOnActivate
        managed object property"
    ::= { cfprApFirmwareBootUnitEntry 11 }

cfprApFirmwareBootUnitSkipValidation OBJECT-TYPE
    SYNTAX       TruthValue
    MAX-ACCESS   read-only
    STATUS       current
    DESCRIPTION
        "Cisco Firepower firmware:BootUnit:skipValidation
        managed object property"
    ::= { cfprApFirmwareBootUnitEntry 12 }

cfprApFirmwareBootUnitType OBJECT-TYPE
    SYNTAX       CfprApFirmwareComponentType
    MAX-ACCESS   read-only
    STATUS       current
    DESCRIPTION
        "Cisco Firepower firmware:BootUnit:type managed object property"
    ::= { cfprApFirmwareBootUnitEntry 13 }

cfprApFirmwareBootUnitVersion OBJECT-TYPE
    SYNTAX       SnmpAdminString
    MAX-ACCESS   read-only
    STATUS       current
    DESCRIPTION
        "Cisco Firepower firmware:BootUnit:version managed
        object property"
    ::= { cfprApFirmwareBootUnitEntry 14 }

cfprApFirmwareBundleInfoTable OBJECT-TYPE
    SYNTAX           SEQUENCE OF CfprApFirmwareBundleInfoEntry
    MAX-ACCESS       not-accessible
    STATUS           current
    DESCRIPTION
        "Cisco Firepower firmware:BundleInfo managed object table"
    ::= { cfprApFirmwareObjects 6 }

cfprApFirmwareBundleInfoEntry OBJECT-TYPE
    SYNTAX           CfprApFirmwareBundleInfoEntry
    MAX-ACCESS       not-accessible
    STATUS           current
    DESCRIPTION
        "Entry for the cfprApFirmwareBundleInfoTable table."
    INDEX { cfprApFirmwareBundleInfoInstanceId }
    ::= { cfprApFirmwareBundleInfoTable 1 }

CfprApFirmwareBundleInfoEntry ::= SEQUENCE {
    cfprApFirmwareBundleInfoInstanceId                               CfprApManagedObjectId,
    cfprApFirmwareBundleInfoDn                                       CfprApManagedObjectDn,
    cfprApFirmwareBundleInfoRn                                       SnmpAdminString,
    cfprApFirmwareBundleInfoType                                     CfprApFirmwareDistributableType,
    cfprApFirmwareBundleInfoVersion                                  SnmpAdminString
}

cfprApFirmwareBundleInfoInstanceId OBJECT-TYPE
    SYNTAX       CfprApManagedObjectId
    MAX-ACCESS   not-accessible
    STATUS       current
    DESCRIPTION
        "Instance identifier of the managed object."
    ::= { cfprApFirmwareBundleInfoEntry 1 }

cfprApFirmwareBundleInfoDn OBJECT-TYPE
    SYNTAX       CfprApManagedObjectDn
    MAX-ACCESS   read-only
    STATUS       current
    DESCRIPTION
        "Cisco Firepower firmware:BundleInfo:dn managed object property"
    ::= { cfprApFirmwareBundleInfoEntry 2 }

cfprApFirmwareBundleInfoRn OBJECT-TYPE
    SYNTAX       SnmpAdminString
    MAX-ACCESS   read-only
    STATUS       current
    DESCRIPTION
        "Cisco Firepower firmware:BundleInfo:rn managed object property"
    ::= { cfprApFirmwareBundleInfoEntry 3 }

cfprApFirmwareBundleInfoType OBJECT-TYPE
    SYNTAX       CfprApFirmwareDistributableType
    MAX-ACCESS   read-only
    STATUS       current
    DESCRIPTION
        "Cisco Firepower firmware:BundleInfo:type managed object property"
    ::= { cfprApFirmwareBundleInfoEntry 4 }

cfprApFirmwareBundleInfoVersion OBJECT-TYPE
    SYNTAX       SnmpAdminString
    MAX-ACCESS   read-only
    STATUS       current
    DESCRIPTION
        "Cisco Firepower firmware:BundleInfo:version managed
        object property"
    ::= { cfprApFirmwareBundleInfoEntry 5 }

cfprApFirmwareBundleInfoDigestTable OBJECT-TYPE
    SYNTAX           SEQUENCE OF CfprApFirmwareBundleInfoDigestEntry
    MAX-ACCESS       not-accessible
    STATUS           current
    DESCRIPTION
        "Cisco Firepower firmware:BundleInfoDigest managed object table"
    ::= { cfprApFirmwareObjects 7 }

cfprApFirmwareBundleInfoDigestEntry OBJECT-TYPE
    SYNTAX           CfprApFirmwareBundleInfoDigestEntry
    MAX-ACCESS       not-accessible
    STATUS           current
    DESCRIPTION
        "Entry for the cfprApFirmwareBundleInfoDigestTable table."
    INDEX { cfprApFirmwareBundleInfoDigestInstanceId }
    ::= { cfprApFirmwareBundleInfoDigestTable 1 }

CfprApFirmwareBundleInfoDigestEntry ::= SEQUENCE {
    cfprApFirmwareBundleInfoDigestInstanceId                         CfprApManagedObjectId,
    cfprApFirmwareBundleInfoDigestDn                                 CfprApManagedObjectDn,
    cfprApFirmwareBundleInfoDigestRn                                 SnmpAdminString,
    cfprApFirmwareBundleInfoDigestBundleName                         SnmpAdminString,
    cfprApFirmwareBundleInfoDigestType                               CfprApFirmwareDistributableType,
    cfprApFirmwareBundleInfoDigestVersion                            SnmpAdminString
}

cfprApFirmwareBundleInfoDigestInstanceId OBJECT-TYPE
    SYNTAX       CfprApManagedObjectId
    MAX-ACCESS   not-accessible
    STATUS       current
    DESCRIPTION
        "Instance identifier of the managed object."
    ::= { cfprApFirmwareBundleInfoDigestEntry 1 }

cfprApFirmwareBundleInfoDigestDn OBJECT-TYPE
    SYNTAX       CfprApManagedObjectDn
    MAX-ACCESS   read-only
    STATUS       current
    DESCRIPTION
        "Cisco Firepower firmware:BundleInfoDigest:dn managed
        object property"
    ::= { cfprApFirmwareBundleInfoDigestEntry 2 }

cfprApFirmwareBundleInfoDigestRn OBJECT-TYPE
    SYNTAX       SnmpAdminString
    MAX-ACCESS   read-only
    STATUS       current
    DESCRIPTION
        "Cisco Firepower firmware:BundleInfoDigest:rn managed
        object property"
    ::= { cfprApFirmwareBundleInfoDigestEntry 3 }

cfprApFirmwareBundleInfoDigestBundleName OBJECT-TYPE
    SYNTAX       SnmpAdminString
    MAX-ACCESS   read-only
    STATUS       current
    DESCRIPTION
        "Cisco Firepower firmware:BundleInfoDigest:bundleName
        managed object property"
    ::= { cfprApFirmwareBundleInfoDigestEntry 4 }

cfprApFirmwareBundleInfoDigestType OBJECT-TYPE
    SYNTAX       CfprApFirmwareDistributableType
    MAX-ACCESS   read-only
    STATUS       current
    DESCRIPTION
        "Cisco Firepower firmware:BundleInfoDigest:type
        managed object property"
    ::= { cfprApFirmwareBundleInfoDigestEntry 5 }

cfprApFirmwareBundleInfoDigestVersion OBJECT-TYPE
    SYNTAX       SnmpAdminString
    MAX-ACCESS   read-only
    STATUS       current
    DESCRIPTION
        "Cisco Firepower firmware:BundleInfoDigest:version
        managed object property"
    ::= { cfprApFirmwareBundleInfoDigestEntry 6 }

cfprApFirmwareBundleTypeTable OBJECT-TYPE
    SYNTAX           SEQUENCE OF CfprApFirmwareBundleTypeEntry
    MAX-ACCESS       not-accessible
    STATUS           current
    DESCRIPTION
        "Cisco Firepower firmware:BundleType managed object table"
    ::= { cfprApFirmwareObjects 8 }

cfprApFirmwareBundleTypeEntry OBJECT-TYPE
    SYNTAX           CfprApFirmwareBundleTypeEntry
    MAX-ACCESS       not-accessible
    STATUS           current
    DESCRIPTION
        "Entry for the cfprApFirmwareBundleTypeTable table."
    INDEX { cfprApFirmwareBundleTypeInstanceId }
    ::= { cfprApFirmwareBundleTypeTable 1 }

CfprApFirmwareBundleTypeEntry ::= SEQUENCE {
    cfprApFirmwareBundleTypeInstanceId                               CfprApManagedObjectId,
    cfprApFirmwareBundleTypeDn                                       CfprApManagedObjectDn,
    cfprApFirmwareBundleTypeRn                                       SnmpAdminString,
    cfprApFirmwareBundleTypeInvTag                                   SnmpAdminString,
    cfprApFirmwareBundleTypeType                                     CfprApFirmwareDistributableType
}

cfprApFirmwareBundleTypeInstanceId OBJECT-TYPE
    SYNTAX       CfprApManagedObjectId
    MAX-ACCESS   not-accessible
    STATUS       current
    DESCRIPTION
        "Instance identifier of the managed object."
    ::= { cfprApFirmwareBundleTypeEntry 1 }

cfprApFirmwareBundleTypeDn OBJECT-TYPE
    SYNTAX       CfprApManagedObjectDn
    MAX-ACCESS   read-only
    STATUS       current
    DESCRIPTION
        "Cisco Firepower firmware:BundleType:dn managed object property"
    ::= { cfprApFirmwareBundleTypeEntry 2 }

cfprApFirmwareBundleTypeRn OBJECT-TYPE
    SYNTAX       SnmpAdminString
    MAX-ACCESS   read-only
    STATUS       current
    DESCRIPTION
        "Cisco Firepower firmware:BundleType:rn managed object property"
    ::= { cfprApFirmwareBundleTypeEntry 3 }

cfprApFirmwareBundleTypeInvTag OBJECT-TYPE
    SYNTAX       SnmpAdminString
    MAX-ACCESS   read-only
    STATUS       current
    DESCRIPTION
        "Cisco Firepower firmware:BundleType:invTag managed
        object property"
    ::= { cfprApFirmwareBundleTypeEntry 4 }

cfprApFirmwareBundleTypeType OBJECT-TYPE
    SYNTAX       CfprApFirmwareDistributableType
    MAX-ACCESS   read-only
    STATUS       current
    DESCRIPTION
        "Cisco Firepower firmware:BundleType:type managed object property"
    ::= { cfprApFirmwareBundleTypeEntry 5 }

cfprApFirmwareBundleTypeCapProviderTable OBJECT-TYPE
    SYNTAX           SEQUENCE OF CfprApFirmwareBundleTypeCapProviderEntry
    MAX-ACCESS       not-accessible
    STATUS           current
    DESCRIPTION
        "Cisco Firepower firmware:BundleTypeCapProvider
        managed object table"
    ::= { cfprApFirmwareObjects 9 }

cfprApFirmwareBundleTypeCapProviderEntry OBJECT-TYPE
    SYNTAX           CfprApFirmwareBundleTypeCapProviderEntry
    MAX-ACCESS       not-accessible
    STATUS           current
    DESCRIPTION
        "Entry for the cfprApFirmwareBundleTypeCapProviderTable table."
    INDEX { cfprApFirmwareBundleTypeCapProviderInstanceId }
    ::= { cfprApFirmwareBundleTypeCapProviderTable 1 }

CfprApFirmwareBundleTypeCapProviderEntry ::= SEQUENCE {
    cfprApFirmwareBundleTypeCapProviderInstanceId                    CfprApManagedObjectId,
    cfprApFirmwareBundleTypeCapProviderDn                            CfprApManagedObjectDn,
    cfprApFirmwareBundleTypeCapProviderRn                            SnmpAdminString,
    cfprApFirmwareBundleTypeCapProviderDeleted                       TruthValue,
    cfprApFirmwareBundleTypeCapProviderDeprecated                    TruthValue,
    cfprApFirmwareBundleTypeCapProviderElementLoadFailures           Gauge32,
    cfprApFirmwareBundleTypeCapProviderElementsLoaded                Gauge32,
    cfprApFirmwareBundleTypeCapProviderGencount                      Gauge32,
    cfprApFirmwareBundleTypeCapProviderLoadErrors                    Gauge32,
    cfprApFirmwareBundleTypeCapProviderLoadWarnings                  Gauge32,
    cfprApFirmwareBundleTypeCapProviderMgmtPlaneVer                  SnmpAdminString,
    cfprApFirmwareBundleTypeCapProviderModel                         SnmpAdminString,
    cfprApFirmwareBundleTypeCapProviderPlatformType                  CfprApFirmwarePlatformType,
    cfprApFirmwareBundleTypeCapProviderVendor                        SnmpAdminString
}

cfprApFirmwareBundleTypeCapProviderInstanceId OBJECT-TYPE
    SYNTAX       CfprApManagedObjectId
    MAX-ACCESS   not-accessible
    STATUS       current
    DESCRIPTION
        "Instance identifier of the managed object."
    ::= { cfprApFirmwareBundleTypeCapProviderEntry 1 }

cfprApFirmwareBundleTypeCapProviderDn OBJECT-TYPE
    SYNTAX       CfprApManagedObjectDn
    MAX-ACCESS   read-only
    STATUS       current
    DESCRIPTION
        "Cisco Firepower firmware:BundleTypeCapProvider:dn
        managed object property"
    ::= { cfprApFirmwareBundleTypeCapProviderEntry 2 }

cfprApFirmwareBundleTypeCapProviderRn OBJECT-TYPE
    SYNTAX       SnmpAdminString
    MAX-ACCESS   read-only
    STATUS       current
    DESCRIPTION
        "Cisco Firepower firmware:BundleTypeCapProvider:rn
        managed object property"
    ::= { cfprApFirmwareBundleTypeCapProviderEntry 3 }

cfprApFirmwareBundleTypeCapProviderDeleted OBJECT-TYPE
    SYNTAX       TruthValue
    MAX-ACCESS   read-only
    STATUS       current
    DESCRIPTION
        "Cisco Firepower firmware:BundleTypeCapProvider:deleted
        managed object property"
    ::= { cfprApFirmwareBundleTypeCapProviderEntry 4 }

cfprApFirmwareBundleTypeCapProviderDeprecated OBJECT-TYPE
    SYNTAX       TruthValue
    MAX-ACCESS   read-only
    STATUS       current
    DESCRIPTION
        "Cisco Firepower firmware:BundleTypeCapProvider:deprecated
        managed object property"
    ::= { cfprApFirmwareBundleTypeCapProviderEntry 5 }

cfprApFirmwareBundleTypeCapProviderElementLoadFailures OBJECT-TYPE
    SYNTAX       Gauge32
    MAX-ACCESS   read-only
    STATUS       current
    DESCRIPTION
        "Cisco Firepower firmware:BundleTypeCapProvider:elementLoadFailure
        s managed object property"
    ::= { cfprApFirmwareBundleTypeCapProviderEntry 6 }

cfprApFirmwareBundleTypeCapProviderElementsLoaded OBJECT-TYPE
    SYNTAX       Gauge32
    MAX-ACCESS   read-only
    STATUS       current
    DESCRIPTION
        "Cisco Firepower firmware:BundleTypeCapProvider:elementsLoaded
        managed object property"
    ::= { cfprApFirmwareBundleTypeCapProviderEntry 7 }

cfprApFirmwareBundleTypeCapProviderGencount OBJECT-TYPE
    SYNTAX       Gauge32
    MAX-ACCESS   read-only
    STATUS       current
    DESCRIPTION
        "Cisco Firepower firmware:BundleTypeCapProvider:gencount
        managed object property"
    ::= { cfprApFirmwareBundleTypeCapProviderEntry 8 }

cfprApFirmwareBundleTypeCapProviderLoadErrors OBJECT-TYPE
    SYNTAX       Gauge32
    MAX-ACCESS   read-only
    STATUS       current
    DESCRIPTION
        "Cisco Firepower firmware:BundleTypeCapProvider:loadErrors
        managed object property"
    ::= { cfprApFirmwareBundleTypeCapProviderEntry 9 }

cfprApFirmwareBundleTypeCapProviderLoadWarnings OBJECT-TYPE
    SYNTAX       Gauge32
    MAX-ACCESS   read-only
    STATUS       current
    DESCRIPTION
        "Cisco Firepower firmware:BundleTypeCapProvider:loadWarnings
        managed object property"
    ::= { cfprApFirmwareBundleTypeCapProviderEntry 10 }

cfprApFirmwareBundleTypeCapProviderMgmtPlaneVer OBJECT-TYPE
    SYNTAX       SnmpAdminString
    MAX-ACCESS   read-only
    STATUS       current
    DESCRIPTION
        "Cisco Firepower firmware:BundleTypeCapProvider:mgmtPlaneVer
        managed object property"
    ::= { cfprApFirmwareBundleTypeCapProviderEntry 11 }

cfprApFirmwareBundleTypeCapProviderModel OBJECT-TYPE
    SYNTAX       SnmpAdminString
    MAX-ACCESS   read-only
    STATUS       current
    DESCRIPTION
        "Cisco Firepower firmware:BundleTypeCapProvider:model
        managed object property"
    ::= { cfprApFirmwareBundleTypeCapProviderEntry 12 }

cfprApFirmwareBundleTypeCapProviderPlatformType OBJECT-TYPE
    SYNTAX       CfprApFirmwarePlatformType
    MAX-ACCESS   read-only
    STATUS       current
    DESCRIPTION
        "Cisco Firepower firmware:BundleTypeCapProvider:platformType
        managed object property"
    ::= { cfprApFirmwareBundleTypeCapProviderEntry 13 }

cfprApFirmwareBundleTypeCapProviderVendor OBJECT-TYPE
    SYNTAX       SnmpAdminString
    MAX-ACCESS   read-only
    STATUS       current
    DESCRIPTION
        "Cisco Firepower firmware:BundleTypeCapProvider:vendor
        managed object property"
    ::= { cfprApFirmwareBundleTypeCapProviderEntry 14 }

cfprApFirmwareCatalogPackTable OBJECT-TYPE
    SYNTAX           SEQUENCE OF CfprApFirmwareCatalogPackEntry
    MAX-ACCESS       not-accessible
    STATUS           current
    DESCRIPTION
        "Cisco Firepower firmware:CatalogPack managed object table"
    ::= { cfprApFirmwareObjects 10 }

cfprApFirmwareCatalogPackEntry OBJECT-TYPE
    SYNTAX           CfprApFirmwareCatalogPackEntry
    MAX-ACCESS       not-accessible
    STATUS           current
    DESCRIPTION
        "Entry for the cfprApFirmwareCatalogPackTable table."
    INDEX { cfprApFirmwareCatalogPackInstanceId }
    ::= { cfprApFirmwareCatalogPackTable 1 }

CfprApFirmwareCatalogPackEntry ::= SEQUENCE {
    cfprApFirmwareCatalogPackInstanceId                              CfprApManagedObjectId,
    cfprApFirmwareCatalogPackDn                                      CfprApManagedObjectDn,
    cfprApFirmwareCatalogPackRn                                      SnmpAdminString,
    cfprApFirmwareCatalogPackCatalogName                             SnmpAdminString,
    cfprApFirmwareCatalogPackCatalogVersion                          SnmpAdminString,
    cfprApFirmwareCatalogPackConfigState                             CfprApFirmwareCatalogPackConfigState,
    cfprApFirmwareCatalogPackConfigStatusMessage                     SnmpAdminString,
    cfprApFirmwareCatalogPackDescr                                   SnmpAdminString,
    cfprApFirmwareCatalogPackIntId                                   SnmpAdminString,
    cfprApFirmwareCatalogPackMode                                    CfprApFirmwarePackMode,
    cfprApFirmwareCatalogPackName                                    SnmpAdminString,
    cfprApFirmwareCatalogPackPolicyLevel                             Gauge32,
    cfprApFirmwareCatalogPackPolicyOwner                             CfprApPolicyPolicyOwner,
    cfprApFirmwareCatalogPackStageSize                               Gauge32,
    cfprApFirmwareCatalogPackUpdateTrigger                           DateAndTime
}

cfprApFirmwareCatalogPackInstanceId OBJECT-TYPE
    SYNTAX       CfprApManagedObjectId
    MAX-ACCESS   not-accessible
    STATUS       current
    DESCRIPTION
        "Instance identifier of the managed object."
    ::= { cfprApFirmwareCatalogPackEntry 1 }

cfprApFirmwareCatalogPackDn OBJECT-TYPE
    SYNTAX       CfprApManagedObjectDn
    MAX-ACCESS   read-only
    STATUS       current
    DESCRIPTION
        "Cisco Firepower firmware:CatalogPack:dn managed object property"
    ::= { cfprApFirmwareCatalogPackEntry 2 }

cfprApFirmwareCatalogPackRn OBJECT-TYPE
    SYNTAX       SnmpAdminString
    MAX-ACCESS   read-only
    STATUS       current
    DESCRIPTION
        "Cisco Firepower firmware:CatalogPack:rn managed object property"
    ::= { cfprApFirmwareCatalogPackEntry 3 }

cfprApFirmwareCatalogPackCatalogName OBJECT-TYPE
    SYNTAX       SnmpAdminString
    MAX-ACCESS   read-only
    STATUS       current
    DESCRIPTION
        "Cisco Firepower firmware:CatalogPack:catalogName
        managed object property"
    ::= { cfprApFirmwareCatalogPackEntry 4 }

cfprApFirmwareCatalogPackCatalogVersion OBJECT-TYPE
    SYNTAX       SnmpAdminString
    MAX-ACCESS   read-only
    STATUS       current
    DESCRIPTION
        "Cisco Firepower firmware:CatalogPack:catalogVersion
        managed object property"
    ::= { cfprApFirmwareCatalogPackEntry 5 }

cfprApFirmwareCatalogPackConfigState OBJECT-TYPE
    SYNTAX       CfprApFirmwareCatalogPackConfigState
    MAX-ACCESS   read-only
    STATUS       current
    DESCRIPTION
        "Cisco Firepower firmware:CatalogPack:configState
        managed object property"
    ::= { cfprApFirmwareCatalogPackEntry 6 }

cfprApFirmwareCatalogPackConfigStatusMessage OBJECT-TYPE
    SYNTAX       SnmpAdminString
    MAX-ACCESS   read-only
    STATUS       current
    DESCRIPTION
        "Cisco Firepower firmware:CatalogPack:configStatusMessage
        managed object property"
    ::= { cfprApFirmwareCatalogPackEntry 7 }

cfprApFirmwareCatalogPackDescr OBJECT-TYPE
    SYNTAX       SnmpAdminString
    MAX-ACCESS   read-only
    STATUS       current
    DESCRIPTION
        "Cisco Firepower firmware:CatalogPack:descr managed
        object property"
    ::= { cfprApFirmwareCatalogPackEntry 8 }

cfprApFirmwareCatalogPackIntId OBJECT-TYPE
    SYNTAX       SnmpAdminString
    MAX-ACCESS   read-only
    STATUS       current
    DESCRIPTION
        "Cisco Firepower firmware:CatalogPack:intId managed
        object property"
    ::= { cfprApFirmwareCatalogPackEntry 9 }

cfprApFirmwareCatalogPackMode OBJECT-TYPE
    SYNTAX       CfprApFirmwarePackMode
    MAX-ACCESS   read-only
    STATUS       current
    DESCRIPTION
        "Cisco Firepower firmware:CatalogPack:mode managed
        object property"
    ::= { cfprApFirmwareCatalogPackEntry 10 }

cfprApFirmwareCatalogPackName OBJECT-TYPE
    SYNTAX       SnmpAdminString
    MAX-ACCESS   read-only
    STATUS       current
    DESCRIPTION
        "Cisco Firepower firmware:CatalogPack:name managed
        object property"
    ::= { cfprApFirmwareCatalogPackEntry 11 }

cfprApFirmwareCatalogPackPolicyLevel OBJECT-TYPE
    SYNTAX       Gauge32
    MAX-ACCESS   read-only
    STATUS       current
    DESCRIPTION
        "Cisco Firepower firmware:CatalogPack:policyLevel
        managed object property"
    ::= { cfprApFirmwareCatalogPackEntry 12 }

cfprApFirmwareCatalogPackPolicyOwner OBJECT-TYPE
    SYNTAX       CfprApPolicyPolicyOwner
    MAX-ACCESS   read-only
    STATUS       current
    DESCRIPTION
        "Cisco Firepower firmware:CatalogPack:policyOwner
        managed object property"
    ::= { cfprApFirmwareCatalogPackEntry 13 }

cfprApFirmwareCatalogPackStageSize OBJECT-TYPE
    SYNTAX       Gauge32
    MAX-ACCESS   read-only
    STATUS       current
    DESCRIPTION
        "Cisco Firepower firmware:CatalogPack:stageSize
        managed object property"
    ::= { cfprApFirmwareCatalogPackEntry 14 }

cfprApFirmwareCatalogPackUpdateTrigger OBJECT-TYPE
    SYNTAX       DateAndTime
    MAX-ACCESS   read-only
    STATUS       current
    DESCRIPTION
        "Cisco Firepower firmware:CatalogPack:updateTrigger
        managed object property"
    ::= { cfprApFirmwareCatalogPackEntry 15 }

cfprApFirmwareCatalogueTable OBJECT-TYPE
    SYNTAX           SEQUENCE OF CfprApFirmwareCatalogueEntry
    MAX-ACCESS       not-accessible
    STATUS           current
    DESCRIPTION
        "Cisco Firepower firmware:Catalogue managed object table"
    ::= { cfprApFirmwareObjects 11 }

cfprApFirmwareCatalogueEntry OBJECT-TYPE
    SYNTAX           CfprApFirmwareCatalogueEntry
    MAX-ACCESS       not-accessible
    STATUS           current
    DESCRIPTION
        "Entry for the cfprApFirmwareCatalogueTable table."
    INDEX { cfprApFirmwareCatalogueInstanceId }
    ::= { cfprApFirmwareCatalogueTable 1 }

CfprApFirmwareCatalogueEntry ::= SEQUENCE {
    cfprApFirmwareCatalogueInstanceId                                CfprApManagedObjectId,
    cfprApFirmwareCatalogueDn                                        CfprApManagedObjectDn,
    cfprApFirmwareCatalogueRn                                        SnmpAdminString,
    cfprApFirmwareCatalogueSyncTrigger                               TruthValue
}

cfprApFirmwareCatalogueInstanceId OBJECT-TYPE
    SYNTAX       CfprApManagedObjectId
    MAX-ACCESS   not-accessible
    STATUS       current
    DESCRIPTION
        "Instance identifier of the managed object."
    ::= { cfprApFirmwareCatalogueEntry 1 }

cfprApFirmwareCatalogueDn OBJECT-TYPE
    SYNTAX       CfprApManagedObjectDn
    MAX-ACCESS   read-only
    STATUS       current
    DESCRIPTION
        "Cisco Firepower firmware:Catalogue:dn managed object property"
    ::= { cfprApFirmwareCatalogueEntry 2 }

cfprApFirmwareCatalogueRn OBJECT-TYPE
    SYNTAX       SnmpAdminString
    MAX-ACCESS   read-only
    STATUS       current
    DESCRIPTION
        "Cisco Firepower firmware:Catalogue:rn managed object property"
    ::= { cfprApFirmwareCatalogueEntry 3 }

cfprApFirmwareCatalogueSyncTrigger OBJECT-TYPE
    SYNTAX       TruthValue
    MAX-ACCESS   read-only
    STATUS       current
    DESCRIPTION
        "Cisco Firepower firmware:Catalogue:syncTrigger
        managed object property"
    ::= { cfprApFirmwareCatalogueEntry 4 }

cfprApFirmwareCompSourceTable OBJECT-TYPE
    SYNTAX           SEQUENCE OF CfprApFirmwareCompSourceEntry
    MAX-ACCESS       not-accessible
    STATUS           current
    DESCRIPTION
        "Cisco Firepower firmware:CompSource managed object table"
    ::= { cfprApFirmwareObjects 12 }

cfprApFirmwareCompSourceEntry OBJECT-TYPE
    SYNTAX           CfprApFirmwareCompSourceEntry
    MAX-ACCESS       not-accessible
    STATUS           current
    DESCRIPTION
        "Entry for the cfprApFirmwareCompSourceTable table."
    INDEX { cfprApFirmwareCompSourceInstanceId }
    ::= { cfprApFirmwareCompSourceTable 1 }

CfprApFirmwareCompSourceEntry ::= SEQUENCE {
    cfprApFirmwareCompSourceInstanceId                               CfprApManagedObjectId,
    cfprApFirmwareCompSourceDn                                       CfprApManagedObjectDn,
    cfprApFirmwareCompSourceRn                                       SnmpAdminString,
    cfprApFirmwareCompSourceDescr                                    SnmpAdminString,
    cfprApFirmwareCompSourceIntId                                    SnmpAdminString,
    cfprApFirmwareCompSourceInvTag                                   SnmpAdminString,
    cfprApFirmwareCompSourceName                                     SnmpAdminString,
    cfprApFirmwareCompSourcePolicyLevel                              Gauge32,
    cfprApFirmwareCompSourcePolicyOwner                              CfprApPolicyPolicyOwner,
    cfprApFirmwareCompSourceVersion                                  SnmpAdminString
}

cfprApFirmwareCompSourceInstanceId OBJECT-TYPE
    SYNTAX       CfprApManagedObjectId
    MAX-ACCESS   not-accessible
    STATUS       current
    DESCRIPTION
        "Instance identifier of the managed object."
    ::= { cfprApFirmwareCompSourceEntry 1 }

cfprApFirmwareCompSourceDn OBJECT-TYPE
    SYNTAX       CfprApManagedObjectDn
    MAX-ACCESS   read-only
    STATUS       current
    DESCRIPTION
        "Cisco Firepower firmware:CompSource:dn managed object property"
    ::= { cfprApFirmwareCompSourceEntry 2 }

cfprApFirmwareCompSourceRn OBJECT-TYPE
    SYNTAX       SnmpAdminString
    MAX-ACCESS   read-only
    STATUS       current
    DESCRIPTION
        "Cisco Firepower firmware:CompSource:rn managed object property"
    ::= { cfprApFirmwareCompSourceEntry 3 }

cfprApFirmwareCompSourceDescr OBJECT-TYPE
    SYNTAX       SnmpAdminString
    MAX-ACCESS   read-only
    STATUS       current
    DESCRIPTION
        "Cisco Firepower firmware:CompSource:descr managed
        object property"
    ::= { cfprApFirmwareCompSourceEntry 4 }

cfprApFirmwareCompSourceIntId OBJECT-TYPE
    SYNTAX       SnmpAdminString
    MAX-ACCESS   read-only
    STATUS       current
    DESCRIPTION
        "Cisco Firepower firmware:CompSource:intId managed
        object property"
    ::= { cfprApFirmwareCompSourceEntry 5 }

cfprApFirmwareCompSourceInvTag OBJECT-TYPE
    SYNTAX       SnmpAdminString
    MAX-ACCESS   read-only
    STATUS       current
    DESCRIPTION
        "Cisco Firepower firmware:CompSource:invTag managed
        object property"
    ::= { cfprApFirmwareCompSourceEntry 6 }

cfprApFirmwareCompSourceName OBJECT-TYPE
    SYNTAX       SnmpAdminString
    MAX-ACCESS   read-only
    STATUS       current
    DESCRIPTION
        "Cisco Firepower firmware:CompSource:name managed object property"
    ::= { cfprApFirmwareCompSourceEntry 7 }

cfprApFirmwareCompSourcePolicyLevel OBJECT-TYPE
    SYNTAX       Gauge32
    MAX-ACCESS   read-only
    STATUS       current
    DESCRIPTION
        "Cisco Firepower firmware:CompSource:policyLevel
        managed object property"
    ::= { cfprApFirmwareCompSourceEntry 8 }

cfprApFirmwareCompSourcePolicyOwner OBJECT-TYPE
    SYNTAX       CfprApPolicyPolicyOwner
    MAX-ACCESS   read-only
    STATUS       current
    DESCRIPTION
        "Cisco Firepower firmware:CompSource:policyOwner
        managed object property"
    ::= { cfprApFirmwareCompSourceEntry 9 }

cfprApFirmwareCompSourceVersion OBJECT-TYPE
    SYNTAX       SnmpAdminString
    MAX-ACCESS   read-only
    STATUS       current
    DESCRIPTION
        "Cisco Firepower firmware:CompSource:version managed
        object property"
    ::= { cfprApFirmwareCompSourceEntry 10 }

cfprApFirmwareCompTargetTable OBJECT-TYPE
    SYNTAX           SEQUENCE OF CfprApFirmwareCompTargetEntry
    MAX-ACCESS       not-accessible
    STATUS           current
    DESCRIPTION
        "Cisco Firepower firmware:CompTarget managed object table"
    ::= { cfprApFirmwareObjects 13 }

cfprApFirmwareCompTargetEntry OBJECT-TYPE
    SYNTAX           CfprApFirmwareCompTargetEntry
    MAX-ACCESS       not-accessible
    STATUS           current
    DESCRIPTION
        "Entry for the cfprApFirmwareCompTargetTable table."
    INDEX { cfprApFirmwareCompTargetInstanceId }
    ::= { cfprApFirmwareCompTargetTable 1 }

CfprApFirmwareCompTargetEntry ::= SEQUENCE {
    cfprApFirmwareCompTargetInstanceId                               CfprApManagedObjectId,
    cfprApFirmwareCompTargetDn                                       CfprApManagedObjectDn,
    cfprApFirmwareCompTargetRn                                       SnmpAdminString,
    cfprApFirmwareCompTargetDescr                                    SnmpAdminString,
    cfprApFirmwareCompTargetIntId                                    SnmpAdminString,
    cfprApFirmwareCompTargetInvTag                                   SnmpAdminString,
    cfprApFirmwareCompTargetName                                     SnmpAdminString,
    cfprApFirmwareCompTargetPolicyLevel                              Gauge32,
    cfprApFirmwareCompTargetPolicyOwner                              CfprApPolicyPolicyOwner,
    cfprApFirmwareCompTargetVersion                                  SnmpAdminString
}

cfprApFirmwareCompTargetInstanceId OBJECT-TYPE
    SYNTAX       CfprApManagedObjectId
    MAX-ACCESS   not-accessible
    STATUS       current
    DESCRIPTION
        "Instance identifier of the managed object."
    ::= { cfprApFirmwareCompTargetEntry 1 }

cfprApFirmwareCompTargetDn OBJECT-TYPE
    SYNTAX       CfprApManagedObjectDn
    MAX-ACCESS   read-only
    STATUS       current
    DESCRIPTION
        "Cisco Firepower firmware:CompTarget:dn managed object property"
    ::= { cfprApFirmwareCompTargetEntry 2 }

cfprApFirmwareCompTargetRn OBJECT-TYPE
    SYNTAX       SnmpAdminString
    MAX-ACCESS   read-only
    STATUS       current
    DESCRIPTION
        "Cisco Firepower firmware:CompTarget:rn managed object property"
    ::= { cfprApFirmwareCompTargetEntry 3 }

cfprApFirmwareCompTargetDescr OBJECT-TYPE
    SYNTAX       SnmpAdminString
    MAX-ACCESS   read-only
    STATUS       current
    DESCRIPTION
        "Cisco Firepower firmware:CompTarget:descr managed
        object property"
    ::= { cfprApFirmwareCompTargetEntry 4 }

cfprApFirmwareCompTargetIntId OBJECT-TYPE
    SYNTAX       SnmpAdminString
    MAX-ACCESS   read-only
    STATUS       current
    DESCRIPTION
        "Cisco Firepower firmware:CompTarget:intId managed
        object property"
    ::= { cfprApFirmwareCompTargetEntry 5 }

cfprApFirmwareCompTargetInvTag OBJECT-TYPE
    SYNTAX       SnmpAdminString
    MAX-ACCESS   read-only
    STATUS       current
    DESCRIPTION
        "Cisco Firepower firmware:CompTarget:invTag managed
        object property"
    ::= { cfprApFirmwareCompTargetEntry 6 }

cfprApFirmwareCompTargetName OBJECT-TYPE
    SYNTAX       SnmpAdminString
    MAX-ACCESS   read-only
    STATUS       current
    DESCRIPTION
        "Cisco Firepower firmware:CompTarget:name managed object property"
    ::= { cfprApFirmwareCompTargetEntry 7 }

cfprApFirmwareCompTargetPolicyLevel OBJECT-TYPE
    SYNTAX       Gauge32
    MAX-ACCESS   read-only
    STATUS       current
    DESCRIPTION
        "Cisco Firepower firmware:CompTarget:policyLevel
        managed object property"
    ::= { cfprApFirmwareCompTargetEntry 8 }

cfprApFirmwareCompTargetPolicyOwner OBJECT-TYPE
    SYNTAX       CfprApPolicyPolicyOwner
    MAX-ACCESS   read-only
    STATUS       current
    DESCRIPTION
        "Cisco Firepower firmware:CompTarget:policyOwner
        managed object property"
    ::= { cfprApFirmwareCompTargetEntry 9 }

cfprApFirmwareCompTargetVersion OBJECT-TYPE
    SYNTAX       SnmpAdminString
    MAX-ACCESS   read-only
    STATUS       current
    DESCRIPTION
        "Cisco Firepower firmware:CompTarget:version managed
        object property"
    ::= { cfprApFirmwareCompTargetEntry 10 }

cfprApFirmwareComputeHostPackTable OBJECT-TYPE
    SYNTAX           SEQUENCE OF CfprApFirmwareComputeHostPackEntry
    MAX-ACCESS       not-accessible
    STATUS           current
    DESCRIPTION
        "Cisco Firepower firmware:ComputeHostPack managed object table"
    ::= { cfprApFirmwareObjects 14 }

cfprApFirmwareComputeHostPackEntry OBJECT-TYPE
    SYNTAX           CfprApFirmwareComputeHostPackEntry
    MAX-ACCESS       not-accessible
    STATUS           current
    DESCRIPTION
        "Entry for the cfprApFirmwareComputeHostPackTable table."
    INDEX { cfprApFirmwareComputeHostPackInstanceId }
    ::= { cfprApFirmwareComputeHostPackTable 1 }

CfprApFirmwareComputeHostPackEntry ::= SEQUENCE {
    cfprApFirmwareComputeHostPackInstanceId                          CfprApManagedObjectId,
    cfprApFirmwareComputeHostPackDn                                  CfprApManagedObjectDn,
    cfprApFirmwareComputeHostPackRn                                  SnmpAdminString,
    cfprApFirmwareComputeHostPackBladeBundleName                     SnmpAdminString,
    cfprApFirmwareComputeHostPackBladeBundleVersion                  SnmpAdminString,
    cfprApFirmwareComputeHostPackConfigQualifier                     CfprApFirmwareHostPackConfigQualifier,
    cfprApFirmwareComputeHostPackDescr                               SnmpAdminString,
    cfprApFirmwareComputeHostPackIgnoreCompCheck                     TruthValue,
    cfprApFirmwareComputeHostPackIntId                               SnmpAdminString,
    cfprApFirmwareComputeHostPackMode                                CfprApFirmwarePackMode,
    cfprApFirmwareComputeHostPackName                                SnmpAdminString,
    cfprApFirmwareComputeHostPackPlatformBundleVersion               SnmpAdminString,
    cfprApFirmwareComputeHostPackPolicyLevel                         Gauge32,
    cfprApFirmwareComputeHostPackPolicyOwner                         CfprApPolicyPolicyOwner,
    cfprApFirmwareComputeHostPackRackBundleName                      SnmpAdminString,
    cfprApFirmwareComputeHostPackRackBundleVersion                   SnmpAdminString,
    cfprApFirmwareComputeHostPackStageSize                           Gauge32,
    cfprApFirmwareComputeHostPackUpdateTrigger                       DateAndTime
}

cfprApFirmwareComputeHostPackInstanceId OBJECT-TYPE
    SYNTAX       CfprApManagedObjectId
    MAX-ACCESS   not-accessible
    STATUS       current
    DESCRIPTION
        "Instance identifier of the managed object."
    ::= { cfprApFirmwareComputeHostPackEntry 1 }

cfprApFirmwareComputeHostPackDn OBJECT-TYPE
    SYNTAX       CfprApManagedObjectDn
    MAX-ACCESS   read-only
    STATUS       current
    DESCRIPTION
        "Cisco Firepower firmware:ComputeHostPack:dn managed
        object property"
    ::= { cfprApFirmwareComputeHostPackEntry 2 }

cfprApFirmwareComputeHostPackRn OBJECT-TYPE
    SYNTAX       SnmpAdminString
    MAX-ACCESS   read-only
    STATUS       current
    DESCRIPTION
        "Cisco Firepower firmware:ComputeHostPack:rn managed
        object property"
    ::= { cfprApFirmwareComputeHostPackEntry 3 }

cfprApFirmwareComputeHostPackBladeBundleName OBJECT-TYPE
    SYNTAX       SnmpAdminString
    MAX-ACCESS   read-only
    STATUS       current
    DESCRIPTION
        "Cisco Firepower firmware:ComputeHostPack:bladeBundleName
        managed object property"
    ::= { cfprApFirmwareComputeHostPackEntry 4 }

cfprApFirmwareComputeHostPackBladeBundleVersion OBJECT-TYPE
    SYNTAX       SnmpAdminString
    MAX-ACCESS   read-only
    STATUS       current
    DESCRIPTION
        "Cisco Firepower firmware:ComputeHostPack:bladeBundleVersion
        managed object property"
    ::= { cfprApFirmwareComputeHostPackEntry 5 }

cfprApFirmwareComputeHostPackConfigQualifier OBJECT-TYPE
    SYNTAX       CfprApFirmwareHostPackConfigQualifier
    MAX-ACCESS   read-only
    STATUS       current
    DESCRIPTION
        "Cisco Firepower firmware:ComputeHostPack:configQualifier
        managed object property"
    ::= { cfprApFirmwareComputeHostPackEntry 6 }

cfprApFirmwareComputeHostPackDescr OBJECT-TYPE
    SYNTAX       SnmpAdminString
    MAX-ACCESS   read-only
    STATUS       current
    DESCRIPTION
        "Cisco Firepower firmware:ComputeHostPack:descr
        managed object property"
    ::= { cfprApFirmwareComputeHostPackEntry 7 }

cfprApFirmwareComputeHostPackIgnoreCompCheck OBJECT-TYPE
    SYNTAX       TruthValue
    MAX-ACCESS   read-only
    STATUS       current
    DESCRIPTION
        "Cisco Firepower firmware:ComputeHostPack:ignoreCompCheck
        managed object property"
    ::= { cfprApFirmwareComputeHostPackEntry 8 }

cfprApFirmwareComputeHostPackIntId OBJECT-TYPE
    SYNTAX       SnmpAdminString
    MAX-ACCESS   read-only
    STATUS       current
    DESCRIPTION
        "Cisco Firepower firmware:ComputeHostPack:intId
        managed object property"
    ::= { cfprApFirmwareComputeHostPackEntry 9 }

cfprApFirmwareComputeHostPackMode OBJECT-TYPE
    SYNTAX       CfprApFirmwarePackMode
    MAX-ACCESS   read-only
    STATUS       current
    DESCRIPTION
        "Cisco Firepower firmware:ComputeHostPack:mode
        managed object property"
    ::= { cfprApFirmwareComputeHostPackEntry 10 }

cfprApFirmwareComputeHostPackName OBJECT-TYPE
    SYNTAX       SnmpAdminString
    MAX-ACCESS   read-only
    STATUS       current
    DESCRIPTION
        "Cisco Firepower firmware:ComputeHostPack:name
        managed object property"
    ::= { cfprApFirmwareComputeHostPackEntry 11 }

cfprApFirmwareComputeHostPackPlatformBundleVersion OBJECT-TYPE
    SYNTAX       SnmpAdminString
    MAX-ACCESS   read-only
    STATUS       current
    DESCRIPTION
        "Cisco Firepower firmware:ComputeHostPack:platformBundleVersion
        managed object property"
    ::= { cfprApFirmwareComputeHostPackEntry 12 }

cfprApFirmwareComputeHostPackPolicyLevel OBJECT-TYPE
    SYNTAX       Gauge32
    MAX-ACCESS   read-only
    STATUS       current
    DESCRIPTION
        "Cisco Firepower firmware:ComputeHostPack:policyLevel
        managed object property"
    ::= { cfprApFirmwareComputeHostPackEntry 13 }

cfprApFirmwareComputeHostPackPolicyOwner OBJECT-TYPE
    SYNTAX       CfprApPolicyPolicyOwner
    MAX-ACCESS   read-only
    STATUS       current
    DESCRIPTION
        "Cisco Firepower firmware:ComputeHostPack:policyOwner
        managed object property"
    ::= { cfprApFirmwareComputeHostPackEntry 14 }

cfprApFirmwareComputeHostPackRackBundleName OBJECT-TYPE
    SYNTAX       SnmpAdminString
    MAX-ACCESS   read-only
    STATUS       current
    DESCRIPTION
        "Cisco Firepower firmware:ComputeHostPack:rackBundleName
        managed object property"
    ::= { cfprApFirmwareComputeHostPackEntry 15 }

cfprApFirmwareComputeHostPackRackBundleVersion OBJECT-TYPE
    SYNTAX       SnmpAdminString
    MAX-ACCESS   read-only
    STATUS       current
    DESCRIPTION
        "Cisco Firepower firmware:ComputeHostPack:rackBundleVersion
        managed object property"
    ::= { cfprApFirmwareComputeHostPackEntry 16 }

cfprApFirmwareComputeHostPackStageSize OBJECT-TYPE
    SYNTAX       Gauge32
    MAX-ACCESS   read-only
    STATUS       current
    DESCRIPTION
        "Cisco Firepower firmware:ComputeHostPack:stageSize
        managed object property"
    ::= { cfprApFirmwareComputeHostPackEntry 17 }

cfprApFirmwareComputeHostPackUpdateTrigger OBJECT-TYPE
    SYNTAX       DateAndTime
    MAX-ACCESS   read-only
    STATUS       current
    DESCRIPTION
        "Cisco Firepower firmware:ComputeHostPack:updateTrigger
        managed object property"
    ::= { cfprApFirmwareComputeHostPackEntry 18 }

cfprApFirmwareComputeMgmtPackTable OBJECT-TYPE
    SYNTAX           SEQUENCE OF CfprApFirmwareComputeMgmtPackEntry
    MAX-ACCESS       not-accessible
    STATUS           current
    DESCRIPTION
        "Cisco Firepower firmware:ComputeMgmtPack managed object table"
    ::= { cfprApFirmwareObjects 15 }

cfprApFirmwareComputeMgmtPackEntry OBJECT-TYPE
    SYNTAX           CfprApFirmwareComputeMgmtPackEntry
    MAX-ACCESS       not-accessible
    STATUS           current
    DESCRIPTION
        "Entry for the cfprApFirmwareComputeMgmtPackTable table."
    INDEX { cfprApFirmwareComputeMgmtPackInstanceId }
    ::= { cfprApFirmwareComputeMgmtPackTable 1 }

CfprApFirmwareComputeMgmtPackEntry ::= SEQUENCE {
    cfprApFirmwareComputeMgmtPackInstanceId                          CfprApManagedObjectId,
    cfprApFirmwareComputeMgmtPackDn                                  CfprApManagedObjectDn,
    cfprApFirmwareComputeMgmtPackRn                                  SnmpAdminString,
    cfprApFirmwareComputeMgmtPackDescr                               SnmpAdminString,
    cfprApFirmwareComputeMgmtPackIgnoreCompCheck                     TruthValue,
    cfprApFirmwareComputeMgmtPackIntId                               SnmpAdminString,
    cfprApFirmwareComputeMgmtPackMode                                CfprApFirmwarePackMode,
    cfprApFirmwareComputeMgmtPackName                                SnmpAdminString,
    cfprApFirmwareComputeMgmtPackPolicyLevel                         Gauge32,
    cfprApFirmwareComputeMgmtPackPolicyOwner                         CfprApPolicyPolicyOwner,
    cfprApFirmwareComputeMgmtPackStageSize                           Gauge32,
    cfprApFirmwareComputeMgmtPackUpdateTrigger                       DateAndTime
}

cfprApFirmwareComputeMgmtPackInstanceId OBJECT-TYPE
    SYNTAX       CfprApManagedObjectId
    MAX-ACCESS   not-accessible
    STATUS       current
    DESCRIPTION
        "Instance identifier of the managed object."
    ::= { cfprApFirmwareComputeMgmtPackEntry 1 }

cfprApFirmwareComputeMgmtPackDn OBJECT-TYPE
    SYNTAX       CfprApManagedObjectDn
    MAX-ACCESS   read-only
    STATUS       current
    DESCRIPTION
        "Cisco Firepower firmware:ComputeMgmtPack:dn managed
        object property"
    ::= { cfprApFirmwareComputeMgmtPackEntry 2 }

cfprApFirmwareComputeMgmtPackRn OBJECT-TYPE
    SYNTAX       SnmpAdminString
    MAX-ACCESS   read-only
    STATUS       current
    DESCRIPTION
        "Cisco Firepower firmware:ComputeMgmtPack:rn managed
        object property"
    ::= { cfprApFirmwareComputeMgmtPackEntry 3 }

cfprApFirmwareComputeMgmtPackDescr OBJECT-TYPE
    SYNTAX       SnmpAdminString
    MAX-ACCESS   read-only
    STATUS       current
    DESCRIPTION
        "Cisco Firepower firmware:ComputeMgmtPack:descr
        managed object property"
    ::= { cfprApFirmwareComputeMgmtPackEntry 4 }

cfprApFirmwareComputeMgmtPackIgnoreCompCheck OBJECT-TYPE
    SYNTAX       TruthValue
    MAX-ACCESS   read-only
    STATUS       current
    DESCRIPTION
        "Cisco Firepower firmware:ComputeMgmtPack:ignoreCompCheck
        managed object property"
    ::= { cfprApFirmwareComputeMgmtPackEntry 5 }

cfprApFirmwareComputeMgmtPackIntId OBJECT-TYPE
    SYNTAX       SnmpAdminString
    MAX-ACCESS   read-only
    STATUS       current
    DESCRIPTION
        "Cisco Firepower firmware:ComputeMgmtPack:intId
        managed object property"
    ::= { cfprApFirmwareComputeMgmtPackEntry 6 }

cfprApFirmwareComputeMgmtPackMode OBJECT-TYPE
    SYNTAX       CfprApFirmwarePackMode
    MAX-ACCESS   read-only
    STATUS       current
    DESCRIPTION
        "Cisco Firepower firmware:ComputeMgmtPack:mode
        managed object property"
    ::= { cfprApFirmwareComputeMgmtPackEntry 7 }

cfprApFirmwareComputeMgmtPackName OBJECT-TYPE
    SYNTAX       SnmpAdminString
    MAX-ACCESS   read-only
    STATUS       current
    DESCRIPTION
        "Cisco Firepower firmware:ComputeMgmtPack:name
        managed object property"
    ::= { cfprApFirmwareComputeMgmtPackEntry 8 }

cfprApFirmwareComputeMgmtPackPolicyLevel OBJECT-TYPE
    SYNTAX       Gauge32
    MAX-ACCESS   read-only
    STATUS       current
    DESCRIPTION
        "Cisco Firepower firmware:ComputeMgmtPack:policyLevel
        managed object property"
    ::= { cfprApFirmwareComputeMgmtPackEntry 9 }

cfprApFirmwareComputeMgmtPackPolicyOwner OBJECT-TYPE
    SYNTAX       CfprApPolicyPolicyOwner
    MAX-ACCESS   read-only
    STATUS       current
    DESCRIPTION
        "Cisco Firepower firmware:ComputeMgmtPack:policyOwner
        managed object property"
    ::= { cfprApFirmwareComputeMgmtPackEntry 10 }

cfprApFirmwareComputeMgmtPackStageSize OBJECT-TYPE
    SYNTAX       Gauge32
    MAX-ACCESS   read-only
    STATUS       current
    DESCRIPTION
        "Cisco Firepower firmware:ComputeMgmtPack:stageSize
        managed object property"
    ::= { cfprApFirmwareComputeMgmtPackEntry 11 }

cfprApFirmwareComputeMgmtPackUpdateTrigger OBJECT-TYPE
    SYNTAX       DateAndTime
    MAX-ACCESS   read-only
    STATUS       current
    DESCRIPTION
        "Cisco Firepower firmware:ComputeMgmtPack:updateTrigger
        managed object property"
    ::= { cfprApFirmwareComputeMgmtPackEntry 12 }

cfprApFirmwareConstraintTable OBJECT-TYPE
    SYNTAX           SEQUENCE OF CfprApFirmwareConstraintEntry
    MAX-ACCESS       not-accessible
    STATUS           current
    DESCRIPTION
        "Cisco Firepower firmware:Constraint managed object table"
    ::= { cfprApFirmwareObjects 16 }

cfprApFirmwareConstraintEntry OBJECT-TYPE
    SYNTAX           CfprApFirmwareConstraintEntry
    MAX-ACCESS       not-accessible
    STATUS           current
    DESCRIPTION
        "Entry for the cfprApFirmwareConstraintTable table."
    INDEX { cfprApFirmwareConstraintInstanceId }
    ::= { cfprApFirmwareConstraintTable 1 }

CfprApFirmwareConstraintEntry ::= SEQUENCE {
    cfprApFirmwareConstraintInstanceId                               CfprApManagedObjectId,
    cfprApFirmwareConstraintDn                                       CfprApManagedObjectDn,
    cfprApFirmwareConstraintRn                                       SnmpAdminString,
    cfprApFirmwareConstraintFeature                                  SnmpAdminString,
    cfprApFirmwareConstraintMinBiosVersion                           SnmpAdminString,
    cfprApFirmwareConstraintMinCimcVersion                           SnmpAdminString
}

cfprApFirmwareConstraintInstanceId OBJECT-TYPE
    SYNTAX       CfprApManagedObjectId
    MAX-ACCESS   not-accessible
    STATUS       current
    DESCRIPTION
        "Instance identifier of the managed object."
    ::= { cfprApFirmwareConstraintEntry 1 }

cfprApFirmwareConstraintDn OBJECT-TYPE
    SYNTAX       CfprApManagedObjectDn
    MAX-ACCESS   read-only
    STATUS       current
    DESCRIPTION
        "Cisco Firepower firmware:Constraint:dn managed object property"
    ::= { cfprApFirmwareConstraintEntry 2 }

cfprApFirmwareConstraintRn OBJECT-TYPE
    SYNTAX       SnmpAdminString
    MAX-ACCESS   read-only
    STATUS       current
    DESCRIPTION
        "Cisco Firepower firmware:Constraint:rn managed object property"
    ::= { cfprApFirmwareConstraintEntry 3 }

cfprApFirmwareConstraintFeature OBJECT-TYPE
    SYNTAX       SnmpAdminString
    MAX-ACCESS   read-only
    STATUS       current
    DESCRIPTION
        "Cisco Firepower firmware:Constraint:feature managed
        object property"
    ::= { cfprApFirmwareConstraintEntry 4 }

cfprApFirmwareConstraintMinBiosVersion OBJECT-TYPE
    SYNTAX       SnmpAdminString
    MAX-ACCESS   read-only
    STATUS       current
    DESCRIPTION
        "Cisco Firepower firmware:Constraint:minBiosVersion
        managed object property"
    ::= { cfprApFirmwareConstraintEntry 5 }

cfprApFirmwareConstraintMinCimcVersion OBJECT-TYPE
    SYNTAX       SnmpAdminString
    MAX-ACCESS   read-only
    STATUS       current
    DESCRIPTION
        "Cisco Firepower firmware:Constraint:minCimcVersion
        managed object property"
    ::= { cfprApFirmwareConstraintEntry 6 }

cfprApFirmwareConstraintsTable OBJECT-TYPE
    SYNTAX           SEQUENCE OF CfprApFirmwareConstraintsEntry
    MAX-ACCESS       not-accessible
    STATUS           current
    DESCRIPTION
        "Cisco Firepower firmware:Constraints managed object table"
    ::= { cfprApFirmwareObjects 17 }

cfprApFirmwareConstraintsEntry OBJECT-TYPE
    SYNTAX           CfprApFirmwareConstraintsEntry
    MAX-ACCESS       not-accessible
    STATUS           current
    DESCRIPTION
        "Entry for the cfprApFirmwareConstraintsTable table."
    INDEX { cfprApFirmwareConstraintsInstanceId }
    ::= { cfprApFirmwareConstraintsTable 1 }

CfprApFirmwareConstraintsEntry ::= SEQUENCE {
    cfprApFirmwareConstraintsInstanceId                              CfprApManagedObjectId,
    cfprApFirmwareConstraintsDn                                      CfprApManagedObjectDn,
    cfprApFirmwareConstraintsRn                                      SnmpAdminString
}

cfprApFirmwareConstraintsInstanceId OBJECT-TYPE
    SYNTAX       CfprApManagedObjectId
    MAX-ACCESS   not-accessible
    STATUS       current
    DESCRIPTION
        "Instance identifier of the managed object."
    ::= { cfprApFirmwareConstraintsEntry 1 }

cfprApFirmwareConstraintsDn OBJECT-TYPE
    SYNTAX       CfprApManagedObjectDn
    MAX-ACCESS   read-only
    STATUS       current
    DESCRIPTION
        "Cisco Firepower firmware:Constraints:dn managed object property"
    ::= { cfprApFirmwareConstraintsEntry 2 }

cfprApFirmwareConstraintsRn OBJECT-TYPE
    SYNTAX       SnmpAdminString
    MAX-ACCESS   read-only
    STATUS       current
    DESCRIPTION
        "Cisco Firepower firmware:Constraints:rn managed object property"
    ::= { cfprApFirmwareConstraintsEntry 3 }

cfprApFirmwareCspAppListTable OBJECT-TYPE
    SYNTAX           SEQUENCE OF CfprApFirmwareCspAppListEntry
    MAX-ACCESS       not-accessible
    STATUS           current
    DESCRIPTION
        "Cisco Firepower firmware:CspAppList managed object table"
    ::= { cfprApFirmwareObjects 18 }

cfprApFirmwareCspAppListEntry OBJECT-TYPE
    SYNTAX           CfprApFirmwareCspAppListEntry
    MAX-ACCESS       not-accessible
    STATUS           current
    DESCRIPTION
        "Entry for the cfprApFirmwareCspAppListTable table."
    INDEX { cfprApFirmwareCspAppListInstanceId }
    ::= { cfprApFirmwareCspAppListTable 1 }

CfprApFirmwareCspAppListEntry ::= SEQUENCE {
    cfprApFirmwareCspAppListInstanceId                               CfprApManagedObjectId,
    cfprApFirmwareCspAppListDn                                       CfprApManagedObjectDn,
    cfprApFirmwareCspAppListRn                                       SnmpAdminString,
    cfprApFirmwareCspAppListName                                     SnmpAdminString
}

cfprApFirmwareCspAppListInstanceId OBJECT-TYPE
    SYNTAX       CfprApManagedObjectId
    MAX-ACCESS   not-accessible
    STATUS       current
    DESCRIPTION
        "Instance identifier of the managed object."
    ::= { cfprApFirmwareCspAppListEntry 1 }

cfprApFirmwareCspAppListDn OBJECT-TYPE
    SYNTAX       CfprApManagedObjectDn
    MAX-ACCESS   read-only
    STATUS       current
    DESCRIPTION
        "Cisco Firepower firmware:CspAppList:dn managed object property"
    ::= { cfprApFirmwareCspAppListEntry 2 }

cfprApFirmwareCspAppListRn OBJECT-TYPE
    SYNTAX       SnmpAdminString
    MAX-ACCESS   read-only
    STATUS       current
    DESCRIPTION
        "Cisco Firepower firmware:CspAppList:rn managed object property"
    ::= { cfprApFirmwareCspAppListEntry 3 }

cfprApFirmwareCspAppListName OBJECT-TYPE
    SYNTAX       SnmpAdminString
    MAX-ACCESS   read-only
    STATUS       current
    DESCRIPTION
        "Cisco Firepower firmware:CspAppList:name managed object property"
    ::= { cfprApFirmwareCspAppListEntry 4 }

cfprApFirmwareCspVersionTable OBJECT-TYPE
    SYNTAX           SEQUENCE OF CfprApFirmwareCspVersionEntry
    MAX-ACCESS       not-accessible
    STATUS           current
    DESCRIPTION
        "Cisco Firepower firmware:CspVersion managed object table"
    ::= { cfprApFirmwareObjects 19 }

cfprApFirmwareCspVersionEntry OBJECT-TYPE
    SYNTAX           CfprApFirmwareCspVersionEntry
    MAX-ACCESS       not-accessible
    STATUS           current
    DESCRIPTION
        "Entry for the cfprApFirmwareCspVersionTable table."
    INDEX { cfprApFirmwareCspVersionInstanceId }
    ::= { cfprApFirmwareCspVersionTable 1 }

CfprApFirmwareCspVersionEntry ::= SEQUENCE {
    cfprApFirmwareCspVersionInstanceId                               CfprApManagedObjectId,
    cfprApFirmwareCspVersionDn                                       CfprApManagedObjectDn,
    cfprApFirmwareCspVersionRn                                       SnmpAdminString,
    cfprApFirmwareCspVersionAppName                                  SnmpAdminString,
    cfprApFirmwareCspVersionFromVersion                              SnmpAdminString,
    cfprApFirmwareCspVersionName                                     SnmpAdminString,
    cfprApFirmwareCspVersionToVersion                                SnmpAdminString
}

cfprApFirmwareCspVersionInstanceId OBJECT-TYPE
    SYNTAX       CfprApManagedObjectId
    MAX-ACCESS   not-accessible
    STATUS       current
    DESCRIPTION
        "Instance identifier of the managed object."
    ::= { cfprApFirmwareCspVersionEntry 1 }

cfprApFirmwareCspVersionDn OBJECT-TYPE
    SYNTAX       CfprApManagedObjectDn
    MAX-ACCESS   read-only
    STATUS       current
    DESCRIPTION
        "Cisco Firepower firmware:CspVersion:dn managed object property"
    ::= { cfprApFirmwareCspVersionEntry 2 }

cfprApFirmwareCspVersionRn OBJECT-TYPE
    SYNTAX       SnmpAdminString
    MAX-ACCESS   read-only
    STATUS       current
    DESCRIPTION
        "Cisco Firepower firmware:CspVersion:rn managed object property"
    ::= { cfprApFirmwareCspVersionEntry 3 }

cfprApFirmwareCspVersionAppName OBJECT-TYPE
    SYNTAX       SnmpAdminString
    MAX-ACCESS   read-only
    STATUS       current
    DESCRIPTION
        "Cisco Firepower firmware:CspVersion:appName managed
        object property"
    ::= { cfprApFirmwareCspVersionEntry 4 }

cfprApFirmwareCspVersionFromVersion OBJECT-TYPE
    SYNTAX       SnmpAdminString
    MAX-ACCESS   read-only
    STATUS       current
    DESCRIPTION
        "Cisco Firepower firmware:CspVersion:fromVersion
        managed object property"
    ::= { cfprApFirmwareCspVersionEntry 5 }

cfprApFirmwareCspVersionName OBJECT-TYPE
    SYNTAX       SnmpAdminString
    MAX-ACCESS   read-only
    STATUS       current
    DESCRIPTION
        "Cisco Firepower firmware:CspVersion:name managed object property"
    ::= { cfprApFirmwareCspVersionEntry 6 }

cfprApFirmwareCspVersionToVersion OBJECT-TYPE
    SYNTAX       SnmpAdminString
    MAX-ACCESS   read-only
    STATUS       current
    DESCRIPTION
        "Cisco Firepower firmware:CspVersion:toVersion
        managed object property"
    ::= { cfprApFirmwareCspVersionEntry 7 }

cfprApFirmwareDependencyTable OBJECT-TYPE
    SYNTAX           SEQUENCE OF CfprApFirmwareDependencyEntry
    MAX-ACCESS       not-accessible
    STATUS           current
    DESCRIPTION
        "Cisco Firepower firmware:Dependency managed object table"
    ::= { cfprApFirmwareObjects 20 }

cfprApFirmwareDependencyEntry OBJECT-TYPE
    SYNTAX           CfprApFirmwareDependencyEntry
    MAX-ACCESS       not-accessible
    STATUS           current
    DESCRIPTION
        "Entry for the cfprApFirmwareDependencyTable table."
    INDEX { cfprApFirmwareDependencyInstanceId }
    ::= { cfprApFirmwareDependencyTable 1 }

CfprApFirmwareDependencyEntry ::= SEQUENCE {
    cfprApFirmwareDependencyInstanceId                               CfprApManagedObjectId,
    cfprApFirmwareDependencyDn                                       CfprApManagedObjectDn,
    cfprApFirmwareDependencyRn                                       SnmpAdminString,
    cfprApFirmwareDependencyEp                                       CfprApFirmwareType,
    cfprApFirmwareDependencyHwModel                                  SnmpAdminString,
    cfprApFirmwareDependencyHwRevision                               SnmpAdminString,
    cfprApFirmwareDependencyHwVendor                                 SnmpAdminString,
    cfprApFirmwareDependencyInvTag                                   SnmpAdminString,
    cfprApFirmwareDependencyMaxVer                                   SnmpAdminString,
    cfprApFirmwareDependencyMinVer                                   SnmpAdminString,
    cfprApFirmwareDependencyRelationship                             CfprApFirmwareDependencyRelationship,
    cfprApFirmwareDependencyScope                                    CfprApFirmwareDependencyScope,
    cfprApFirmwareDependencySensitivity                              CfprApFirmwareDependencySensitivity
}

cfprApFirmwareDependencyInstanceId OBJECT-TYPE
    SYNTAX       CfprApManagedObjectId
    MAX-ACCESS   not-accessible
    STATUS       current
    DESCRIPTION
        "Instance identifier of the managed object."
    ::= { cfprApFirmwareDependencyEntry 1 }

cfprApFirmwareDependencyDn OBJECT-TYPE
    SYNTAX       CfprApManagedObjectDn
    MAX-ACCESS   read-only
    STATUS       current
    DESCRIPTION
        "Cisco Firepower firmware:Dependency:dn managed object property"
    ::= { cfprApFirmwareDependencyEntry 2 }

cfprApFirmwareDependencyRn OBJECT-TYPE
    SYNTAX       SnmpAdminString
    MAX-ACCESS   read-only
    STATUS       current
    DESCRIPTION
        "Cisco Firepower firmware:Dependency:rn managed object property"
    ::= { cfprApFirmwareDependencyEntry 3 }

cfprApFirmwareDependencyEp OBJECT-TYPE
    SYNTAX       CfprApFirmwareType
    MAX-ACCESS   read-only
    STATUS       current
    DESCRIPTION
        "Cisco Firepower firmware:Dependency:ep managed object property"
    ::= { cfprApFirmwareDependencyEntry 4 }

cfprApFirmwareDependencyHwModel OBJECT-TYPE
    SYNTAX       SnmpAdminString
    MAX-ACCESS   read-only
    STATUS       current
    DESCRIPTION
        "Cisco Firepower firmware:Dependency:hwModel managed
        object property"
    ::= { cfprApFirmwareDependencyEntry 5 }

cfprApFirmwareDependencyHwRevision OBJECT-TYPE
    SYNTAX       SnmpAdminString
    MAX-ACCESS   read-only
    STATUS       current
    DESCRIPTION
        "Cisco Firepower firmware:Dependency:hwRevision
        managed object property"
    ::= { cfprApFirmwareDependencyEntry 6 }

cfprApFirmwareDependencyHwVendor OBJECT-TYPE
    SYNTAX       SnmpAdminString
    MAX-ACCESS   read-only
    STATUS       current
    DESCRIPTION
        "Cisco Firepower firmware:Dependency:hwVendor managed
        object property"
    ::= { cfprApFirmwareDependencyEntry 7 }

cfprApFirmwareDependencyInvTag OBJECT-TYPE
    SYNTAX       SnmpAdminString
    MAX-ACCESS   read-only
    STATUS       current
    DESCRIPTION
        "Cisco Firepower firmware:Dependency:invTag managed
        object property"
    ::= { cfprApFirmwareDependencyEntry 8 }

cfprApFirmwareDependencyMaxVer OBJECT-TYPE
    SYNTAX       SnmpAdminString
    MAX-ACCESS   read-only
    STATUS       current
    DESCRIPTION
        "Cisco Firepower firmware:Dependency:maxVer managed
        object property"
    ::= { cfprApFirmwareDependencyEntry 9 }

cfprApFirmwareDependencyMinVer OBJECT-TYPE
    SYNTAX       SnmpAdminString
    MAX-ACCESS   read-only
    STATUS       current
    DESCRIPTION
        "Cisco Firepower firmware:Dependency:minVer managed
        object property"
    ::= { cfprApFirmwareDependencyEntry 10 }

cfprApFirmwareDependencyRelationship OBJECT-TYPE
    SYNTAX       CfprApFirmwareDependencyRelationship
    MAX-ACCESS   read-only
    STATUS       current
    DESCRIPTION
        "Cisco Firepower firmware:Dependency:relationship
        managed object property"
    ::= { cfprApFirmwareDependencyEntry 11 }

cfprApFirmwareDependencyScope OBJECT-TYPE
    SYNTAX       CfprApFirmwareDependencyScope
    MAX-ACCESS   read-only
    STATUS       current
    DESCRIPTION
        "Cisco Firepower firmware:Dependency:scope managed
        object property"
    ::= { cfprApFirmwareDependencyEntry 12 }

cfprApFirmwareDependencySensitivity OBJECT-TYPE
    SYNTAX       CfprApFirmwareDependencySensitivity
    MAX-ACCESS   read-only
    STATUS       current
    DESCRIPTION
        "Cisco Firepower firmware:Dependency:sensitivity
        managed object property"
    ::= { cfprApFirmwareDependencyEntry 13 }

cfprApFirmwareDistCspBlackListTable OBJECT-TYPE
    SYNTAX           SEQUENCE OF CfprApFirmwareDistCspBlackListEntry
    MAX-ACCESS       not-accessible
    STATUS           current
    DESCRIPTION
        "Cisco Firepower firmware:DistCspBlackList managed object table"
    ::= { cfprApFirmwareObjects 21 }

cfprApFirmwareDistCspBlackListEntry OBJECT-TYPE
    SYNTAX           CfprApFirmwareDistCspBlackListEntry
    MAX-ACCESS       not-accessible
    STATUS           current
    DESCRIPTION
        "Entry for the cfprApFirmwareDistCspBlackListTable table."
    INDEX { cfprApFirmwareDistCspBlackListInstanceId }
    ::= { cfprApFirmwareDistCspBlackListTable 1 }

CfprApFirmwareDistCspBlackListEntry ::= SEQUENCE {
    cfprApFirmwareDistCspBlackListInstanceId                         CfprApManagedObjectId,
    cfprApFirmwareDistCspBlackListDn                                 CfprApManagedObjectDn,
    cfprApFirmwareDistCspBlackListRn                                 SnmpAdminString,
    cfprApFirmwareDistCspBlackListName                               SnmpAdminString,
    cfprApFirmwareDistCspBlackListTimeStamp                          DateAndTime,
    cfprApFirmwareDistCspBlackListVersion                            SnmpAdminString
}

cfprApFirmwareDistCspBlackListInstanceId OBJECT-TYPE
    SYNTAX       CfprApManagedObjectId
    MAX-ACCESS   not-accessible
    STATUS       current
    DESCRIPTION
        "Instance identifier of the managed object."
    ::= { cfprApFirmwareDistCspBlackListEntry 1 }

cfprApFirmwareDistCspBlackListDn OBJECT-TYPE
    SYNTAX       CfprApManagedObjectDn
    MAX-ACCESS   read-only
    STATUS       current
    DESCRIPTION
        "Cisco Firepower firmware:DistCspBlackList:dn managed
        object property"
    ::= { cfprApFirmwareDistCspBlackListEntry 2 }

cfprApFirmwareDistCspBlackListRn OBJECT-TYPE
    SYNTAX       SnmpAdminString
    MAX-ACCESS   read-only
    STATUS       current
    DESCRIPTION
        "Cisco Firepower firmware:DistCspBlackList:rn managed
        object property"
    ::= { cfprApFirmwareDistCspBlackListEntry 3 }

cfprApFirmwareDistCspBlackListName OBJECT-TYPE
    SYNTAX       SnmpAdminString
    MAX-ACCESS   read-only
    STATUS       current
    DESCRIPTION
        "Cisco Firepower firmware:DistCspBlackList:name
        managed object property"
    ::= { cfprApFirmwareDistCspBlackListEntry 4 }

cfprApFirmwareDistCspBlackListTimeStamp OBJECT-TYPE
    SYNTAX       DateAndTime
    MAX-ACCESS   read-only
    STATUS       current
    DESCRIPTION
        "Cisco Firepower firmware:DistCspBlackList:timeStamp
        managed object property"
    ::= { cfprApFirmwareDistCspBlackListEntry 5 }

cfprApFirmwareDistCspBlackListVersion OBJECT-TYPE
    SYNTAX       SnmpAdminString
    MAX-ACCESS   read-only
    STATUS       current
    DESCRIPTION
        "Cisco Firepower firmware:DistCspBlackList:version
        managed object property"
    ::= { cfprApFirmwareDistCspBlackListEntry 6 }

cfprApFirmwareDistImageTable OBJECT-TYPE
    SYNTAX           SEQUENCE OF CfprApFirmwareDistImageEntry
    MAX-ACCESS       not-accessible
    STATUS           current
    DESCRIPTION
        "Cisco Firepower firmware:DistImage managed object table"
    ::= { cfprApFirmwareObjects 22 }

cfprApFirmwareDistImageEntry OBJECT-TYPE
    SYNTAX           CfprApFirmwareDistImageEntry
    MAX-ACCESS       not-accessible
    STATUS           current
    DESCRIPTION
        "Entry for the cfprApFirmwareDistImageTable table."
    INDEX { cfprApFirmwareDistImageInstanceId }
    ::= { cfprApFirmwareDistImageTable 1 }

CfprApFirmwareDistImageEntry ::= SEQUENCE {
    cfprApFirmwareDistImageInstanceId                                CfprApManagedObjectId,
    cfprApFirmwareDistImageDn                                        CfprApManagedObjectDn,
    cfprApFirmwareDistImageRn                                        SnmpAdminString,
    cfprApFirmwareDistImageImageDeleted                              CfprApFirmwareImageDeleted,
    cfprApFirmwareDistImageName                                      SnmpAdminString,
    cfprApFirmwareDistImageType                                      CfprApFirmwareType
}

cfprApFirmwareDistImageInstanceId OBJECT-TYPE
    SYNTAX       CfprApManagedObjectId
    MAX-ACCESS   not-accessible
    STATUS       current
    DESCRIPTION
        "Instance identifier of the managed object."
    ::= { cfprApFirmwareDistImageEntry 1 }

cfprApFirmwareDistImageDn OBJECT-TYPE
    SYNTAX       CfprApManagedObjectDn
    MAX-ACCESS   read-only
    STATUS       current
    DESCRIPTION
        "Cisco Firepower firmware:DistImage:dn managed object property"
    ::= { cfprApFirmwareDistImageEntry 2 }

cfprApFirmwareDistImageRn OBJECT-TYPE
    SYNTAX       SnmpAdminString
    MAX-ACCESS   read-only
    STATUS       current
    DESCRIPTION
        "Cisco Firepower firmware:DistImage:rn managed object property"
    ::= { cfprApFirmwareDistImageEntry 3 }

cfprApFirmwareDistImageImageDeleted OBJECT-TYPE
    SYNTAX       CfprApFirmwareImageDeleted
    MAX-ACCESS   read-only
    STATUS       current
    DESCRIPTION
        "Cisco Firepower firmware:DistImage:imageDeleted
        managed object property"
    ::= { cfprApFirmwareDistImageEntry 4 }

cfprApFirmwareDistImageName OBJECT-TYPE
    SYNTAX       SnmpAdminString
    MAX-ACCESS   read-only
    STATUS       current
    DESCRIPTION
        "Cisco Firepower firmware:DistImage:name managed object property"
    ::= { cfprApFirmwareDistImageEntry 5 }

cfprApFirmwareDistImageType OBJECT-TYPE
    SYNTAX       CfprApFirmwareType
    MAX-ACCESS   read-only
    STATUS       current
    DESCRIPTION
        "Cisco Firepower firmware:DistImage:type managed object property"
    ::= { cfprApFirmwareDistImageEntry 6 }

cfprApFirmwareDistributableTable OBJECT-TYPE
    SYNTAX           SEQUENCE OF CfprApFirmwareDistributableEntry
    MAX-ACCESS       not-accessible
    STATUS           current
    DESCRIPTION
        "Cisco Firepower firmware:Distributable managed object table"
    ::= { cfprApFirmwareObjects 23 }

cfprApFirmwareDistributableEntry OBJECT-TYPE
    SYNTAX           CfprApFirmwareDistributableEntry
    MAX-ACCESS       not-accessible
    STATUS           current
    DESCRIPTION
        "Entry for the cfprApFirmwareDistributableTable table."
    INDEX { cfprApFirmwareDistributableInstanceId }
    ::= { cfprApFirmwareDistributableTable 1 }

CfprApFirmwareDistributableEntry ::= SEQUENCE {
    cfprApFirmwareDistributableInstanceId                            CfprApManagedObjectId,
    cfprApFirmwareDistributableDn                                    CfprApManagedObjectDn,
    cfprApFirmwareDistributableRn                                    SnmpAdminString,
    cfprApFirmwareDistributableAdminState                            CfprApFirmwareAdminState,
    cfprApFirmwareDistributableBuildDate                             SnmpAdminString,
    cfprApFirmwareDistributableCompleteness                          CfprApFirmwareCompleteness,
    cfprApFirmwareDistributableDescr                                 SnmpAdminString,
    cfprApFirmwareDistributableDisplayFlag                           TruthValue,
    cfprApFirmwareDistributableFsmDescr                              SnmpAdminString,
    cfprApFirmwareDistributableFsmPrev                               SnmpAdminString,
    cfprApFirmwareDistributableFsmProgr                              Gauge32,
    cfprApFirmwareDistributableFsmRmtInvErrCode                      Gauge32,
    cfprApFirmwareDistributableFsmRmtInvErrDescr                     SnmpAdminString,
    cfprApFirmwareDistributableFsmRmtInvRslt                         CfprApConditionRemoteInvRslt,
    cfprApFirmwareDistributableFsmStageDescr                         SnmpAdminString,
    cfprApFirmwareDistributableFsmStamp                              DateAndTime,
    cfprApFirmwareDistributableFsmStatus                             SnmpAdminString,
    cfprApFirmwareDistributableFsmTry                                Gauge32,
    cfprApFirmwareDistributableImagePresence                         CfprApFirmwareImagePresence,
    cfprApFirmwareDistributableIntId                                 SnmpAdminString,
    cfprApFirmwareDistributableInvTag                                SnmpAdminString,
    cfprApFirmwareDistributableModel                                 SnmpAdminString,
    cfprApFirmwareDistributableName                                  SnmpAdminString,
    cfprApFirmwareDistributablePlatformVersion                       SnmpAdminString,
    cfprApFirmwareDistributablePolicyLevel                           Gauge32,
    cfprApFirmwareDistributablePolicyOwner                           CfprApPolicyPolicyOwner,
    cfprApFirmwareDistributableTimeStamp                             DateAndTime,
    cfprApFirmwareDistributableTransferState                         CfprApFirmwareTransferState,
    cfprApFirmwareDistributableType                                  CfprApFirmwareDistributableType,
    cfprApFirmwareDistributableVendor                                SnmpAdminString,
    cfprApFirmwareDistributableVersion                               SnmpAdminString
}

cfprApFirmwareDistributableInstanceId OBJECT-TYPE
    SYNTAX       CfprApManagedObjectId
    MAX-ACCESS   not-accessible
    STATUS       current
    DESCRIPTION
        "Instance identifier of the managed object."
    ::= { cfprApFirmwareDistributableEntry 1 }

cfprApFirmwareDistributableDn OBJECT-TYPE
    SYNTAX       CfprApManagedObjectDn
    MAX-ACCESS   read-only
    STATUS       current
    DESCRIPTION
        "Cisco Firepower firmware:Distributable:dn managed
        object property"
    ::= { cfprApFirmwareDistributableEntry 2 }

cfprApFirmwareDistributableRn OBJECT-TYPE
    SYNTAX       SnmpAdminString
    MAX-ACCESS   read-only
    STATUS       current
    DESCRIPTION
        "Cisco Firepower firmware:Distributable:rn managed
        object property"
    ::= { cfprApFirmwareDistributableEntry 3 }

cfprApFirmwareDistributableAdminState OBJECT-TYPE
    SYNTAX       CfprApFirmwareAdminState
    MAX-ACCESS   read-only
    STATUS       current
    DESCRIPTION
        "Cisco Firepower firmware:Distributable:adminState
        managed object property"
    ::= { cfprApFirmwareDistributableEntry 4 }

cfprApFirmwareDistributableBuildDate OBJECT-TYPE
    SYNTAX       SnmpAdminString
    MAX-ACCESS   read-only
    STATUS       current
    DESCRIPTION
        "Cisco Firepower firmware:Distributable:buildDate
        managed object property"
    ::= { cfprApFirmwareDistributableEntry 5 }

cfprApFirmwareDistributableCompleteness OBJECT-TYPE
    SYNTAX       CfprApFirmwareCompleteness
    MAX-ACCESS   read-only
    STATUS       current
    DESCRIPTION
        "Cisco Firepower firmware:Distributable:completeness
        managed object property"
    ::= { cfprApFirmwareDistributableEntry 6 }

cfprApFirmwareDistributableDescr OBJECT-TYPE
    SYNTAX       SnmpAdminString
    MAX-ACCESS   read-only
    STATUS       current
    DESCRIPTION
        "Cisco Firepower firmware:Distributable:descr managed
        object property"
    ::= { cfprApFirmwareDistributableEntry 7 }

cfprApFirmwareDistributableDisplayFlag OBJECT-TYPE
    SYNTAX       TruthValue
    MAX-ACCESS   read-only
    STATUS       current
    DESCRIPTION
        "Cisco Firepower firmware:Distributable:displayFlag
        managed object property"
    ::= { cfprApFirmwareDistributableEntry 8 }

cfprApFirmwareDistributableFsmDescr OBJECT-TYPE
    SYNTAX       SnmpAdminString
    MAX-ACCESS   read-only
    STATUS       current
    DESCRIPTION
        "Cisco Firepower firmware:Distributable:fsmDescr
        managed object property"
    ::= { cfprApFirmwareDistributableEntry 9 }

cfprApFirmwareDistributableFsmPrev OBJECT-TYPE
    SYNTAX       SnmpAdminString
    MAX-ACCESS   read-only
    STATUS       current
    DESCRIPTION
        "Cisco Firepower firmware:Distributable:fsmPrev
        managed object property"
    ::= { cfprApFirmwareDistributableEntry 10 }

cfprApFirmwareDistributableFsmProgr OBJECT-TYPE
    SYNTAX       Gauge32
    MAX-ACCESS   read-only
    STATUS       current
    DESCRIPTION
        "Cisco Firepower firmware:Distributable:fsmProgr
        managed object property"
    ::= { cfprApFirmwareDistributableEntry 11 }

cfprApFirmwareDistributableFsmRmtInvErrCode OBJECT-TYPE
    SYNTAX       Gauge32
    MAX-ACCESS   read-only
    STATUS       current
    DESCRIPTION
        "Cisco Firepower firmware:Distributable:fsmRmtInvErrCode
        managed object property"
    ::= { cfprApFirmwareDistributableEntry 12 }

cfprApFirmwareDistributableFsmRmtInvErrDescr OBJECT-TYPE
    SYNTAX       SnmpAdminString
    MAX-ACCESS   read-only
    STATUS       current
    DESCRIPTION
        "Cisco Firepower firmware:Distributable:fsmRmtInvErrDescr
        managed object property"
    ::= { cfprApFirmwareDistributableEntry 13 }

cfprApFirmwareDistributableFsmRmtInvRslt OBJECT-TYPE
    SYNTAX       CfprApConditionRemoteInvRslt
    MAX-ACCESS   read-only
    STATUS       current
    DESCRIPTION
        "Cisco Firepower firmware:Distributable:fsmRmtInvRslt
        managed object property"
    ::= { cfprApFirmwareDistributableEntry 14 }

cfprApFirmwareDistributableFsmStageDescr OBJECT-TYPE
    SYNTAX       SnmpAdminString
    MAX-ACCESS   read-only
    STATUS       current
    DESCRIPTION
        "Cisco Firepower firmware:Distributable:fsmStageDescr
        managed object property"
    ::= { cfprApFirmwareDistributableEntry 15 }

cfprApFirmwareDistributableFsmStamp OBJECT-TYPE
    SYNTAX       DateAndTime
    MAX-ACCESS   read-only
    STATUS       current
    DESCRIPTION
        "Cisco Firepower firmware:Distributable:fsmStamp
        managed object property"
    ::= { cfprApFirmwareDistributableEntry 16 }

cfprApFirmwareDistributableFsmStatus OBJECT-TYPE
    SYNTAX       SnmpAdminString
    MAX-ACCESS   read-only
    STATUS       current
    DESCRIPTION
        "Cisco Firepower firmware:Distributable:fsmStatus
        managed object property"
    ::= { cfprApFirmwareDistributableEntry 17 }

cfprApFirmwareDistributableFsmTry OBJECT-TYPE
    SYNTAX       Gauge32
    MAX-ACCESS   read-only
    STATUS       current
    DESCRIPTION
        "Cisco Firepower firmware:Distributable:fsmTry
        managed object property"
    ::= { cfprApFirmwareDistributableEntry 18 }

cfprApFirmwareDistributableImagePresence OBJECT-TYPE
    SYNTAX       CfprApFirmwareImagePresence
    MAX-ACCESS   read-only
    STATUS       current
    DESCRIPTION
        "Cisco Firepower firmware:Distributable:imagePresence
        managed object property"
    ::= { cfprApFirmwareDistributableEntry 19 }

cfprApFirmwareDistributableIntId OBJECT-TYPE
    SYNTAX       SnmpAdminString
    MAX-ACCESS   read-only
    STATUS       current
    DESCRIPTION
        "Cisco Firepower firmware:Distributable:intId managed
        object property"
    ::= { cfprApFirmwareDistributableEntry 20 }

cfprApFirmwareDistributableInvTag OBJECT-TYPE
    SYNTAX       SnmpAdminString
    MAX-ACCESS   read-only
    STATUS       current
    DESCRIPTION
        "Cisco Firepower firmware:Distributable:invTag
        managed object property"
    ::= { cfprApFirmwareDistributableEntry 21 }

cfprApFirmwareDistributableModel OBJECT-TYPE
    SYNTAX       SnmpAdminString
    MAX-ACCESS   read-only
    STATUS       current
    DESCRIPTION
        "Cisco Firepower firmware:Distributable:model managed
        object property"
    ::= { cfprApFirmwareDistributableEntry 22 }

cfprApFirmwareDistributableName OBJECT-TYPE
    SYNTAX       SnmpAdminString
    MAX-ACCESS   read-only
    STATUS       current
    DESCRIPTION
        "Cisco Firepower firmware:Distributable:name managed
        object property"
    ::= { cfprApFirmwareDistributableEntry 23 }

cfprApFirmwareDistributablePlatformVersion OBJECT-TYPE
    SYNTAX       SnmpAdminString
    MAX-ACCESS   read-only
    STATUS       current
    DESCRIPTION
        "Cisco Firepower firmware:Distributable:platformVersion
        managed object property"
    ::= { cfprApFirmwareDistributableEntry 24 }

cfprApFirmwareDistributablePolicyLevel OBJECT-TYPE
    SYNTAX       Gauge32
    MAX-ACCESS   read-only
    STATUS       current
    DESCRIPTION
        "Cisco Firepower firmware:Distributable:policyLevel
        managed object property"
    ::= { cfprApFirmwareDistributableEntry 25 }

cfprApFirmwareDistributablePolicyOwner OBJECT-TYPE
    SYNTAX       CfprApPolicyPolicyOwner
    MAX-ACCESS   read-only
    STATUS       current
    DESCRIPTION
        "Cisco Firepower firmware:Distributable:policyOwner
        managed object property"
    ::= { cfprApFirmwareDistributableEntry 26 }

cfprApFirmwareDistributableTimeStamp OBJECT-TYPE
    SYNTAX       DateAndTime
    MAX-ACCESS   read-only
    STATUS       current
    DESCRIPTION
        "Cisco Firepower firmware:Distributable:timeStamp
        managed object property"
    ::= { cfprApFirmwareDistributableEntry 27 }

cfprApFirmwareDistributableTransferState OBJECT-TYPE
    SYNTAX       CfprApFirmwareTransferState
    MAX-ACCESS   read-only
    STATUS       current
    DESCRIPTION
        "Cisco Firepower firmware:Distributable:transferState
        managed object property"
    ::= { cfprApFirmwareDistributableEntry 28 }

cfprApFirmwareDistributableType OBJECT-TYPE
    SYNTAX       CfprApFirmwareDistributableType
    MAX-ACCESS   read-only
    STATUS       current
    DESCRIPTION
        "Cisco Firepower firmware:Distributable:type managed
        object property"
    ::= { cfprApFirmwareDistributableEntry 29 }

cfprApFirmwareDistributableVendor OBJECT-TYPE
    SYNTAX       SnmpAdminString
    MAX-ACCESS   read-only
    STATUS       current
    DESCRIPTION
        "Cisco Firepower firmware:Distributable:vendor
        managed object property"
    ::= { cfprApFirmwareDistributableEntry 30 }

cfprApFirmwareDistributableVersion OBJECT-TYPE
    SYNTAX       SnmpAdminString
    MAX-ACCESS   read-only
    STATUS       current
    DESCRIPTION
        "Cisco Firepower firmware:Distributable:version
        managed object property"
    ::= { cfprApFirmwareDistributableEntry 31 }

cfprApFirmwareDistributableFsmTable OBJECT-TYPE
    SYNTAX           SEQUENCE OF CfprApFirmwareDistributableFsmEntry
    MAX-ACCESS       not-accessible
    STATUS           current
    DESCRIPTION
        "Cisco Firepower firmware:DistributableFsm managed object table"
    ::= { cfprApFirmwareObjects 24 }

cfprApFirmwareDistributableFsmEntry OBJECT-TYPE
    SYNTAX           CfprApFirmwareDistributableFsmEntry
    MAX-ACCESS       not-accessible
    STATUS           current
    DESCRIPTION
        "Entry for the cfprApFirmwareDistributableFsmTable table."
    INDEX { cfprApFirmwareDistributableFsmInstanceId }
    ::= { cfprApFirmwareDistributableFsmTable 1 }

CfprApFirmwareDistributableFsmEntry ::= SEQUENCE {
    cfprApFirmwareDistributableFsmInstanceId                         CfprApManagedObjectId,
    cfprApFirmwareDistributableFsmDn                                 CfprApManagedObjectDn,
    cfprApFirmwareDistributableFsmRn                                 SnmpAdminString,
    cfprApFirmwareDistributableFsmCompletionTime                     DateAndTime,
    cfprApFirmwareDistributableFsmCurrentFsm                         CfprApFirmwareDistributableFsmCurrentFsm,
    cfprApFirmwareDistributableFsmDescrData                          SnmpAdminString,
    cfprApFirmwareDistributableFsmFsmStatus                          CfprApFsmFsmStageStatus,
    cfprApFirmwareDistributableFsmProgress                           Gauge32,
    cfprApFirmwareDistributableFsmRmtErrCode                         Gauge32,
    cfprApFirmwareDistributableFsmRmtErrDescr                        SnmpAdminString,
    cfprApFirmwareDistributableFsmRmtRslt                            CfprApConditionRemoteInvRslt
}

cfprApFirmwareDistributableFsmInstanceId OBJECT-TYPE
    SYNTAX       CfprApManagedObjectId
    MAX-ACCESS   not-accessible
    STATUS       current
    DESCRIPTION
        "Instance identifier of the managed object."
    ::= { cfprApFirmwareDistributableFsmEntry 1 }

cfprApFirmwareDistributableFsmDn OBJECT-TYPE
    SYNTAX       CfprApManagedObjectDn
    MAX-ACCESS   read-only
    STATUS       current
    DESCRIPTION
        "Cisco Firepower firmware:DistributableFsm:dn managed
        object property"
    ::= { cfprApFirmwareDistributableFsmEntry 2 }

cfprApFirmwareDistributableFsmRn OBJECT-TYPE
    SYNTAX       SnmpAdminString
    MAX-ACCESS   read-only
    STATUS       current
    DESCRIPTION
        "Cisco Firepower firmware:DistributableFsm:rn managed
        object property"
    ::= { cfprApFirmwareDistributableFsmEntry 3 }

cfprApFirmwareDistributableFsmCompletionTime OBJECT-TYPE
    SYNTAX       DateAndTime
    MAX-ACCESS   read-only
    STATUS       current
    DESCRIPTION
        "Cisco Firepower firmware:DistributableFsm:completionTime
        managed object property"
    ::= { cfprApFirmwareDistributableFsmEntry 4 }

cfprApFirmwareDistributableFsmCurrentFsm OBJECT-TYPE
    SYNTAX       CfprApFirmwareDistributableFsmCurrentFsm
    MAX-ACCESS   read-only
    STATUS       current
    DESCRIPTION
        "Cisco Firepower firmware:DistributableFsm:currentFsm
        managed object property"
    ::= { cfprApFirmwareDistributableFsmEntry 5 }

cfprApFirmwareDistributableFsmDescrData OBJECT-TYPE
    SYNTAX       SnmpAdminString
    MAX-ACCESS   read-only
    STATUS       current
    DESCRIPTION
        "Cisco Firepower firmware:DistributableFsm:descr
        managed object property"
    ::= { cfprApFirmwareDistributableFsmEntry 6 }

cfprApFirmwareDistributableFsmFsmStatus OBJECT-TYPE
    SYNTAX       CfprApFsmFsmStageStatus
    MAX-ACCESS   read-only
    STATUS       current
    DESCRIPTION
        "Cisco Firepower firmware:DistributableFsm:fsmStatus
        managed object property"
    ::= { cfprApFirmwareDistributableFsmEntry 7 }

cfprApFirmwareDistributableFsmProgress OBJECT-TYPE
    SYNTAX       Gauge32
    MAX-ACCESS   read-only
    STATUS       current
    DESCRIPTION
        "Cisco Firepower firmware:DistributableFsm:progress
        managed object property"
    ::= { cfprApFirmwareDistributableFsmEntry 8 }

cfprApFirmwareDistributableFsmRmtErrCode OBJECT-TYPE
    SYNTAX       Gauge32
    MAX-ACCESS   read-only
    STATUS       current
    DESCRIPTION
        "Cisco Firepower firmware:DistributableFsm:rmtErrCode
        managed object property"
    ::= { cfprApFirmwareDistributableFsmEntry 9 }

cfprApFirmwareDistributableFsmRmtErrDescr OBJECT-TYPE
    SYNTAX       SnmpAdminString
    MAX-ACCESS   read-only
    STATUS       current
    DESCRIPTION
        "Cisco Firepower firmware:DistributableFsm:rmtErrDescr
        managed object property"
    ::= { cfprApFirmwareDistributableFsmEntry 10 }

cfprApFirmwareDistributableFsmRmtRslt OBJECT-TYPE
    SYNTAX       CfprApConditionRemoteInvRslt
    MAX-ACCESS   read-only
    STATUS       current
    DESCRIPTION
        "Cisco Firepower firmware:DistributableFsm:rmtRslt
        managed object property"
    ::= { cfprApFirmwareDistributableFsmEntry 11 }

cfprApFirmwareDistributableFsmStageTable OBJECT-TYPE
    SYNTAX           SEQUENCE OF CfprApFirmwareDistributableFsmStageEntry
    MAX-ACCESS       not-accessible
    STATUS           current
    DESCRIPTION
        "Cisco Firepower firmware:DistributableFsmStage
        managed object table"
    ::= { cfprApFirmwareObjects 25 }

cfprApFirmwareDistributableFsmStageEntry OBJECT-TYPE
    SYNTAX           CfprApFirmwareDistributableFsmStageEntry
    MAX-ACCESS       not-accessible
    STATUS           current
    DESCRIPTION
        "Entry for the cfprApFirmwareDistributableFsmStageTable table."
    INDEX { cfprApFirmwareDistributableFsmStageInstanceId }
    ::= { cfprApFirmwareDistributableFsmStageTable 1 }

CfprApFirmwareDistributableFsmStageEntry ::= SEQUENCE {
    cfprApFirmwareDistributableFsmStageInstanceId                    CfprApManagedObjectId,
    cfprApFirmwareDistributableFsmStageDn                            CfprApManagedObjectDn,
    cfprApFirmwareDistributableFsmStageRn                            SnmpAdminString,
    cfprApFirmwareDistributableFsmStageDescrData                     SnmpAdminString,
    cfprApFirmwareDistributableFsmStageLastUpdateTime                DateAndTime,
    cfprApFirmwareDistributableFsmStageName                          CfprApFirmwareDistributableFsmStageName,
    cfprApFirmwareDistributableFsmStageOrder                         Gauge32,
    cfprApFirmwareDistributableFsmStageRetry                         Gauge32,
    cfprApFirmwareDistributableFsmStageStageStatus                   CfprApFsmFsmStageStatus
}

cfprApFirmwareDistributableFsmStageInstanceId OBJECT-TYPE
    SYNTAX       CfprApManagedObjectId
    MAX-ACCESS   not-accessible
    STATUS       current
    DESCRIPTION
        "Instance identifier of the managed object."
    ::= { cfprApFirmwareDistributableFsmStageEntry 1 }

cfprApFirmwareDistributableFsmStageDn OBJECT-TYPE
    SYNTAX       CfprApManagedObjectDn
    MAX-ACCESS   read-only
    STATUS       current
    DESCRIPTION
        "Cisco Firepower firmware:DistributableFsmStage:dn
        managed object property"
    ::= { cfprApFirmwareDistributableFsmStageEntry 2 }

cfprApFirmwareDistributableFsmStageRn OBJECT-TYPE
    SYNTAX       SnmpAdminString
    MAX-ACCESS   read-only
    STATUS       current
    DESCRIPTION
        "Cisco Firepower firmware:DistributableFsmStage:rn
        managed object property"
    ::= { cfprApFirmwareDistributableFsmStageEntry 3 }

cfprApFirmwareDistributableFsmStageDescrData OBJECT-TYPE
    SYNTAX       SnmpAdminString
    MAX-ACCESS   read-only
    STATUS       current
    DESCRIPTION
        "Cisco Firepower firmware:DistributableFsmStage:descr
        managed object property"
    ::= { cfprApFirmwareDistributableFsmStageEntry 4 }

cfprApFirmwareDistributableFsmStageLastUpdateTime OBJECT-TYPE
    SYNTAX       DateAndTime
    MAX-ACCESS   read-only
    STATUS       current
    DESCRIPTION
        "Cisco Firepower firmware:DistributableFsmStage:lastUpdateTime
        managed object property"
    ::= { cfprApFirmwareDistributableFsmStageEntry 5 }

cfprApFirmwareDistributableFsmStageName OBJECT-TYPE
    SYNTAX       CfprApFirmwareDistributableFsmStageName
    MAX-ACCESS   read-only
    STATUS       current
    DESCRIPTION
        "Cisco Firepower firmware:DistributableFsmStage:name
        managed object property"
    ::= { cfprApFirmwareDistributableFsmStageEntry 6 }

cfprApFirmwareDistributableFsmStageOrder OBJECT-TYPE
    SYNTAX       Gauge32
    MAX-ACCESS   read-only
    STATUS       current
    DESCRIPTION
        "Cisco Firepower firmware:DistributableFsmStage:order
        managed object property"
    ::= { cfprApFirmwareDistributableFsmStageEntry 7 }

cfprApFirmwareDistributableFsmStageRetry OBJECT-TYPE
    SYNTAX       Gauge32
    MAX-ACCESS   read-only
    STATUS       current
    DESCRIPTION
        "Cisco Firepower firmware:DistributableFsmStage:retry
        managed object property"
    ::= { cfprApFirmwareDistributableFsmStageEntry 8 }

cfprApFirmwareDistributableFsmStageStageStatus OBJECT-TYPE
    SYNTAX       CfprApFsmFsmStageStatus
    MAX-ACCESS   read-only
    STATUS       current
    DESCRIPTION
        "Cisco Firepower firmware:DistributableFsmStage:stageStatus
        managed object property"
    ::= { cfprApFirmwareDistributableFsmStageEntry 9 }

cfprApFirmwareDistributableFsmTaskTable OBJECT-TYPE
    SYNTAX           SEQUENCE OF CfprApFirmwareDistributableFsmTaskEntry
    MAX-ACCESS       not-accessible
    STATUS           current
    DESCRIPTION
        "Cisco Firepower firmware:DistributableFsmTask
        managed object table"
    ::= { cfprApFirmwareObjects 26 }

cfprApFirmwareDistributableFsmTaskEntry OBJECT-TYPE
    SYNTAX           CfprApFirmwareDistributableFsmTaskEntry
    MAX-ACCESS       not-accessible
    STATUS           current
    DESCRIPTION
        "Entry for the cfprApFirmwareDistributableFsmTaskTable table."
    INDEX { cfprApFirmwareDistributableFsmTaskInstanceId }
    ::= { cfprApFirmwareDistributableFsmTaskTable 1 }

CfprApFirmwareDistributableFsmTaskEntry ::= SEQUENCE {
    cfprApFirmwareDistributableFsmTaskInstanceId                     CfprApManagedObjectId,
    cfprApFirmwareDistributableFsmTaskDn                             CfprApManagedObjectDn,
    cfprApFirmwareDistributableFsmTaskRn                             SnmpAdminString,
    cfprApFirmwareDistributableFsmTaskCompletion                     CfprApFsmCompletion,
    cfprApFirmwareDistributableFsmTaskFlags                          CfprApFsmFlags,
    cfprApFirmwareDistributableFsmTaskItem                           CfprApFirmwareDistributableFsmTaskItem,
    cfprApFirmwareDistributableFsmTaskSeqId                          Gauge32
}

cfprApFirmwareDistributableFsmTaskInstanceId OBJECT-TYPE
    SYNTAX       CfprApManagedObjectId
    MAX-ACCESS   not-accessible
    STATUS       current
    DESCRIPTION
        "Instance identifier of the managed object."
    ::= { cfprApFirmwareDistributableFsmTaskEntry 1 }

cfprApFirmwareDistributableFsmTaskDn OBJECT-TYPE
    SYNTAX       CfprApManagedObjectDn
    MAX-ACCESS   read-only
    STATUS       current
    DESCRIPTION
        "Cisco Firepower firmware:DistributableFsmTask:dn
        managed object property"
    ::= { cfprApFirmwareDistributableFsmTaskEntry 2 }

cfprApFirmwareDistributableFsmTaskRn OBJECT-TYPE
    SYNTAX       SnmpAdminString
    MAX-ACCESS   read-only
    STATUS       current
    DESCRIPTION
        "Cisco Firepower firmware:DistributableFsmTask:rn
        managed object property"
    ::= { cfprApFirmwareDistributableFsmTaskEntry 3 }

cfprApFirmwareDistributableFsmTaskCompletion OBJECT-TYPE
    SYNTAX       CfprApFsmCompletion
    MAX-ACCESS   read-only
    STATUS       current
    DESCRIPTION
        "Cisco Firepower firmware:DistributableFsmTask:completion
        managed object property"
    ::= { cfprApFirmwareDistributableFsmTaskEntry 4 }

cfprApFirmwareDistributableFsmTaskFlags OBJECT-TYPE
    SYNTAX       CfprApFsmFlags
    MAX-ACCESS   read-only
    STATUS       current
    DESCRIPTION
        "Cisco Firepower firmware:DistributableFsmTask:flags
        managed object property"
    ::= { cfprApFirmwareDistributableFsmTaskEntry 5 }

cfprApFirmwareDistributableFsmTaskItem OBJECT-TYPE
    SYNTAX       CfprApFirmwareDistributableFsmTaskItem
    MAX-ACCESS   read-only
    STATUS       current
    DESCRIPTION
        "Cisco Firepower firmware:DistributableFsmTask:item
        managed object property"
    ::= { cfprApFirmwareDistributableFsmTaskEntry 6 }

cfprApFirmwareDistributableFsmTaskSeqId OBJECT-TYPE
    SYNTAX       Gauge32
    MAX-ACCESS   read-only
    STATUS       current
    DESCRIPTION
        "Cisco Firepower firmware:DistributableFsmTask:seqId
        managed object property"
    ::= { cfprApFirmwareDistributableFsmTaskEntry 7 }

cfprApFirmwareDownloaderTable OBJECT-TYPE
    SYNTAX           SEQUENCE OF CfprApFirmwareDownloaderEntry
    MAX-ACCESS       not-accessible
    STATUS           current
    DESCRIPTION
        "Cisco Firepower firmware:Downloader managed object table"
    ::= { cfprApFirmwareObjects 27 }

cfprApFirmwareDownloaderEntry OBJECT-TYPE
    SYNTAX           CfprApFirmwareDownloaderEntry
    MAX-ACCESS       not-accessible
    STATUS           current
    DESCRIPTION
        "Entry for the cfprApFirmwareDownloaderTable table."
    INDEX { cfprApFirmwareDownloaderInstanceId }
    ::= { cfprApFirmwareDownloaderTable 1 }

CfprApFirmwareDownloaderEntry ::= SEQUENCE {
    cfprApFirmwareDownloaderInstanceId                               CfprApManagedObjectId,
    cfprApFirmwareDownloaderDn                                       CfprApManagedObjectDn,
    cfprApFirmwareDownloaderRn                                       SnmpAdminString,
    cfprApFirmwareDownloaderAdminState                               CfprApFirmwareDownloadActivity,
    cfprApFirmwareDownloaderFileName                                 SnmpAdminString,
    cfprApFirmwareDownloaderFsmDescr                                 SnmpAdminString,
    cfprApFirmwareDownloaderFsmPrev                                  SnmpAdminString,
    cfprApFirmwareDownloaderFsmProgr                                 Gauge32,
    cfprApFirmwareDownloaderFsmRmtInvErrCode                         Gauge32,
    cfprApFirmwareDownloaderFsmRmtInvErrDescr                        SnmpAdminString,
    cfprApFirmwareDownloaderFsmRmtInvRslt                            CfprApConditionRemoteInvRslt,
    cfprApFirmwareDownloaderFsmStageDescr                            SnmpAdminString,
    cfprApFirmwareDownloaderFsmStamp                                 DateAndTime,
    cfprApFirmwareDownloaderFsmStatus                                SnmpAdminString,
    cfprApFirmwareDownloaderFsmTry                                   Gauge32,
    cfprApFirmwareDownloaderImageSize                                Gauge32,
    cfprApFirmwareDownloaderPort                                     Gauge32,
    cfprApFirmwareDownloaderProtocol                                 CfprApFirmwareTransport,
    cfprApFirmwareDownloaderPwd                                      SnmpAdminString,
    cfprApFirmwareDownloaderRemotePath                               SnmpAdminString,
    cfprApFirmwareDownloaderServer                                   SnmpAdminString,
    cfprApFirmwareDownloaderStartTime                                DateAndTime,
    cfprApFirmwareDownloaderTimeStamp                                DateAndTime,
    cfprApFirmwareDownloaderTransferRate                             INTEGER,
    cfprApFirmwareDownloaderTransferState                            CfprApFirmwareTransferState,
    cfprApFirmwareDownloaderUser                                     SnmpAdminString
}

cfprApFirmwareDownloaderInstanceId OBJECT-TYPE
    SYNTAX       CfprApManagedObjectId
    MAX-ACCESS   not-accessible
    STATUS       current
    DESCRIPTION
        "Instance identifier of the managed object."
    ::= { cfprApFirmwareDownloaderEntry 1 }

cfprApFirmwareDownloaderDn OBJECT-TYPE
    SYNTAX       CfprApManagedObjectDn
    MAX-ACCESS   read-only
    STATUS       current
    DESCRIPTION
        "Cisco Firepower firmware:Downloader:dn managed object property"
    ::= { cfprApFirmwareDownloaderEntry 2 }

cfprApFirmwareDownloaderRn OBJECT-TYPE
    SYNTAX       SnmpAdminString
    MAX-ACCESS   read-only
    STATUS       current
    DESCRIPTION
        "Cisco Firepower firmware:Downloader:rn managed object property"
    ::= { cfprApFirmwareDownloaderEntry 3 }

cfprApFirmwareDownloaderAdminState OBJECT-TYPE
    SYNTAX       CfprApFirmwareDownloadActivity
    MAX-ACCESS   read-only
    STATUS       current
    DESCRIPTION
        "Cisco Firepower firmware:Downloader:adminState
        managed object property"
    ::= { cfprApFirmwareDownloaderEntry 4 }

cfprApFirmwareDownloaderFileName OBJECT-TYPE
    SYNTAX       SnmpAdminString
    MAX-ACCESS   read-only
    STATUS       current
    DESCRIPTION
        "Cisco Firepower firmware:Downloader:fileName managed
        object property"
    ::= { cfprApFirmwareDownloaderEntry 5 }

cfprApFirmwareDownloaderFsmDescr OBJECT-TYPE
    SYNTAX       SnmpAdminString
    MAX-ACCESS   read-only
    STATUS       current
    DESCRIPTION
        "Cisco Firepower firmware:Downloader:fsmDescr managed
        object property"
    ::= { cfprApFirmwareDownloaderEntry 6 }

cfprApFirmwareDownloaderFsmPrev OBJECT-TYPE
    SYNTAX       SnmpAdminString
    MAX-ACCESS   read-only
    STATUS       current
    DESCRIPTION
        "Cisco Firepower firmware:Downloader:fsmPrev managed
        object property"
    ::= { cfprApFirmwareDownloaderEntry 7 }

cfprApFirmwareDownloaderFsmProgr OBJECT-TYPE
    SYNTAX       Gauge32
    MAX-ACCESS   read-only
    STATUS       current
    DESCRIPTION
        "Cisco Firepower firmware:Downloader:fsmProgr managed
        object property"
    ::= { cfprApFirmwareDownloaderEntry 8 }

cfprApFirmwareDownloaderFsmRmtInvErrCode OBJECT-TYPE
    SYNTAX       Gauge32
    MAX-ACCESS   read-only
    STATUS       current
    DESCRIPTION
        "Cisco Firepower firmware:Downloader:fsmRmtInvErrCode
        managed object property"
    ::= { cfprApFirmwareDownloaderEntry 9 }

cfprApFirmwareDownloaderFsmRmtInvErrDescr OBJECT-TYPE
    SYNTAX       SnmpAdminString
    MAX-ACCESS   read-only
    STATUS       current
    DESCRIPTION
        "Cisco Firepower firmware:Downloader:fsmRmtInvErrDescr
        managed object property"
    ::= { cfprApFirmwareDownloaderEntry 10 }

cfprApFirmwareDownloaderFsmRmtInvRslt OBJECT-TYPE
    SYNTAX       CfprApConditionRemoteInvRslt
    MAX-ACCESS   read-only
    STATUS       current
    DESCRIPTION
        "Cisco Firepower firmware:Downloader:fsmRmtInvRslt
        managed object property"
    ::= { cfprApFirmwareDownloaderEntry 11 }

cfprApFirmwareDownloaderFsmStageDescr OBJECT-TYPE
    SYNTAX       SnmpAdminString
    MAX-ACCESS   read-only
    STATUS       current
    DESCRIPTION
        "Cisco Firepower firmware:Downloader:fsmStageDescr
        managed object property"
    ::= { cfprApFirmwareDownloaderEntry 12 }

cfprApFirmwareDownloaderFsmStamp OBJECT-TYPE
    SYNTAX       DateAndTime
    MAX-ACCESS   read-only
    STATUS       current
    DESCRIPTION
        "Cisco Firepower firmware:Downloader:fsmStamp managed
        object property"
    ::= { cfprApFirmwareDownloaderEntry 13 }

cfprApFirmwareDownloaderFsmStatus OBJECT-TYPE
    SYNTAX       SnmpAdminString
    MAX-ACCESS   read-only
    STATUS       current
    DESCRIPTION
        "Cisco Firepower firmware:Downloader:fsmStatus
        managed object property"
    ::= { cfprApFirmwareDownloaderEntry 14 }

cfprApFirmwareDownloaderFsmTry OBJECT-TYPE
    SYNTAX       Gauge32
    MAX-ACCESS   read-only
    STATUS       current
    DESCRIPTION
        "Cisco Firepower firmware:Downloader:fsmTry managed
        object property"
    ::= { cfprApFirmwareDownloaderEntry 15 }

cfprApFirmwareDownloaderImageSize OBJECT-TYPE
    SYNTAX       Gauge32
    MAX-ACCESS   read-only
    STATUS       current
    DESCRIPTION
        "Cisco Firepower firmware:Downloader:imageSize
        managed object property"
    ::= { cfprApFirmwareDownloaderEntry 16 }

cfprApFirmwareDownloaderPort OBJECT-TYPE
    SYNTAX       Gauge32
    MAX-ACCESS   read-only
    STATUS       current
    DESCRIPTION
        "Cisco Firepower firmware:Downloader:port managed object property"
    ::= { cfprApFirmwareDownloaderEntry 17 }

cfprApFirmwareDownloaderProtocol OBJECT-TYPE
    SYNTAX       CfprApFirmwareTransport
    MAX-ACCESS   read-only
    STATUS       current
    DESCRIPTION
        "Cisco Firepower firmware:Downloader:protocol managed
        object property"
    ::= { cfprApFirmwareDownloaderEntry 18 }

cfprApFirmwareDownloaderPwd OBJECT-TYPE
    SYNTAX       SnmpAdminString
    MAX-ACCESS   read-only
    STATUS       current
    DESCRIPTION
        "Cisco Firepower firmware:Downloader:pwd managed object property"
    ::= { cfprApFirmwareDownloaderEntry 19 }

cfprApFirmwareDownloaderRemotePath OBJECT-TYPE
    SYNTAX       SnmpAdminString
    MAX-ACCESS   read-only
    STATUS       current
    DESCRIPTION
        "Cisco Firepower firmware:Downloader:remotePath
        managed object property"
    ::= { cfprApFirmwareDownloaderEntry 20 }

cfprApFirmwareDownloaderServer OBJECT-TYPE
    SYNTAX       SnmpAdminString
    MAX-ACCESS   read-only
    STATUS       current
    DESCRIPTION
        "Cisco Firepower firmware:Downloader:server managed
        object property"
    ::= { cfprApFirmwareDownloaderEntry 21 }

cfprApFirmwareDownloaderStartTime OBJECT-TYPE
    SYNTAX       DateAndTime
    MAX-ACCESS   read-only
    STATUS       current
    DESCRIPTION
        "Cisco Firepower firmware:Downloader:startTime
        managed object property"
    ::= { cfprApFirmwareDownloaderEntry 22 }

cfprApFirmwareDownloaderTimeStamp OBJECT-TYPE
    SYNTAX       DateAndTime
    MAX-ACCESS   read-only
    STATUS       current
    DESCRIPTION
        "Cisco Firepower firmware:Downloader:timeStamp
        managed object property"
    ::= { cfprApFirmwareDownloaderEntry 23 }

cfprApFirmwareDownloaderTransferRate OBJECT-TYPE
    SYNTAX       INTEGER
    MAX-ACCESS   read-only
    STATUS       current
    DESCRIPTION
        "Cisco Firepower firmware:Downloader:transferRate
        managed object property"
    ::= { cfprApFirmwareDownloaderEntry 24 }

cfprApFirmwareDownloaderTransferState OBJECT-TYPE
    SYNTAX       CfprApFirmwareTransferState
    MAX-ACCESS   read-only
    STATUS       current
    DESCRIPTION
        "Cisco Firepower firmware:Downloader:transferState
        managed object property"
    ::= { cfprApFirmwareDownloaderEntry 25 }

cfprApFirmwareDownloaderUser OBJECT-TYPE
    SYNTAX       SnmpAdminString
    MAX-ACCESS   read-only
    STATUS       current
    DESCRIPTION
        "Cisco Firepower firmware:Downloader:user managed object property"
    ::= { cfprApFirmwareDownloaderEntry 26 }

cfprApFirmwareDownloaderFsmTable OBJECT-TYPE
    SYNTAX           SEQUENCE OF CfprApFirmwareDownloaderFsmEntry
    MAX-ACCESS       not-accessible
    STATUS           current
    DESCRIPTION
        "Cisco Firepower firmware:DownloaderFsm managed object table"
    ::= { cfprApFirmwareObjects 28 }

cfprApFirmwareDownloaderFsmEntry OBJECT-TYPE
    SYNTAX           CfprApFirmwareDownloaderFsmEntry
    MAX-ACCESS       not-accessible
    STATUS           current
    DESCRIPTION
        "Entry for the cfprApFirmwareDownloaderFsmTable table."
    INDEX { cfprApFirmwareDownloaderFsmInstanceId }
    ::= { cfprApFirmwareDownloaderFsmTable 1 }

CfprApFirmwareDownloaderFsmEntry ::= SEQUENCE {
    cfprApFirmwareDownloaderFsmInstanceId                            CfprApManagedObjectId,
    cfprApFirmwareDownloaderFsmDn                                    CfprApManagedObjectDn,
    cfprApFirmwareDownloaderFsmRn                                    SnmpAdminString,
    cfprApFirmwareDownloaderFsmCompletionTime                        DateAndTime,
    cfprApFirmwareDownloaderFsmCurrentFsm                            CfprApFirmwareDownloaderFsmCurrentFsm,
    cfprApFirmwareDownloaderFsmDescrData                             SnmpAdminString,
    cfprApFirmwareDownloaderFsmFsmStatus                             CfprApFsmFsmStageStatus,
    cfprApFirmwareDownloaderFsmProgress                              Gauge32,
    cfprApFirmwareDownloaderFsmRmtErrCode                            Gauge32,
    cfprApFirmwareDownloaderFsmRmtErrDescr                           SnmpAdminString,
    cfprApFirmwareDownloaderFsmRmtRslt                               CfprApConditionRemoteInvRslt
}

cfprApFirmwareDownloaderFsmInstanceId OBJECT-TYPE
    SYNTAX       CfprApManagedObjectId
    MAX-ACCESS   not-accessible
    STATUS       current
    DESCRIPTION
        "Instance identifier of the managed object."
    ::= { cfprApFirmwareDownloaderFsmEntry 1 }

cfprApFirmwareDownloaderFsmDn OBJECT-TYPE
    SYNTAX       CfprApManagedObjectDn
    MAX-ACCESS   read-only
    STATUS       current
    DESCRIPTION
        "Cisco Firepower firmware:DownloaderFsm:dn managed
        object property"
    ::= { cfprApFirmwareDownloaderFsmEntry 2 }

cfprApFirmwareDownloaderFsmRn OBJECT-TYPE
    SYNTAX       SnmpAdminString
    MAX-ACCESS   read-only
    STATUS       current
    DESCRIPTION
        "Cisco Firepower firmware:DownloaderFsm:rn managed
        object property"
    ::= { cfprApFirmwareDownloaderFsmEntry 3 }

cfprApFirmwareDownloaderFsmCompletionTime OBJECT-TYPE
    SYNTAX       DateAndTime
    MAX-ACCESS   read-only
    STATUS       current
    DESCRIPTION
        "Cisco Firepower firmware:DownloaderFsm:completionTime
        managed object property"
    ::= { cfprApFirmwareDownloaderFsmEntry 4 }

cfprApFirmwareDownloaderFsmCurrentFsm OBJECT-TYPE
    SYNTAX       CfprApFirmwareDownloaderFsmCurrentFsm
    MAX-ACCESS   read-only
    STATUS       current
    DESCRIPTION
        "Cisco Firepower firmware:DownloaderFsm:currentFsm
        managed object property"
    ::= { cfprApFirmwareDownloaderFsmEntry 5 }

cfprApFirmwareDownloaderFsmDescrData OBJECT-TYPE
    SYNTAX       SnmpAdminString
    MAX-ACCESS   read-only
    STATUS       current
    DESCRIPTION
        "Cisco Firepower firmware:DownloaderFsm:descr managed
        object property"
    ::= { cfprApFirmwareDownloaderFsmEntry 6 }

cfprApFirmwareDownloaderFsmFsmStatus OBJECT-TYPE
    SYNTAX       CfprApFsmFsmStageStatus
    MAX-ACCESS   read-only
    STATUS       current
    DESCRIPTION
        "Cisco Firepower firmware:DownloaderFsm:fsmStatus
        managed object property"
    ::= { cfprApFirmwareDownloaderFsmEntry 7 }

cfprApFirmwareDownloaderFsmProgress OBJECT-TYPE
    SYNTAX       Gauge32
    MAX-ACCESS   read-only
    STATUS       current
    DESCRIPTION
        "Cisco Firepower firmware:DownloaderFsm:progress
        managed object property"
    ::= { cfprApFirmwareDownloaderFsmEntry 8 }

cfprApFirmwareDownloaderFsmRmtErrCode OBJECT-TYPE
    SYNTAX       Gauge32
    MAX-ACCESS   read-only
    STATUS       current
    DESCRIPTION
        "Cisco Firepower firmware:DownloaderFsm:rmtErrCode
        managed object property"
    ::= { cfprApFirmwareDownloaderFsmEntry 9 }

cfprApFirmwareDownloaderFsmRmtErrDescr OBJECT-TYPE
    SYNTAX       SnmpAdminString
    MAX-ACCESS   read-only
    STATUS       current
    DESCRIPTION
        "Cisco Firepower firmware:DownloaderFsm:rmtErrDescr
        managed object property"
    ::= { cfprApFirmwareDownloaderFsmEntry 10 }

cfprApFirmwareDownloaderFsmRmtRslt OBJECT-TYPE
    SYNTAX       CfprApConditionRemoteInvRslt
    MAX-ACCESS   read-only
    STATUS       current
    DESCRIPTION
        "Cisco Firepower firmware:DownloaderFsm:rmtRslt
        managed object property"
    ::= { cfprApFirmwareDownloaderFsmEntry 11 }

cfprApFirmwareDownloaderFsmStageTable OBJECT-TYPE
    SYNTAX           SEQUENCE OF CfprApFirmwareDownloaderFsmStageEntry
    MAX-ACCESS       not-accessible
    STATUS           current
    DESCRIPTION
        "Cisco Firepower firmware:DownloaderFsmStage managed object table"
    ::= { cfprApFirmwareObjects 29 }

cfprApFirmwareDownloaderFsmStageEntry OBJECT-TYPE
    SYNTAX           CfprApFirmwareDownloaderFsmStageEntry
    MAX-ACCESS       not-accessible
    STATUS           current
    DESCRIPTION
        "Entry for the cfprApFirmwareDownloaderFsmStageTable table."
    INDEX { cfprApFirmwareDownloaderFsmStageInstanceId }
    ::= { cfprApFirmwareDownloaderFsmStageTable 1 }

CfprApFirmwareDownloaderFsmStageEntry ::= SEQUENCE {
    cfprApFirmwareDownloaderFsmStageInstanceId                       CfprApManagedObjectId,
    cfprApFirmwareDownloaderFsmStageDn                               CfprApManagedObjectDn,
    cfprApFirmwareDownloaderFsmStageRn                               SnmpAdminString,
    cfprApFirmwareDownloaderFsmStageDescrData                        SnmpAdminString,
    cfprApFirmwareDownloaderFsmStageLastUpdateTime                   DateAndTime,
    cfprApFirmwareDownloaderFsmStageName                             CfprApFirmwareDownloaderFsmStageName,
    cfprApFirmwareDownloaderFsmStageOrder                            Gauge32,
    cfprApFirmwareDownloaderFsmStageRetry                            Gauge32,
    cfprApFirmwareDownloaderFsmStageStageStatus                      CfprApFsmFsmStageStatus
}

cfprApFirmwareDownloaderFsmStageInstanceId OBJECT-TYPE
    SYNTAX       CfprApManagedObjectId
    MAX-ACCESS   not-accessible
    STATUS       current
    DESCRIPTION
        "Instance identifier of the managed object."
    ::= { cfprApFirmwareDownloaderFsmStageEntry 1 }

cfprApFirmwareDownloaderFsmStageDn OBJECT-TYPE
    SYNTAX       CfprApManagedObjectDn
    MAX-ACCESS   read-only
    STATUS       current
    DESCRIPTION
        "Cisco Firepower firmware:DownloaderFsmStage:dn
        managed object property"
    ::= { cfprApFirmwareDownloaderFsmStageEntry 2 }

cfprApFirmwareDownloaderFsmStageRn OBJECT-TYPE
    SYNTAX       SnmpAdminString
    MAX-ACCESS   read-only
    STATUS       current
    DESCRIPTION
        "Cisco Firepower firmware:DownloaderFsmStage:rn
        managed object property"
    ::= { cfprApFirmwareDownloaderFsmStageEntry 3 }

cfprApFirmwareDownloaderFsmStageDescrData OBJECT-TYPE
    SYNTAX       SnmpAdminString
    MAX-ACCESS   read-only
    STATUS       current
    DESCRIPTION
        "Cisco Firepower firmware:DownloaderFsmStage:descr
        managed object property"
    ::= { cfprApFirmwareDownloaderFsmStageEntry 4 }

cfprApFirmwareDownloaderFsmStageLastUpdateTime OBJECT-TYPE
    SYNTAX       DateAndTime
    MAX-ACCESS   read-only
    STATUS       current
    DESCRIPTION
        "Cisco Firepower firmware:DownloaderFsmStage:lastUpdateTime
        managed object property"
    ::= { cfprApFirmwareDownloaderFsmStageEntry 5 }

cfprApFirmwareDownloaderFsmStageName OBJECT-TYPE
    SYNTAX       CfprApFirmwareDownloaderFsmStageName
    MAX-ACCESS   read-only
    STATUS       current
    DESCRIPTION
        "Cisco Firepower firmware:DownloaderFsmStage:name
        managed object property"
    ::= { cfprApFirmwareDownloaderFsmStageEntry 6 }

cfprApFirmwareDownloaderFsmStageOrder OBJECT-TYPE
    SYNTAX       Gauge32
    MAX-ACCESS   read-only
    STATUS       current
    DESCRIPTION
        "Cisco Firepower firmware:DownloaderFsmStage:order
        managed object property"
    ::= { cfprApFirmwareDownloaderFsmStageEntry 7 }

cfprApFirmwareDownloaderFsmStageRetry OBJECT-TYPE
    SYNTAX       Gauge32
    MAX-ACCESS   read-only
    STATUS       current
    DESCRIPTION
        "Cisco Firepower firmware:DownloaderFsmStage:retry
        managed object property"
    ::= { cfprApFirmwareDownloaderFsmStageEntry 8 }

cfprApFirmwareDownloaderFsmStageStageStatus OBJECT-TYPE
    SYNTAX       CfprApFsmFsmStageStatus
    MAX-ACCESS   read-only
    STATUS       current
    DESCRIPTION
        "Cisco Firepower firmware:DownloaderFsmStage:stageStatus
        managed object property"
    ::= { cfprApFirmwareDownloaderFsmStageEntry 9 }

cfprApFirmwareDownloaderFsmTaskTable OBJECT-TYPE
    SYNTAX           SEQUENCE OF CfprApFirmwareDownloaderFsmTaskEntry
    MAX-ACCESS       not-accessible
    STATUS           current
    DESCRIPTION
        "Cisco Firepower firmware:DownloaderFsmTask managed object table"
    ::= { cfprApFirmwareObjects 30 }

cfprApFirmwareDownloaderFsmTaskEntry OBJECT-TYPE
    SYNTAX           CfprApFirmwareDownloaderFsmTaskEntry
    MAX-ACCESS       not-accessible
    STATUS           current
    DESCRIPTION
        "Entry for the cfprApFirmwareDownloaderFsmTaskTable table."
    INDEX { cfprApFirmwareDownloaderFsmTaskInstanceId }
    ::= { cfprApFirmwareDownloaderFsmTaskTable 1 }

CfprApFirmwareDownloaderFsmTaskEntry ::= SEQUENCE {
    cfprApFirmwareDownloaderFsmTaskInstanceId                        CfprApManagedObjectId,
    cfprApFirmwareDownloaderFsmTaskDn                                CfprApManagedObjectDn,
    cfprApFirmwareDownloaderFsmTaskRn                                SnmpAdminString,
    cfprApFirmwareDownloaderFsmTaskCompletion                        CfprApFsmCompletion,
    cfprApFirmwareDownloaderFsmTaskFlags                             CfprApFsmFlags,
    cfprApFirmwareDownloaderFsmTaskItem                              CfprApFirmwareDownloaderFsmTaskItem,
    cfprApFirmwareDownloaderFsmTaskSeqId                             Gauge32
}

cfprApFirmwareDownloaderFsmTaskInstanceId OBJECT-TYPE
    SYNTAX       CfprApManagedObjectId
    MAX-ACCESS   not-accessible
    STATUS       current
    DESCRIPTION
        "Instance identifier of the managed object."
    ::= { cfprApFirmwareDownloaderFsmTaskEntry 1 }

cfprApFirmwareDownloaderFsmTaskDn OBJECT-TYPE
    SYNTAX       CfprApManagedObjectDn
    MAX-ACCESS   read-only
    STATUS       current
    DESCRIPTION
        "Cisco Firepower firmware:DownloaderFsmTask:dn
        managed object property"
    ::= { cfprApFirmwareDownloaderFsmTaskEntry 2 }

cfprApFirmwareDownloaderFsmTaskRn OBJECT-TYPE
    SYNTAX       SnmpAdminString
    MAX-ACCESS   read-only
    STATUS       current
    DESCRIPTION
        "Cisco Firepower firmware:DownloaderFsmTask:rn
        managed object property"
    ::= { cfprApFirmwareDownloaderFsmTaskEntry 3 }

cfprApFirmwareDownloaderFsmTaskCompletion OBJECT-TYPE
    SYNTAX       CfprApFsmCompletion
    MAX-ACCESS   read-only
    STATUS       current
    DESCRIPTION
        "Cisco Firepower firmware:DownloaderFsmTask:completion
        managed object property"
    ::= { cfprApFirmwareDownloaderFsmTaskEntry 4 }

cfprApFirmwareDownloaderFsmTaskFlags OBJECT-TYPE
    SYNTAX       CfprApFsmFlags
    MAX-ACCESS   read-only
    STATUS       current
    DESCRIPTION
        "Cisco Firepower firmware:DownloaderFsmTask:flags
        managed object property"
    ::= { cfprApFirmwareDownloaderFsmTaskEntry 5 }

cfprApFirmwareDownloaderFsmTaskItem OBJECT-TYPE
    SYNTAX       CfprApFirmwareDownloaderFsmTaskItem
    MAX-ACCESS   read-only
    STATUS       current
    DESCRIPTION
        "Cisco Firepower firmware:DownloaderFsmTask:item
        managed object property"
    ::= { cfprApFirmwareDownloaderFsmTaskEntry 6 }

cfprApFirmwareDownloaderFsmTaskSeqId OBJECT-TYPE
    SYNTAX       Gauge32
    MAX-ACCESS   read-only
    STATUS       current
    DESCRIPTION
        "Cisco Firepower firmware:DownloaderFsmTask:seqId
        managed object property"
    ::= { cfprApFirmwareDownloaderFsmTaskEntry 7 }

cfprApFirmwareHostTable OBJECT-TYPE
    SYNTAX           SEQUENCE OF CfprApFirmwareHostEntry
    MAX-ACCESS       not-accessible
    STATUS           current
    DESCRIPTION
        "Cisco Firepower firmware:Host managed object table"
    ::= { cfprApFirmwareObjects 31 }

cfprApFirmwareHostEntry OBJECT-TYPE
    SYNTAX           CfprApFirmwareHostEntry
    MAX-ACCESS       not-accessible
    STATUS           current
    DESCRIPTION
        "Entry for the cfprApFirmwareHostTable table."
    INDEX { cfprApFirmwareHostInstanceId }
    ::= { cfprApFirmwareHostTable 1 }

CfprApFirmwareHostEntry ::= SEQUENCE {
    cfprApFirmwareHostInstanceId                                     CfprApManagedObjectId,
    cfprApFirmwareHostDn                                             CfprApManagedObjectDn,
    cfprApFirmwareHostRn                                             SnmpAdminString
}

cfprApFirmwareHostInstanceId OBJECT-TYPE
    SYNTAX       CfprApManagedObjectId
    MAX-ACCESS   not-accessible
    STATUS       current
    DESCRIPTION
        "Instance identifier of the managed object."
    ::= { cfprApFirmwareHostEntry 1 }

cfprApFirmwareHostDn OBJECT-TYPE
    SYNTAX       CfprApManagedObjectDn
    MAX-ACCESS   read-only
    STATUS       current
    DESCRIPTION
        "Cisco Firepower firmware:Host:dn managed object property"
    ::= { cfprApFirmwareHostEntry 2 }

cfprApFirmwareHostRn OBJECT-TYPE
    SYNTAX       SnmpAdminString
    MAX-ACCESS   read-only
    STATUS       current
    DESCRIPTION
        "Cisco Firepower firmware:Host:rn managed object property"
    ::= { cfprApFirmwareHostEntry 3 }

cfprApFirmwareHostPackModImpactTable OBJECT-TYPE
    SYNTAX           SEQUENCE OF CfprApFirmwareHostPackModImpactEntry
    MAX-ACCESS       not-accessible
    STATUS           current
    DESCRIPTION
        "Cisco Firepower firmware:HostPackModImpact managed object table"
    ::= { cfprApFirmwareObjects 32 }

cfprApFirmwareHostPackModImpactEntry OBJECT-TYPE
    SYNTAX           CfprApFirmwareHostPackModImpactEntry
    MAX-ACCESS       not-accessible
    STATUS           current
    DESCRIPTION
        "Entry for the cfprApFirmwareHostPackModImpactTable table."
    INDEX { cfprApFirmwareHostPackModImpactInstanceId }
    ::= { cfprApFirmwareHostPackModImpactTable 1 }

CfprApFirmwareHostPackModImpactEntry ::= SEQUENCE {
    cfprApFirmwareHostPackModImpactInstanceId                        CfprApManagedObjectId,
    cfprApFirmwareHostPackModImpactDn                                CfprApManagedObjectDn,
    cfprApFirmwareHostPackModImpactRn                                SnmpAdminString,
    cfprApFirmwareHostPackModImpactKeyDn                             SnmpAdminString,
    cfprApFirmwareHostPackModImpactMaintPolicyDn                     SnmpAdminString,
    cfprApFirmwareHostPackModImpactPnDn                              SnmpAdminString,
    cfprApFirmwareHostPackModImpactRebootPolicy                      SnmpAdminString,
    cfprApFirmwareHostPackModImpactServiceProfileDn                  SnmpAdminString
}

cfprApFirmwareHostPackModImpactInstanceId OBJECT-TYPE
    SYNTAX       CfprApManagedObjectId
    MAX-ACCESS   not-accessible
    STATUS       current
    DESCRIPTION
        "Instance identifier of the managed object."
    ::= { cfprApFirmwareHostPackModImpactEntry 1 }

cfprApFirmwareHostPackModImpactDn OBJECT-TYPE
    SYNTAX       CfprApManagedObjectDn
    MAX-ACCESS   read-only
    STATUS       current
    DESCRIPTION
        "Cisco Firepower firmware:HostPackModImpact:dn
        managed object property"
    ::= { cfprApFirmwareHostPackModImpactEntry 2 }

cfprApFirmwareHostPackModImpactRn OBJECT-TYPE
    SYNTAX       SnmpAdminString
    MAX-ACCESS   read-only
    STATUS       current
    DESCRIPTION
        "Cisco Firepower firmware:HostPackModImpact:rn
        managed object property"
    ::= { cfprApFirmwareHostPackModImpactEntry 3 }

cfprApFirmwareHostPackModImpactKeyDn OBJECT-TYPE
    SYNTAX       SnmpAdminString
    MAX-ACCESS   read-only
    STATUS       current
    DESCRIPTION
        "Cisco Firepower firmware:HostPackModImpact:keyDn
        managed object property"
    ::= { cfprApFirmwareHostPackModImpactEntry 4 }

cfprApFirmwareHostPackModImpactMaintPolicyDn OBJECT-TYPE
    SYNTAX       SnmpAdminString
    MAX-ACCESS   read-only
    STATUS       current
    DESCRIPTION
        "Cisco Firepower firmware:HostPackModImpact:maintPolicyDn
        managed object property"
    ::= { cfprApFirmwareHostPackModImpactEntry 5 }

cfprApFirmwareHostPackModImpactPnDn OBJECT-TYPE
    SYNTAX       SnmpAdminString
    MAX-ACCESS   read-only
    STATUS       current
    DESCRIPTION
        "Cisco Firepower firmware:HostPackModImpact:pnDn
        managed object property"
    ::= { cfprApFirmwareHostPackModImpactEntry 6 }

cfprApFirmwareHostPackModImpactRebootPolicy OBJECT-TYPE
    SYNTAX       SnmpAdminString
    MAX-ACCESS   read-only
    STATUS       current
    DESCRIPTION
        "Cisco Firepower firmware:HostPackModImpact:rebootPolicy
        managed object property"
    ::= { cfprApFirmwareHostPackModImpactEntry 7 }

cfprApFirmwareHostPackModImpactServiceProfileDn OBJECT-TYPE
    SYNTAX       SnmpAdminString
    MAX-ACCESS   read-only
    STATUS       current
    DESCRIPTION
        "Cisco Firepower firmware:HostPackModImpact:serviceProfileDn
        managed object property"
    ::= { cfprApFirmwareHostPackModImpactEntry 8 }

cfprApFirmwareImageTable OBJECT-TYPE
    SYNTAX           SEQUENCE OF CfprApFirmwareImageEntry
    MAX-ACCESS       not-accessible
    STATUS           current
    DESCRIPTION
        "Cisco Firepower firmware:Image managed object table"
    ::= { cfprApFirmwareObjects 33 }

cfprApFirmwareImageEntry OBJECT-TYPE
    SYNTAX           CfprApFirmwareImageEntry
    MAX-ACCESS       not-accessible
    STATUS           current
    DESCRIPTION
        "Entry for the cfprApFirmwareImageTable table."
    INDEX { cfprApFirmwareImageInstanceId }
    ::= { cfprApFirmwareImageTable 1 }

CfprApFirmwareImageEntry ::= SEQUENCE {
    cfprApFirmwareImageInstanceId                                    CfprApManagedObjectId,
    cfprApFirmwareImageDn                                            CfprApManagedObjectDn,
    cfprApFirmwareImageRn                                            SnmpAdminString,
    cfprApFirmwareImageAdminState                                    CfprApFirmwareAdminState,
    cfprApFirmwareImageChecksum                                      SnmpAdminString,
    cfprApFirmwareImageDescr                                         SnmpAdminString,
    cfprApFirmwareImageDownloadDate                                  DateAndTime,
    cfprApFirmwareImageFsmDescr                                      SnmpAdminString,
    cfprApFirmwareImageFsmPrev                                       SnmpAdminString,
    cfprApFirmwareImageFsmProgr                                      Gauge32,
    cfprApFirmwareImageFsmRmtInvErrCode                              Gauge32,
    cfprApFirmwareImageFsmRmtInvErrDescr                             SnmpAdminString,
    cfprApFirmwareImageFsmRmtInvRslt                                 CfprApConditionRemoteInvRslt,
    cfprApFirmwareImageFsmStageDescr                                 SnmpAdminString,
    cfprApFirmwareImageFsmStamp                                      DateAndTime,
    cfprApFirmwareImageFsmStatus                                     SnmpAdminString,
    cfprApFirmwareImageFsmTry                                        Gauge32,
    cfprApFirmwareImageImagePresence                                 CfprApFirmwareImagePresence,
    cfprApFirmwareImageIntId                                         SnmpAdminString,
    cfprApFirmwareImageInvTag                                        SnmpAdminString,
    cfprApFirmwareImageIsoname                                       SnmpAdminString,
    cfprApFirmwareImageLocation                                      SnmpAdminString,
    cfprApFirmwareImageName                                          SnmpAdminString,
    cfprApFirmwareImagePolicyLevel                                   Gauge32,
    cfprApFirmwareImagePolicyOwner                                   CfprApPolicyPolicyOwner,
    cfprApFirmwareImageSize                                          Gauge32,
    cfprApFirmwareImageType                                          CfprApFirmwareType,
    cfprApFirmwareImageVersion                                       SnmpAdminString
}

cfprApFirmwareImageInstanceId OBJECT-TYPE
    SYNTAX       CfprApManagedObjectId
    MAX-ACCESS   not-accessible
    STATUS       current
    DESCRIPTION
        "Instance identifier of the managed object."
    ::= { cfprApFirmwareImageEntry 1 }

cfprApFirmwareImageDn OBJECT-TYPE
    SYNTAX       CfprApManagedObjectDn
    MAX-ACCESS   read-only
    STATUS       current
    DESCRIPTION
        "Cisco Firepower firmware:Image:dn managed object property"
    ::= { cfprApFirmwareImageEntry 2 }

cfprApFirmwareImageRn OBJECT-TYPE
    SYNTAX       SnmpAdminString
    MAX-ACCESS   read-only
    STATUS       current
    DESCRIPTION
        "Cisco Firepower firmware:Image:rn managed object property"
    ::= { cfprApFirmwareImageEntry 3 }

cfprApFirmwareImageAdminState OBJECT-TYPE
    SYNTAX       CfprApFirmwareAdminState
    MAX-ACCESS   read-only
    STATUS       current
    DESCRIPTION
        "Cisco Firepower firmware:Image:adminState managed
        object property"
    ::= { cfprApFirmwareImageEntry 4 }

cfprApFirmwareImageChecksum OBJECT-TYPE
    SYNTAX       SnmpAdminString
    MAX-ACCESS   read-only
    STATUS       current
    DESCRIPTION
        "Cisco Firepower firmware:Image:checksum managed object property"
    ::= { cfprApFirmwareImageEntry 5 }

cfprApFirmwareImageDescr OBJECT-TYPE
    SYNTAX       SnmpAdminString
    MAX-ACCESS   read-only
    STATUS       current
    DESCRIPTION
        "Cisco Firepower firmware:Image:descr managed object property"
    ::= { cfprApFirmwareImageEntry 6 }

cfprApFirmwareImageDownloadDate OBJECT-TYPE
    SYNTAX       DateAndTime
    MAX-ACCESS   read-only
    STATUS       current
    DESCRIPTION
        "Cisco Firepower firmware:Image:downloadDate managed
        object property"
    ::= { cfprApFirmwareImageEntry 7 }

cfprApFirmwareImageFsmDescr OBJECT-TYPE
    SYNTAX       SnmpAdminString
    MAX-ACCESS   read-only
    STATUS       current
    DESCRIPTION
        "Cisco Firepower firmware:Image:fsmDescr managed object property"
    ::= { cfprApFirmwareImageEntry 8 }

cfprApFirmwareImageFsmPrev OBJECT-TYPE
    SYNTAX       SnmpAdminString
    MAX-ACCESS   read-only
    STATUS       current
    DESCRIPTION
        "Cisco Firepower firmware:Image:fsmPrev managed object property"
    ::= { cfprApFirmwareImageEntry 9 }

cfprApFirmwareImageFsmProgr OBJECT-TYPE
    SYNTAX       Gauge32
    MAX-ACCESS   read-only
    STATUS       current
    DESCRIPTION
        "Cisco Firepower firmware:Image:fsmProgr managed object property"
    ::= { cfprApFirmwareImageEntry 10 }

cfprApFirmwareImageFsmRmtInvErrCode OBJECT-TYPE
    SYNTAX       Gauge32
    MAX-ACCESS   read-only
    STATUS       current
    DESCRIPTION
        "Cisco Firepower firmware:Image:fsmRmtInvErrCode
        managed object property"
    ::= { cfprApFirmwareImageEntry 11 }

cfprApFirmwareImageFsmRmtInvErrDescr OBJECT-TYPE
    SYNTAX       SnmpAdminString
    MAX-ACCESS   read-only
    STATUS       current
    DESCRIPTION
        "Cisco Firepower firmware:Image:fsmRmtInvErrDescr
        managed object property"
    ::= { cfprApFirmwareImageEntry 12 }

cfprApFirmwareImageFsmRmtInvRslt OBJECT-TYPE
    SYNTAX       CfprApConditionRemoteInvRslt
    MAX-ACCESS   read-only
    STATUS       current
    DESCRIPTION
        "Cisco Firepower firmware:Image:fsmRmtInvRslt managed
        object property"
    ::= { cfprApFirmwareImageEntry 13 }

cfprApFirmwareImageFsmStageDescr OBJECT-TYPE
    SYNTAX       SnmpAdminString
    MAX-ACCESS   read-only
    STATUS       current
    DESCRIPTION
        "Cisco Firepower firmware:Image:fsmStageDescr managed
        object property"
    ::= { cfprApFirmwareImageEntry 14 }

cfprApFirmwareImageFsmStamp OBJECT-TYPE
    SYNTAX       DateAndTime
    MAX-ACCESS   read-only
    STATUS       current
    DESCRIPTION
        "Cisco Firepower firmware:Image:fsmStamp managed object property"
    ::= { cfprApFirmwareImageEntry 15 }

cfprApFirmwareImageFsmStatus OBJECT-TYPE
    SYNTAX       SnmpAdminString
    MAX-ACCESS   read-only
    STATUS       current
    DESCRIPTION
        "Cisco Firepower firmware:Image:fsmStatus managed object property"
    ::= { cfprApFirmwareImageEntry 16 }

cfprApFirmwareImageFsmTry OBJECT-TYPE
    SYNTAX       Gauge32
    MAX-ACCESS   read-only
    STATUS       current
    DESCRIPTION
        "Cisco Firepower firmware:Image:fsmTry managed object property"
    ::= { cfprApFirmwareImageEntry 17 }

cfprApFirmwareImageImagePresence OBJECT-TYPE
    SYNTAX       CfprApFirmwareImagePresence
    MAX-ACCESS   read-only
    STATUS       current
    DESCRIPTION
        "Cisco Firepower firmware:Image:imagePresence managed
        object property"
    ::= { cfprApFirmwareImageEntry 18 }

cfprApFirmwareImageIntId OBJECT-TYPE
    SYNTAX       SnmpAdminString
    MAX-ACCESS   read-only
    STATUS       current
    DESCRIPTION
        "Cisco Firepower firmware:Image:intId managed object property"
    ::= { cfprApFirmwareImageEntry 19 }

cfprApFirmwareImageInvTag OBJECT-TYPE
    SYNTAX       SnmpAdminString
    MAX-ACCESS   read-only
    STATUS       current
    DESCRIPTION
        "Cisco Firepower firmware:Image:invTag managed object property"
    ::= { cfprApFirmwareImageEntry 20 }

cfprApFirmwareImageIsoname OBJECT-TYPE
    SYNTAX       SnmpAdminString
    MAX-ACCESS   read-only
    STATUS       current
    DESCRIPTION
        "Cisco Firepower firmware:Image:isoname managed object property"
    ::= { cfprApFirmwareImageEntry 21 }

cfprApFirmwareImageLocation OBJECT-TYPE
    SYNTAX       SnmpAdminString
    MAX-ACCESS   read-only
    STATUS       current
    DESCRIPTION
        "Cisco Firepower firmware:Image:location managed object property"
    ::= { cfprApFirmwareImageEntry 22 }

cfprApFirmwareImageName OBJECT-TYPE
    SYNTAX       SnmpAdminString
    MAX-ACCESS   read-only
    STATUS       current
    DESCRIPTION
        "Cisco Firepower firmware:Image:name managed object property"
    ::= { cfprApFirmwareImageEntry 23 }

cfprApFirmwareImagePolicyLevel OBJECT-TYPE
    SYNTAX       Gauge32
    MAX-ACCESS   read-only
    STATUS       current
    DESCRIPTION
        "Cisco Firepower firmware:Image:policyLevel managed
        object property"
    ::= { cfprApFirmwareImageEntry 24 }

cfprApFirmwareImagePolicyOwner OBJECT-TYPE
    SYNTAX       CfprApPolicyPolicyOwner
    MAX-ACCESS   read-only
    STATUS       current
    DESCRIPTION
        "Cisco Firepower firmware:Image:policyOwner managed
        object property"
    ::= { cfprApFirmwareImageEntry 25 }

cfprApFirmwareImageSize OBJECT-TYPE
    SYNTAX       Gauge32
    MAX-ACCESS   read-only
    STATUS       current
    DESCRIPTION
        "Cisco Firepower firmware:Image:size managed object property"
    ::= { cfprApFirmwareImageEntry 26 }

cfprApFirmwareImageType OBJECT-TYPE
    SYNTAX       CfprApFirmwareType
    MAX-ACCESS   read-only
    STATUS       current
    DESCRIPTION
        "Cisco Firepower firmware:Image:type managed object property"
    ::= { cfprApFirmwareImageEntry 27 }

cfprApFirmwareImageVersion OBJECT-TYPE
    SYNTAX       SnmpAdminString
    MAX-ACCESS   read-only
    STATUS       current
    DESCRIPTION
        "Cisco Firepower firmware:Image:version managed object property"
    ::= { cfprApFirmwareImageEntry 28 }

cfprApFirmwareImageFsmTable OBJECT-TYPE
    SYNTAX           SEQUENCE OF CfprApFirmwareImageFsmEntry
    MAX-ACCESS       not-accessible
    STATUS           current
    DESCRIPTION
        "Cisco Firepower firmware:ImageFsm managed object table"
    ::= { cfprApFirmwareObjects 34 }

cfprApFirmwareImageFsmEntry OBJECT-TYPE
    SYNTAX           CfprApFirmwareImageFsmEntry
    MAX-ACCESS       not-accessible
    STATUS           current
    DESCRIPTION
        "Entry for the cfprApFirmwareImageFsmTable table."
    INDEX { cfprApFirmwareImageFsmInstanceId }
    ::= { cfprApFirmwareImageFsmTable 1 }

CfprApFirmwareImageFsmEntry ::= SEQUENCE {
    cfprApFirmwareImageFsmInstanceId                                 CfprApManagedObjectId,
    cfprApFirmwareImageFsmDn                                         CfprApManagedObjectDn,
    cfprApFirmwareImageFsmRn                                         SnmpAdminString,
    cfprApFirmwareImageFsmCompletionTime                             DateAndTime,
    cfprApFirmwareImageFsmCurrentFsm                                 CfprApFirmwareImageFsmCurrentFsm,
    cfprApFirmwareImageFsmDescrData                                  SnmpAdminString,
    cfprApFirmwareImageFsmFsmStatus                                  CfprApFsmFsmStageStatus,
    cfprApFirmwareImageFsmProgress                                   Gauge32,
    cfprApFirmwareImageFsmRmtErrCode                                 Gauge32,
    cfprApFirmwareImageFsmRmtErrDescr                                SnmpAdminString,
    cfprApFirmwareImageFsmRmtRslt                                    CfprApConditionRemoteInvRslt
}

cfprApFirmwareImageFsmInstanceId OBJECT-TYPE
    SYNTAX       CfprApManagedObjectId
    MAX-ACCESS   not-accessible
    STATUS       current
    DESCRIPTION
        "Instance identifier of the managed object."
    ::= { cfprApFirmwareImageFsmEntry 1 }

cfprApFirmwareImageFsmDn OBJECT-TYPE
    SYNTAX       CfprApManagedObjectDn
    MAX-ACCESS   read-only
    STATUS       current
    DESCRIPTION
        "Cisco Firepower firmware:ImageFsm:dn managed object property"
    ::= { cfprApFirmwareImageFsmEntry 2 }

cfprApFirmwareImageFsmRn OBJECT-TYPE
    SYNTAX       SnmpAdminString
    MAX-ACCESS   read-only
    STATUS       current
    DESCRIPTION
        "Cisco Firepower firmware:ImageFsm:rn managed object property"
    ::= { cfprApFirmwareImageFsmEntry 3 }

cfprApFirmwareImageFsmCompletionTime OBJECT-TYPE
    SYNTAX       DateAndTime
    MAX-ACCESS   read-only
    STATUS       current
    DESCRIPTION
        "Cisco Firepower firmware:ImageFsm:completionTime
        managed object property"
    ::= { cfprApFirmwareImageFsmEntry 4 }

cfprApFirmwareImageFsmCurrentFsm OBJECT-TYPE
    SYNTAX       CfprApFirmwareImageFsmCurrentFsm
    MAX-ACCESS   read-only
    STATUS       current
    DESCRIPTION
        "Cisco Firepower firmware:ImageFsm:currentFsm managed
        object property"
    ::= { cfprApFirmwareImageFsmEntry 5 }

cfprApFirmwareImageFsmDescrData OBJECT-TYPE
    SYNTAX       SnmpAdminString
    MAX-ACCESS   read-only
    STATUS       current
    DESCRIPTION
        "Cisco Firepower firmware:ImageFsm:descr managed object property"
    ::= { cfprApFirmwareImageFsmEntry 6 }

cfprApFirmwareImageFsmFsmStatus OBJECT-TYPE
    SYNTAX       CfprApFsmFsmStageStatus
    MAX-ACCESS   read-only
    STATUS       current
    DESCRIPTION
        "Cisco Firepower firmware:ImageFsm:fsmStatus managed
        object property"
    ::= { cfprApFirmwareImageFsmEntry 7 }

cfprApFirmwareImageFsmProgress OBJECT-TYPE
    SYNTAX       Gauge32
    MAX-ACCESS   read-only
    STATUS       current
    DESCRIPTION
        "Cisco Firepower firmware:ImageFsm:progress managed
        object property"
    ::= { cfprApFirmwareImageFsmEntry 8 }

cfprApFirmwareImageFsmRmtErrCode OBJECT-TYPE
    SYNTAX       Gauge32
    MAX-ACCESS   read-only
    STATUS       current
    DESCRIPTION
        "Cisco Firepower firmware:ImageFsm:rmtErrCode managed
        object property"
    ::= { cfprApFirmwareImageFsmEntry 9 }

cfprApFirmwareImageFsmRmtErrDescr OBJECT-TYPE
    SYNTAX       SnmpAdminString
    MAX-ACCESS   read-only
    STATUS       current
    DESCRIPTION
        "Cisco Firepower firmware:ImageFsm:rmtErrDescr
        managed object property"
    ::= { cfprApFirmwareImageFsmEntry 10 }

cfprApFirmwareImageFsmRmtRslt OBJECT-TYPE
    SYNTAX       CfprApConditionRemoteInvRslt
    MAX-ACCESS   read-only
    STATUS       current
    DESCRIPTION
        "Cisco Firepower firmware:ImageFsm:rmtRslt managed
        object property"
    ::= { cfprApFirmwareImageFsmEntry 11 }

cfprApFirmwareImageFsmStageTable OBJECT-TYPE
    SYNTAX           SEQUENCE OF CfprApFirmwareImageFsmStageEntry
    MAX-ACCESS       not-accessible
    STATUS           current
    DESCRIPTION
        "Cisco Firepower firmware:ImageFsmStage managed object table"
    ::= { cfprApFirmwareObjects 35 }

cfprApFirmwareImageFsmStageEntry OBJECT-TYPE
    SYNTAX           CfprApFirmwareImageFsmStageEntry
    MAX-ACCESS       not-accessible
    STATUS           current
    DESCRIPTION
        "Entry for the cfprApFirmwareImageFsmStageTable table."
    INDEX { cfprApFirmwareImageFsmStageInstanceId }
    ::= { cfprApFirmwareImageFsmStageTable 1 }

CfprApFirmwareImageFsmStageEntry ::= SEQUENCE {
    cfprApFirmwareImageFsmStageInstanceId                            CfprApManagedObjectId,
    cfprApFirmwareImageFsmStageDn                                    CfprApManagedObjectDn,
    cfprApFirmwareImageFsmStageRn                                    SnmpAdminString,
    cfprApFirmwareImageFsmStageDescrData                             SnmpAdminString,
    cfprApFirmwareImageFsmStageLastUpdateTime                        DateAndTime,
    cfprApFirmwareImageFsmStageName                                  CfprApFirmwareImageFsmStageName,
    cfprApFirmwareImageFsmStageOrder                                 Gauge32,
    cfprApFirmwareImageFsmStageRetry                                 Gauge32,
    cfprApFirmwareImageFsmStageStageStatus                           CfprApFsmFsmStageStatus
}

cfprApFirmwareImageFsmStageInstanceId OBJECT-TYPE
    SYNTAX       CfprApManagedObjectId
    MAX-ACCESS   not-accessible
    STATUS       current
    DESCRIPTION
        "Instance identifier of the managed object."
    ::= { cfprApFirmwareImageFsmStageEntry 1 }

cfprApFirmwareImageFsmStageDn OBJECT-TYPE
    SYNTAX       CfprApManagedObjectDn
    MAX-ACCESS   read-only
    STATUS       current
    DESCRIPTION
        "Cisco Firepower firmware:ImageFsmStage:dn managed
        object property"
    ::= { cfprApFirmwareImageFsmStageEntry 2 }

cfprApFirmwareImageFsmStageRn OBJECT-TYPE
    SYNTAX       SnmpAdminString
    MAX-ACCESS   read-only
    STATUS       current
    DESCRIPTION
        "Cisco Firepower firmware:ImageFsmStage:rn managed
        object property"
    ::= { cfprApFirmwareImageFsmStageEntry 3 }

cfprApFirmwareImageFsmStageDescrData OBJECT-TYPE
    SYNTAX       SnmpAdminString
    MAX-ACCESS   read-only
    STATUS       current
    DESCRIPTION
        "Cisco Firepower firmware:ImageFsmStage:descr managed
        object property"
    ::= { cfprApFirmwareImageFsmStageEntry 4 }

cfprApFirmwareImageFsmStageLastUpdateTime OBJECT-TYPE
    SYNTAX       DateAndTime
    MAX-ACCESS   read-only
    STATUS       current
    DESCRIPTION
        "Cisco Firepower firmware:ImageFsmStage:lastUpdateTime
        managed object property"
    ::= { cfprApFirmwareImageFsmStageEntry 5 }

cfprApFirmwareImageFsmStageName OBJECT-TYPE
    SYNTAX       CfprApFirmwareImageFsmStageName
    MAX-ACCESS   read-only
    STATUS       current
    DESCRIPTION
        "Cisco Firepower firmware:ImageFsmStage:name managed
        object property"
    ::= { cfprApFirmwareImageFsmStageEntry 6 }

cfprApFirmwareImageFsmStageOrder OBJECT-TYPE
    SYNTAX       Gauge32
    MAX-ACCESS   read-only
    STATUS       current
    DESCRIPTION
        "Cisco Firepower firmware:ImageFsmStage:order managed
        object property"
    ::= { cfprApFirmwareImageFsmStageEntry 7 }

cfprApFirmwareImageFsmStageRetry OBJECT-TYPE
    SYNTAX       Gauge32
    MAX-ACCESS   read-only
    STATUS       current
    DESCRIPTION
        "Cisco Firepower firmware:ImageFsmStage:retry managed
        object property"
    ::= { cfprApFirmwareImageFsmStageEntry 8 }

cfprApFirmwareImageFsmStageStageStatus OBJECT-TYPE
    SYNTAX       CfprApFsmFsmStageStatus
    MAX-ACCESS   read-only
    STATUS       current
    DESCRIPTION
        "Cisco Firepower firmware:ImageFsmStage:stageStatus
        managed object property"
    ::= { cfprApFirmwareImageFsmStageEntry 9 }

cfprApFirmwareImageFsmTaskTable OBJECT-TYPE
    SYNTAX           SEQUENCE OF CfprApFirmwareImageFsmTaskEntry
    MAX-ACCESS       not-accessible
    STATUS           current
    DESCRIPTION
        "Cisco Firepower firmware:ImageFsmTask managed object table"
    ::= { cfprApFirmwareObjects 36 }

cfprApFirmwareImageFsmTaskEntry OBJECT-TYPE
    SYNTAX           CfprApFirmwareImageFsmTaskEntry
    MAX-ACCESS       not-accessible
    STATUS           current
    DESCRIPTION
        "Entry for the cfprApFirmwareImageFsmTaskTable table."
    INDEX { cfprApFirmwareImageFsmTaskInstanceId }
    ::= { cfprApFirmwareImageFsmTaskTable 1 }

CfprApFirmwareImageFsmTaskEntry ::= SEQUENCE {
    cfprApFirmwareImageFsmTaskInstanceId                             CfprApManagedObjectId,
    cfprApFirmwareImageFsmTaskDn                                     CfprApManagedObjectDn,
    cfprApFirmwareImageFsmTaskRn                                     SnmpAdminString,
    cfprApFirmwareImageFsmTaskCompletion                             CfprApFsmCompletion,
    cfprApFirmwareImageFsmTaskFlags                                  CfprApFsmFlags,
    cfprApFirmwareImageFsmTaskItem                                   CfprApFirmwareImageFsmTaskItem,
    cfprApFirmwareImageFsmTaskSeqId                                  Gauge32
}

cfprApFirmwareImageFsmTaskInstanceId OBJECT-TYPE
    SYNTAX       CfprApManagedObjectId
    MAX-ACCESS   not-accessible
    STATUS       current
    DESCRIPTION
        "Instance identifier of the managed object."
    ::= { cfprApFirmwareImageFsmTaskEntry 1 }

cfprApFirmwareImageFsmTaskDn OBJECT-TYPE
    SYNTAX       CfprApManagedObjectDn
    MAX-ACCESS   read-only
    STATUS       current
    DESCRIPTION
        "Cisco Firepower firmware:ImageFsmTask:dn managed object property"
    ::= { cfprApFirmwareImageFsmTaskEntry 2 }

cfprApFirmwareImageFsmTaskRn OBJECT-TYPE
    SYNTAX       SnmpAdminString
    MAX-ACCESS   read-only
    STATUS       current
    DESCRIPTION
        "Cisco Firepower firmware:ImageFsmTask:rn managed object property"
    ::= { cfprApFirmwareImageFsmTaskEntry 3 }

cfprApFirmwareImageFsmTaskCompletion OBJECT-TYPE
    SYNTAX       CfprApFsmCompletion
    MAX-ACCESS   read-only
    STATUS       current
    DESCRIPTION
        "Cisco Firepower firmware:ImageFsmTask:completion
        managed object property"
    ::= { cfprApFirmwareImageFsmTaskEntry 4 }

cfprApFirmwareImageFsmTaskFlags OBJECT-TYPE
    SYNTAX       CfprApFsmFlags
    MAX-ACCESS   read-only
    STATUS       current
    DESCRIPTION
        "Cisco Firepower firmware:ImageFsmTask:flags managed
        object property"
    ::= { cfprApFirmwareImageFsmTaskEntry 5 }

cfprApFirmwareImageFsmTaskItem OBJECT-TYPE
    SYNTAX       CfprApFirmwareImageFsmTaskItem
    MAX-ACCESS   read-only
    STATUS       current
    DESCRIPTION
        "Cisco Firepower firmware:ImageFsmTask:item managed
        object property"
    ::= { cfprApFirmwareImageFsmTaskEntry 6 }

cfprApFirmwareImageFsmTaskSeqId OBJECT-TYPE
    SYNTAX       Gauge32
    MAX-ACCESS   read-only
    STATUS       current
    DESCRIPTION
        "Cisco Firepower firmware:ImageFsmTask:seqId managed
        object property"
    ::= { cfprApFirmwareImageFsmTaskEntry 7 }

cfprApFirmwareImageLockTable OBJECT-TYPE
    SYNTAX           SEQUENCE OF CfprApFirmwareImageLockEntry
    MAX-ACCESS       not-accessible
    STATUS           current
    DESCRIPTION
        "Cisco Firepower firmware:ImageLock managed object table"
    ::= { cfprApFirmwareObjects 37 }

cfprApFirmwareImageLockEntry OBJECT-TYPE
    SYNTAX           CfprApFirmwareImageLockEntry
    MAX-ACCESS       not-accessible
    STATUS           current
    DESCRIPTION
        "Entry for the cfprApFirmwareImageLockTable table."
    INDEX { cfprApFirmwareImageLockInstanceId }
    ::= { cfprApFirmwareImageLockTable 1 }

CfprApFirmwareImageLockEntry ::= SEQUENCE {
    cfprApFirmwareImageLockInstanceId                                CfprApManagedObjectId,
    cfprApFirmwareImageLockDn                                        CfprApManagedObjectDn,
    cfprApFirmwareImageLockRn                                        SnmpAdminString,
    cfprApFirmwareImageLockImageNameDn                               SnmpAdminString,
    cfprApFirmwareImageLockName                                      SnmpAdminString
}

cfprApFirmwareImageLockInstanceId OBJECT-TYPE
    SYNTAX       CfprApManagedObjectId
    MAX-ACCESS   not-accessible
    STATUS       current
    DESCRIPTION
        "Instance identifier of the managed object."
    ::= { cfprApFirmwareImageLockEntry 1 }

cfprApFirmwareImageLockDn OBJECT-TYPE
    SYNTAX       CfprApManagedObjectDn
    MAX-ACCESS   read-only
    STATUS       current
    DESCRIPTION
        "Cisco Firepower firmware:ImageLock:dn managed object property"
    ::= { cfprApFirmwareImageLockEntry 2 }

cfprApFirmwareImageLockRn OBJECT-TYPE
    SYNTAX       SnmpAdminString
    MAX-ACCESS   read-only
    STATUS       current
    DESCRIPTION
        "Cisco Firepower firmware:ImageLock:rn managed object property"
    ::= { cfprApFirmwareImageLockEntry 3 }

cfprApFirmwareImageLockImageNameDn OBJECT-TYPE
    SYNTAX       SnmpAdminString
    MAX-ACCESS   read-only
    STATUS       current
    DESCRIPTION
        "Cisco Firepower firmware:ImageLock:ImageNameDn
        managed object property"
    ::= { cfprApFirmwareImageLockEntry 4 }

cfprApFirmwareImageLockName OBJECT-TYPE
    SYNTAX       SnmpAdminString
    MAX-ACCESS   read-only
    STATUS       current
    DESCRIPTION
        "Cisco Firepower firmware:ImageLock:name managed object property"
    ::= { cfprApFirmwareImageLockEntry 5 }

cfprApFirmwareInfraTable OBJECT-TYPE
    SYNTAX           SEQUENCE OF CfprApFirmwareInfraEntry
    MAX-ACCESS       not-accessible
    STATUS           current
    DESCRIPTION
        "Cisco Firepower firmware:Infra managed object table"
    ::= { cfprApFirmwareObjects 38 }

cfprApFirmwareInfraEntry OBJECT-TYPE
    SYNTAX           CfprApFirmwareInfraEntry
    MAX-ACCESS       not-accessible
    STATUS           current
    DESCRIPTION
        "Entry for the cfprApFirmwareInfraTable table."
    INDEX { cfprApFirmwareInfraInstanceId }
    ::= { cfprApFirmwareInfraTable 1 }

CfprApFirmwareInfraEntry ::= SEQUENCE {
    cfprApFirmwareInfraInstanceId                                    CfprApManagedObjectId,
    cfprApFirmwareInfraDn                                            CfprApManagedObjectDn,
    cfprApFirmwareInfraRn                                            SnmpAdminString,
    cfprApFirmwareInfraAdminState                                    CfprApTrigAdminState,
    cfprApFirmwareInfraAutoDelete                                    TruthValue,
    cfprApFirmwareInfraDescr                                         SnmpAdminString,
    cfprApFirmwareInfraIgnoreCap                                     TruthValue,
    cfprApFirmwareInfraIntId                                         SnmpAdminString,
    cfprApFirmwareInfraName                                          SnmpAdminString,
    cfprApFirmwareInfraOperScheduler                                 SnmpAdminString,
    cfprApFirmwareInfraOperState                                     CfprApTrigTrigOperState,
    cfprApFirmwareInfraOperVersion                                   SnmpAdminString,
    cfprApFirmwareInfraPolicyLevel                                   Gauge32,
    cfprApFirmwareInfraPolicyOwner                                   CfprApPolicyPolicyOwner,
    cfprApFirmwareInfraScheduler                                     SnmpAdminString
}

cfprApFirmwareInfraInstanceId OBJECT-TYPE
    SYNTAX       CfprApManagedObjectId
    MAX-ACCESS   not-accessible
    STATUS       current
    DESCRIPTION
        "Instance identifier of the managed object."
    ::= { cfprApFirmwareInfraEntry 1 }

cfprApFirmwareInfraDn OBJECT-TYPE
    SYNTAX       CfprApManagedObjectDn
    MAX-ACCESS   read-only
    STATUS       current
    DESCRIPTION
        "Cisco Firepower firmware:Infra:dn managed object property"
    ::= { cfprApFirmwareInfraEntry 2 }

cfprApFirmwareInfraRn OBJECT-TYPE
    SYNTAX       SnmpAdminString
    MAX-ACCESS   read-only
    STATUS       current
    DESCRIPTION
        "Cisco Firepower firmware:Infra:rn managed object property"
    ::= { cfprApFirmwareInfraEntry 3 }

cfprApFirmwareInfraAdminState OBJECT-TYPE
    SYNTAX       CfprApTrigAdminState
    MAX-ACCESS   read-only
    STATUS       current
    DESCRIPTION
        "Cisco Firepower firmware:Infra:adminState managed
        object property"
    ::= { cfprApFirmwareInfraEntry 4 }

cfprApFirmwareInfraAutoDelete OBJECT-TYPE
    SYNTAX       TruthValue
    MAX-ACCESS   read-only
    STATUS       current
    DESCRIPTION
        "Cisco Firepower firmware:Infra:autoDelete managed
        object property"
    ::= { cfprApFirmwareInfraEntry 5 }

cfprApFirmwareInfraDescr OBJECT-TYPE
    SYNTAX       SnmpAdminString
    MAX-ACCESS   read-only
    STATUS       current
    DESCRIPTION
        "Cisco Firepower firmware:Infra:descr managed object property"
    ::= { cfprApFirmwareInfraEntry 6 }

cfprApFirmwareInfraIgnoreCap OBJECT-TYPE
    SYNTAX       TruthValue
    MAX-ACCESS   read-only
    STATUS       current
    DESCRIPTION
        "Cisco Firepower firmware:Infra:ignoreCap managed object property"
    ::= { cfprApFirmwareInfraEntry 7 }

cfprApFirmwareInfraIntId OBJECT-TYPE
    SYNTAX       SnmpAdminString
    MAX-ACCESS   read-only
    STATUS       current
    DESCRIPTION
        "Cisco Firepower firmware:Infra:intId managed object property"
    ::= { cfprApFirmwareInfraEntry 8 }

cfprApFirmwareInfraName OBJECT-TYPE
    SYNTAX       SnmpAdminString
    MAX-ACCESS   read-only
    STATUS       current
    DESCRIPTION
        "Cisco Firepower firmware:Infra:name managed object property"
    ::= { cfprApFirmwareInfraEntry 9 }

cfprApFirmwareInfraOperScheduler OBJECT-TYPE
    SYNTAX       SnmpAdminString
    MAX-ACCESS   read-only
    STATUS       current
    DESCRIPTION
        "Cisco Firepower firmware:Infra:operScheduler managed
        object property"
    ::= { cfprApFirmwareInfraEntry 10 }

cfprApFirmwareInfraOperState OBJECT-TYPE
    SYNTAX       CfprApTrigTrigOperState
    MAX-ACCESS   read-only
    STATUS       current
    DESCRIPTION
        "Cisco Firepower firmware:Infra:operState managed object property"
    ::= { cfprApFirmwareInfraEntry 11 }

cfprApFirmwareInfraOperVersion OBJECT-TYPE
    SYNTAX       SnmpAdminString
    MAX-ACCESS   read-only
    STATUS       current
    DESCRIPTION
        "Cisco Firepower firmware:Infra:operVersion managed
        object property"
    ::= { cfprApFirmwareInfraEntry 12 }

cfprApFirmwareInfraPolicyLevel OBJECT-TYPE
    SYNTAX       Gauge32
    MAX-ACCESS   read-only
    STATUS       current
    DESCRIPTION
        "Cisco Firepower firmware:Infra:policyLevel managed
        object property"
    ::= { cfprApFirmwareInfraEntry 13 }

cfprApFirmwareInfraPolicyOwner OBJECT-TYPE
    SYNTAX       CfprApPolicyPolicyOwner
    MAX-ACCESS   read-only
    STATUS       current
    DESCRIPTION
        "Cisco Firepower firmware:Infra:policyOwner managed
        object property"
    ::= { cfprApFirmwareInfraEntry 14 }

cfprApFirmwareInfraScheduler OBJECT-TYPE
    SYNTAX       SnmpAdminString
    MAX-ACCESS   read-only
    STATUS       current
    DESCRIPTION
        "Cisco Firepower firmware:Infra:scheduler managed object property"
    ::= { cfprApFirmwareInfraEntry 15 }

cfprApFirmwareInfraPackTable OBJECT-TYPE
    SYNTAX           SEQUENCE OF CfprApFirmwareInfraPackEntry
    MAX-ACCESS       not-accessible
    STATUS           current
    DESCRIPTION
        "Cisco Firepower firmware:InfraPack managed object table"
    ::= { cfprApFirmwareObjects 39 }

cfprApFirmwareInfraPackEntry OBJECT-TYPE
    SYNTAX           CfprApFirmwareInfraPackEntry
    MAX-ACCESS       not-accessible
    STATUS           current
    DESCRIPTION
        "Entry for the cfprApFirmwareInfraPackTable table."
    INDEX { cfprApFirmwareInfraPackInstanceId }
    ::= { cfprApFirmwareInfraPackTable 1 }

CfprApFirmwareInfraPackEntry ::= SEQUENCE {
    cfprApFirmwareInfraPackInstanceId                                CfprApManagedObjectId,
    cfprApFirmwareInfraPackDn                                        CfprApManagedObjectDn,
    cfprApFirmwareInfraPackRn                                        SnmpAdminString,
    cfprApFirmwareInfraPackDescr                                     SnmpAdminString,
    cfprApFirmwareInfraPackForceDeploy                               TruthValue,
    cfprApFirmwareInfraPackFsmDescr                                  SnmpAdminString,
    cfprApFirmwareInfraPackFsmFlags                                  SnmpAdminString,
    cfprApFirmwareInfraPackFsmPrev                                   SnmpAdminString,
    cfprApFirmwareInfraPackFsmProgr                                  Gauge32,
    cfprApFirmwareInfraPackFsmRmtInvErrCode                          Gauge32,
    cfprApFirmwareInfraPackFsmRmtInvErrDescr                         SnmpAdminString,
    cfprApFirmwareInfraPackFsmRmtInvRslt                             CfprApConditionRemoteInvRslt,
    cfprApFirmwareInfraPackFsmStageDescr                             SnmpAdminString,
    cfprApFirmwareInfraPackFsmStamp                                  DateAndTime,
    cfprApFirmwareInfraPackFsmStatus                                 SnmpAdminString,
    cfprApFirmwareInfraPackFsmTry                                    Gauge32,
    cfprApFirmwareInfraPackInfraBundleName                           SnmpAdminString,
    cfprApFirmwareInfraPackInfraBundleVersion                        SnmpAdminString,
    cfprApFirmwareInfraPackIntId                                     SnmpAdminString,
    cfprApFirmwareInfraPackMode                                      CfprApFirmwarePackMode,
    cfprApFirmwareInfraPackName                                      SnmpAdminString,
    cfprApFirmwareInfraPackPolicyLevel                               Gauge32,
    cfprApFirmwareInfraPackPolicyOwner                               CfprApPolicyPolicyOwner,
    cfprApFirmwareInfraPackPreviousBundleVersion                     SnmpAdminString,
    cfprApFirmwareInfraPackStageSize                                 Gauge32,
    cfprApFirmwareInfraPackUpdateTrigger                             DateAndTime
}

cfprApFirmwareInfraPackInstanceId OBJECT-TYPE
    SYNTAX       CfprApManagedObjectId
    MAX-ACCESS   not-accessible
    STATUS       current
    DESCRIPTION
        "Instance identifier of the managed object."
    ::= { cfprApFirmwareInfraPackEntry 1 }

cfprApFirmwareInfraPackDn OBJECT-TYPE
    SYNTAX       CfprApManagedObjectDn
    MAX-ACCESS   read-only
    STATUS       current
    DESCRIPTION
        "Cisco Firepower firmware:InfraPack:dn managed object property"
    ::= { cfprApFirmwareInfraPackEntry 2 }

cfprApFirmwareInfraPackRn OBJECT-TYPE
    SYNTAX       SnmpAdminString
    MAX-ACCESS   read-only
    STATUS       current
    DESCRIPTION
        "Cisco Firepower firmware:InfraPack:rn managed object property"
    ::= { cfprApFirmwareInfraPackEntry 3 }

cfprApFirmwareInfraPackDescr OBJECT-TYPE
    SYNTAX       SnmpAdminString
    MAX-ACCESS   read-only
    STATUS       current
    DESCRIPTION
        "Cisco Firepower firmware:InfraPack:descr managed object property"
    ::= { cfprApFirmwareInfraPackEntry 4 }

cfprApFirmwareInfraPackForceDeploy OBJECT-TYPE
    SYNTAX       TruthValue
    MAX-ACCESS   read-only
    STATUS       current
    DESCRIPTION
        "Cisco Firepower firmware:InfraPack:forceDeploy
        managed object property"
    ::= { cfprApFirmwareInfraPackEntry 5 }

cfprApFirmwareInfraPackFsmDescr OBJECT-TYPE
    SYNTAX       SnmpAdminString
    MAX-ACCESS   read-only
    STATUS       current
    DESCRIPTION
        "Cisco Firepower firmware:InfraPack:fsmDescr managed
        object property"
    ::= { cfprApFirmwareInfraPackEntry 6 }

cfprApFirmwareInfraPackFsmFlags OBJECT-TYPE
    SYNTAX       SnmpAdminString
    MAX-ACCESS   read-only
    STATUS       current
    DESCRIPTION
        "Cisco Firepower firmware:InfraPack:fsmFlags managed
        object property"
    ::= { cfprApFirmwareInfraPackEntry 7 }

cfprApFirmwareInfraPackFsmPrev OBJECT-TYPE
    SYNTAX       SnmpAdminString
    MAX-ACCESS   read-only
    STATUS       current
    DESCRIPTION
        "Cisco Firepower firmware:InfraPack:fsmPrev managed
        object property"
    ::= { cfprApFirmwareInfraPackEntry 8 }

cfprApFirmwareInfraPackFsmProgr OBJECT-TYPE
    SYNTAX       Gauge32
    MAX-ACCESS   read-only
    STATUS       current
    DESCRIPTION
        "Cisco Firepower firmware:InfraPack:fsmProgr managed
        object property"
    ::= { cfprApFirmwareInfraPackEntry 9 }

cfprApFirmwareInfraPackFsmRmtInvErrCode OBJECT-TYPE
    SYNTAX       Gauge32
    MAX-ACCESS   read-only
    STATUS       current
    DESCRIPTION
        "Cisco Firepower firmware:InfraPack:fsmRmtInvErrCode
        managed object property"
    ::= { cfprApFirmwareInfraPackEntry 10 }

cfprApFirmwareInfraPackFsmRmtInvErrDescr OBJECT-TYPE
    SYNTAX       SnmpAdminString
    MAX-ACCESS   read-only
    STATUS       current
    DESCRIPTION
        "Cisco Firepower firmware:InfraPack:fsmRmtInvErrDescr
        managed object property"
    ::= { cfprApFirmwareInfraPackEntry 11 }

cfprApFirmwareInfraPackFsmRmtInvRslt OBJECT-TYPE
    SYNTAX       CfprApConditionRemoteInvRslt
    MAX-ACCESS   read-only
    STATUS       current
    DESCRIPTION
        "Cisco Firepower firmware:InfraPack:fsmRmtInvRslt
        managed object property"
    ::= { cfprApFirmwareInfraPackEntry 12 }

cfprApFirmwareInfraPackFsmStageDescr OBJECT-TYPE
    SYNTAX       SnmpAdminString
    MAX-ACCESS   read-only
    STATUS       current
    DESCRIPTION
        "Cisco Firepower firmware:InfraPack:fsmStageDescr
        managed object property"
    ::= { cfprApFirmwareInfraPackEntry 13 }

cfprApFirmwareInfraPackFsmStamp OBJECT-TYPE
    SYNTAX       DateAndTime
    MAX-ACCESS   read-only
    STATUS       current
    DESCRIPTION
        "Cisco Firepower firmware:InfraPack:fsmStamp managed
        object property"
    ::= { cfprApFirmwareInfraPackEntry 14 }

cfprApFirmwareInfraPackFsmStatus OBJECT-TYPE
    SYNTAX       SnmpAdminString
    MAX-ACCESS   read-only
    STATUS       current
    DESCRIPTION
        "Cisco Firepower firmware:InfraPack:fsmStatus managed
        object property"
    ::= { cfprApFirmwareInfraPackEntry 15 }

cfprApFirmwareInfraPackFsmTry OBJECT-TYPE
    SYNTAX       Gauge32
    MAX-ACCESS   read-only
    STATUS       current
    DESCRIPTION
        "Cisco Firepower firmware:InfraPack:fsmTry managed
        object property"
    ::= { cfprApFirmwareInfraPackEntry 16 }

cfprApFirmwareInfraPackInfraBundleName OBJECT-TYPE
    SYNTAX       SnmpAdminString
    MAX-ACCESS   read-only
    STATUS       current
    DESCRIPTION
        "Cisco Firepower firmware:InfraPack:infraBundleName
        managed object property"
    ::= { cfprApFirmwareInfraPackEntry 17 }

cfprApFirmwareInfraPackInfraBundleVersion OBJECT-TYPE
    SYNTAX       SnmpAdminString
    MAX-ACCESS   read-only
    STATUS       current
    DESCRIPTION
        "Cisco Firepower firmware:InfraPack:infraBundleVersion
        managed object property"
    ::= { cfprApFirmwareInfraPackEntry 18 }

cfprApFirmwareInfraPackIntId OBJECT-TYPE
    SYNTAX       SnmpAdminString
    MAX-ACCESS   read-only
    STATUS       current
    DESCRIPTION
        "Cisco Firepower firmware:InfraPack:intId managed object property"
    ::= { cfprApFirmwareInfraPackEntry 19 }

cfprApFirmwareInfraPackMode OBJECT-TYPE
    SYNTAX       CfprApFirmwarePackMode
    MAX-ACCESS   read-only
    STATUS       current
    DESCRIPTION
        "Cisco Firepower firmware:InfraPack:mode managed object property"
    ::= { cfprApFirmwareInfraPackEntry 20 }

cfprApFirmwareInfraPackName OBJECT-TYPE
    SYNTAX       SnmpAdminString
    MAX-ACCESS   read-only
    STATUS       current
    DESCRIPTION
        "Cisco Firepower firmware:InfraPack:name managed object property"
    ::= { cfprApFirmwareInfraPackEntry 21 }

cfprApFirmwareInfraPackPolicyLevel OBJECT-TYPE
    SYNTAX       Gauge32
    MAX-ACCESS   read-only
    STATUS       current
    DESCRIPTION
        "Cisco Firepower firmware:InfraPack:policyLevel
        managed object property"
    ::= { cfprApFirmwareInfraPackEntry 22 }

cfprApFirmwareInfraPackPolicyOwner OBJECT-TYPE
    SYNTAX       CfprApPolicyPolicyOwner
    MAX-ACCESS   read-only
    STATUS       current
    DESCRIPTION
        "Cisco Firepower firmware:InfraPack:policyOwner
        managed object property"
    ::= { cfprApFirmwareInfraPackEntry 23 }

cfprApFirmwareInfraPackPreviousBundleVersion OBJECT-TYPE
    SYNTAX       SnmpAdminString
    MAX-ACCESS   read-only
    STATUS       current
    DESCRIPTION
        "Cisco Firepower firmware:InfraPack:previousBundleVersion
        managed object property"
    ::= { cfprApFirmwareInfraPackEntry 24 }

cfprApFirmwareInfraPackStageSize OBJECT-TYPE
    SYNTAX       Gauge32
    MAX-ACCESS   read-only
    STATUS       current
    DESCRIPTION
        "Cisco Firepower firmware:InfraPack:stageSize managed
        object property"
    ::= { cfprApFirmwareInfraPackEntry 25 }

cfprApFirmwareInfraPackUpdateTrigger OBJECT-TYPE
    SYNTAX       DateAndTime
    MAX-ACCESS   read-only
    STATUS       current
    DESCRIPTION
        "Cisco Firepower firmware:InfraPack:updateTrigger
        managed object property"
    ::= { cfprApFirmwareInfraPackEntry 26 }

cfprApFirmwareInfraPackFsmTable OBJECT-TYPE
    SYNTAX           SEQUENCE OF CfprApFirmwareInfraPackFsmEntry
    MAX-ACCESS       not-accessible
    STATUS           current
    DESCRIPTION
        "Cisco Firepower firmware:InfraPackFsm managed object table"
    ::= { cfprApFirmwareObjects 40 }

cfprApFirmwareInfraPackFsmEntry OBJECT-TYPE
    SYNTAX           CfprApFirmwareInfraPackFsmEntry
    MAX-ACCESS       not-accessible
    STATUS           current
    DESCRIPTION
        "Entry for the cfprApFirmwareInfraPackFsmTable table."
    INDEX { cfprApFirmwareInfraPackFsmInstanceId }
    ::= { cfprApFirmwareInfraPackFsmTable 1 }

CfprApFirmwareInfraPackFsmEntry ::= SEQUENCE {
    cfprApFirmwareInfraPackFsmInstanceId                             CfprApManagedObjectId,
    cfprApFirmwareInfraPackFsmDn                                     CfprApManagedObjectDn,
    cfprApFirmwareInfraPackFsmRn                                     SnmpAdminString,
    cfprApFirmwareInfraPackFsmCompletionTime                         DateAndTime,
    cfprApFirmwareInfraPackFsmCurrentFsm                             CfprApFirmwareInfraPackFsmCurrentFsm,
    cfprApFirmwareInfraPackFsmDescrData                              SnmpAdminString,
    cfprApFirmwareInfraPackFsmFsmStatus                              CfprApFsmFsmStageStatus,
    cfprApFirmwareInfraPackFsmProgress                               Gauge32,
    cfprApFirmwareInfraPackFsmRmtErrCode                             Gauge32,
    cfprApFirmwareInfraPackFsmRmtErrDescr                            SnmpAdminString,
    cfprApFirmwareInfraPackFsmRmtRslt                                CfprApConditionRemoteInvRslt
}

cfprApFirmwareInfraPackFsmInstanceId OBJECT-TYPE
    SYNTAX       CfprApManagedObjectId
    MAX-ACCESS   not-accessible
    STATUS       current
    DESCRIPTION
        "Instance identifier of the managed object."
    ::= { cfprApFirmwareInfraPackFsmEntry 1 }

cfprApFirmwareInfraPackFsmDn OBJECT-TYPE
    SYNTAX       CfprApManagedObjectDn
    MAX-ACCESS   read-only
    STATUS       current
    DESCRIPTION
        "Cisco Firepower firmware:InfraPackFsm:dn managed object property"
    ::= { cfprApFirmwareInfraPackFsmEntry 2 }

cfprApFirmwareInfraPackFsmRn OBJECT-TYPE
    SYNTAX       SnmpAdminString
    MAX-ACCESS   read-only
    STATUS       current
    DESCRIPTION
        "Cisco Firepower firmware:InfraPackFsm:rn managed object property"
    ::= { cfprApFirmwareInfraPackFsmEntry 3 }

cfprApFirmwareInfraPackFsmCompletionTime OBJECT-TYPE
    SYNTAX       DateAndTime
    MAX-ACCESS   read-only
    STATUS       current
    DESCRIPTION
        "Cisco Firepower firmware:InfraPackFsm:completionTime
        managed object property"
    ::= { cfprApFirmwareInfraPackFsmEntry 4 }

cfprApFirmwareInfraPackFsmCurrentFsm OBJECT-TYPE
    SYNTAX       CfprApFirmwareInfraPackFsmCurrentFsm
    MAX-ACCESS   read-only
    STATUS       current
    DESCRIPTION
        "Cisco Firepower firmware:InfraPackFsm:currentFsm
        managed object property"
    ::= { cfprApFirmwareInfraPackFsmEntry 5 }

cfprApFirmwareInfraPackFsmDescrData OBJECT-TYPE
    SYNTAX       SnmpAdminString
    MAX-ACCESS   read-only
    STATUS       current
    DESCRIPTION
        "Cisco Firepower firmware:InfraPackFsm:descr managed
        object property"
    ::= { cfprApFirmwareInfraPackFsmEntry 6 }

cfprApFirmwareInfraPackFsmFsmStatus OBJECT-TYPE
    SYNTAX       CfprApFsmFsmStageStatus
    MAX-ACCESS   read-only
    STATUS       current
    DESCRIPTION
        "Cisco Firepower firmware:InfraPackFsm:fsmStatus
        managed object property"
    ::= { cfprApFirmwareInfraPackFsmEntry 7 }

cfprApFirmwareInfraPackFsmProgress OBJECT-TYPE
    SYNTAX       Gauge32
    MAX-ACCESS   read-only
    STATUS       current
    DESCRIPTION
        "Cisco Firepower firmware:InfraPackFsm:progress
        managed object property"
    ::= { cfprApFirmwareInfraPackFsmEntry 8 }

cfprApFirmwareInfraPackFsmRmtErrCode OBJECT-TYPE
    SYNTAX       Gauge32
    MAX-ACCESS   read-only
    STATUS       current
    DESCRIPTION
        "Cisco Firepower firmware:InfraPackFsm:rmtErrCode
        managed object property"
    ::= { cfprApFirmwareInfraPackFsmEntry 9 }

cfprApFirmwareInfraPackFsmRmtErrDescr OBJECT-TYPE
    SYNTAX       SnmpAdminString
    MAX-ACCESS   read-only
    STATUS       current
    DESCRIPTION
        "Cisco Firepower firmware:InfraPackFsm:rmtErrDescr
        managed object property"
    ::= { cfprApFirmwareInfraPackFsmEntry 10 }

cfprApFirmwareInfraPackFsmRmtRslt OBJECT-TYPE
    SYNTAX       CfprApConditionRemoteInvRslt
    MAX-ACCESS   read-only
    STATUS       current
    DESCRIPTION
        "Cisco Firepower firmware:InfraPackFsm:rmtRslt
        managed object property"
    ::= { cfprApFirmwareInfraPackFsmEntry 11 }

cfprApFirmwareInfraPackFsmStageTable OBJECT-TYPE
    SYNTAX           SEQUENCE OF CfprApFirmwareInfraPackFsmStageEntry
    MAX-ACCESS       not-accessible
    STATUS           current
    DESCRIPTION
        "Cisco Firepower firmware:InfraPackFsmStage managed object table"
    ::= { cfprApFirmwareObjects 41 }

cfprApFirmwareInfraPackFsmStageEntry OBJECT-TYPE
    SYNTAX           CfprApFirmwareInfraPackFsmStageEntry
    MAX-ACCESS       not-accessible
    STATUS           current
    DESCRIPTION
        "Entry for the cfprApFirmwareInfraPackFsmStageTable table."
    INDEX { cfprApFirmwareInfraPackFsmStageInstanceId }
    ::= { cfprApFirmwareInfraPackFsmStageTable 1 }

CfprApFirmwareInfraPackFsmStageEntry ::= SEQUENCE {
    cfprApFirmwareInfraPackFsmStageInstanceId                        CfprApManagedObjectId,
    cfprApFirmwareInfraPackFsmStageDn                                CfprApManagedObjectDn,
    cfprApFirmwareInfraPackFsmStageRn                                SnmpAdminString,
    cfprApFirmwareInfraPackFsmStageDescrData                         SnmpAdminString,
    cfprApFirmwareInfraPackFsmStageLastUpdateTime                    DateAndTime,
    cfprApFirmwareInfraPackFsmStageName                              CfprApFirmwareInfraPackFsmStageName,
    cfprApFirmwareInfraPackFsmStageOrder                             Gauge32,
    cfprApFirmwareInfraPackFsmStageRetry                             Gauge32,
    cfprApFirmwareInfraPackFsmStageStageStatus                       CfprApFsmFsmStageStatus
}

cfprApFirmwareInfraPackFsmStageInstanceId OBJECT-TYPE
    SYNTAX       CfprApManagedObjectId
    MAX-ACCESS   not-accessible
    STATUS       current
    DESCRIPTION
        "Instance identifier of the managed object."
    ::= { cfprApFirmwareInfraPackFsmStageEntry 1 }

cfprApFirmwareInfraPackFsmStageDn OBJECT-TYPE
    SYNTAX       CfprApManagedObjectDn
    MAX-ACCESS   read-only
    STATUS       current
    DESCRIPTION
        "Cisco Firepower firmware:InfraPackFsmStage:dn
        managed object property"
    ::= { cfprApFirmwareInfraPackFsmStageEntry 2 }

cfprApFirmwareInfraPackFsmStageRn OBJECT-TYPE
    SYNTAX       SnmpAdminString
    MAX-ACCESS   read-only
    STATUS       current
    DESCRIPTION
        "Cisco Firepower firmware:InfraPackFsmStage:rn
        managed object property"
    ::= { cfprApFirmwareInfraPackFsmStageEntry 3 }

cfprApFirmwareInfraPackFsmStageDescrData OBJECT-TYPE
    SYNTAX       SnmpAdminString
    MAX-ACCESS   read-only
    STATUS       current
    DESCRIPTION
        "Cisco Firepower firmware:InfraPackFsmStage:descr
        managed object property"
    ::= { cfprApFirmwareInfraPackFsmStageEntry 4 }

cfprApFirmwareInfraPackFsmStageLastUpdateTime OBJECT-TYPE
    SYNTAX       DateAndTime
    MAX-ACCESS   read-only
    STATUS       current
    DESCRIPTION
        "Cisco Firepower firmware:InfraPackFsmStage:lastUpdateTime
        managed object property"
    ::= { cfprApFirmwareInfraPackFsmStageEntry 5 }

cfprApFirmwareInfraPackFsmStageName OBJECT-TYPE
    SYNTAX       CfprApFirmwareInfraPackFsmStageName
    MAX-ACCESS   read-only
    STATUS       current
    DESCRIPTION
        "Cisco Firepower firmware:InfraPackFsmStage:name
        managed object property"
    ::= { cfprApFirmwareInfraPackFsmStageEntry 6 }

cfprApFirmwareInfraPackFsmStageOrder OBJECT-TYPE
    SYNTAX       Gauge32
    MAX-ACCESS   read-only
    STATUS       current
    DESCRIPTION
        "Cisco Firepower firmware:InfraPackFsmStage:order
        managed object property"
    ::= { cfprApFirmwareInfraPackFsmStageEntry 7 }

cfprApFirmwareInfraPackFsmStageRetry OBJECT-TYPE
    SYNTAX       Gauge32
    MAX-ACCESS   read-only
    STATUS       current
    DESCRIPTION
        "Cisco Firepower firmware:InfraPackFsmStage:retry
        managed object property"
    ::= { cfprApFirmwareInfraPackFsmStageEntry 8 }

cfprApFirmwareInfraPackFsmStageStageStatus OBJECT-TYPE
    SYNTAX       CfprApFsmFsmStageStatus
    MAX-ACCESS   read-only
    STATUS       current
    DESCRIPTION
        "Cisco Firepower firmware:InfraPackFsmStage:stageStatus
        managed object property"
    ::= { cfprApFirmwareInfraPackFsmStageEntry 9 }

cfprApFirmwareInfraPackFsmTaskTable OBJECT-TYPE
    SYNTAX           SEQUENCE OF CfprApFirmwareInfraPackFsmTaskEntry
    MAX-ACCESS       not-accessible
    STATUS           current
    DESCRIPTION
        "Cisco Firepower firmware:InfraPackFsmTask managed object table"
    ::= { cfprApFirmwareObjects 42 }

cfprApFirmwareInfraPackFsmTaskEntry OBJECT-TYPE
    SYNTAX           CfprApFirmwareInfraPackFsmTaskEntry
    MAX-ACCESS       not-accessible
    STATUS           current
    DESCRIPTION
        "Entry for the cfprApFirmwareInfraPackFsmTaskTable table."
    INDEX { cfprApFirmwareInfraPackFsmTaskInstanceId }
    ::= { cfprApFirmwareInfraPackFsmTaskTable 1 }

CfprApFirmwareInfraPackFsmTaskEntry ::= SEQUENCE {
    cfprApFirmwareInfraPackFsmTaskInstanceId                         CfprApManagedObjectId,
    cfprApFirmwareInfraPackFsmTaskDn                                 CfprApManagedObjectDn,
    cfprApFirmwareInfraPackFsmTaskRn                                 SnmpAdminString,
    cfprApFirmwareInfraPackFsmTaskCompletion                         CfprApFsmCompletion,
    cfprApFirmwareInfraPackFsmTaskFlags                              CfprApFirmwareInfraPackFsmTaskFlags,
    cfprApFirmwareInfraPackFsmTaskItem                               CfprApFirmwareInfraPackFsmTaskItem,
    cfprApFirmwareInfraPackFsmTaskSeqId                              Gauge32
}

cfprApFirmwareInfraPackFsmTaskInstanceId OBJECT-TYPE
    SYNTAX       CfprApManagedObjectId
    MAX-ACCESS   not-accessible
    STATUS       current
    DESCRIPTION
        "Instance identifier of the managed object."
    ::= { cfprApFirmwareInfraPackFsmTaskEntry 1 }

cfprApFirmwareInfraPackFsmTaskDn OBJECT-TYPE
    SYNTAX       CfprApManagedObjectDn
    MAX-ACCESS   read-only
    STATUS       current
    DESCRIPTION
        "Cisco Firepower firmware:InfraPackFsmTask:dn managed
        object property"
    ::= { cfprApFirmwareInfraPackFsmTaskEntry 2 }

cfprApFirmwareInfraPackFsmTaskRn OBJECT-TYPE
    SYNTAX       SnmpAdminString
    MAX-ACCESS   read-only
    STATUS       current
    DESCRIPTION
        "Cisco Firepower firmware:InfraPackFsmTask:rn managed
        object property"
    ::= { cfprApFirmwareInfraPackFsmTaskEntry 3 }

cfprApFirmwareInfraPackFsmTaskCompletion OBJECT-TYPE
    SYNTAX       CfprApFsmCompletion
    MAX-ACCESS   read-only
    STATUS       current
    DESCRIPTION
        "Cisco Firepower firmware:InfraPackFsmTask:completion
        managed object property"
    ::= { cfprApFirmwareInfraPackFsmTaskEntry 4 }

cfprApFirmwareInfraPackFsmTaskFlags OBJECT-TYPE
    SYNTAX       CfprApFirmwareInfraPackFsmTaskFlags
    MAX-ACCESS   read-only
    STATUS       current
    DESCRIPTION
        "Cisco Firepower firmware:InfraPackFsmTask:flags
        managed object property"
    ::= { cfprApFirmwareInfraPackFsmTaskEntry 5 }

cfprApFirmwareInfraPackFsmTaskItem OBJECT-TYPE
    SYNTAX       CfprApFirmwareInfraPackFsmTaskItem
    MAX-ACCESS   read-only
    STATUS       current
    DESCRIPTION
        "Cisco Firepower firmware:InfraPackFsmTask:item
        managed object property"
    ::= { cfprApFirmwareInfraPackFsmTaskEntry 6 }

cfprApFirmwareInfraPackFsmTaskSeqId OBJECT-TYPE
    SYNTAX       Gauge32
    MAX-ACCESS   read-only
    STATUS       current
    DESCRIPTION
        "Cisco Firepower firmware:InfraPackFsmTask:seqId
        managed object property"
    ::= { cfprApFirmwareInfraPackFsmTaskEntry 7 }

cfprApFirmwareInstallImpactTable OBJECT-TYPE
    SYNTAX           SEQUENCE OF CfprApFirmwareInstallImpactEntry
    MAX-ACCESS       not-accessible
    STATUS           current
    DESCRIPTION
        "Cisco Firepower firmware:InstallImpact managed object table"
    ::= { cfprApFirmwareObjects 43 }

cfprApFirmwareInstallImpactEntry OBJECT-TYPE
    SYNTAX           CfprApFirmwareInstallImpactEntry
    MAX-ACCESS       not-accessible
    STATUS           current
    DESCRIPTION
        "Entry for the cfprApFirmwareInstallImpactTable table."
    INDEX { cfprApFirmwareInstallImpactInstanceId }
    ::= { cfprApFirmwareInstallImpactTable 1 }

CfprApFirmwareInstallImpactEntry ::= SEQUENCE {
    cfprApFirmwareInstallImpactInstanceId                            CfprApManagedObjectId,
    cfprApFirmwareInstallImpactDn                                    CfprApManagedObjectDn,
    cfprApFirmwareInstallImpactRn                                    SnmpAdminString,
    cfprApFirmwareInstallImpactDescr                                 SnmpAdminString,
    cfprApFirmwareInstallImpactKeyDn                                 SnmpAdminString,
    cfprApFirmwareInstallImpactMaintPolicyDn                         SnmpAdminString,
    cfprApFirmwareInstallImpactRebootPolicy                          SnmpAdminString,
    cfprApFirmwareInstallImpactSubject                               CfprApFirmwareEquipmentType,
    cfprApFirmwareInstallImpactType                                  CfprApFirmwareImpactType
}

cfprApFirmwareInstallImpactInstanceId OBJECT-TYPE
    SYNTAX       CfprApManagedObjectId
    MAX-ACCESS   not-accessible
    STATUS       current
    DESCRIPTION
        "Instance identifier of the managed object."
    ::= { cfprApFirmwareInstallImpactEntry 1 }

cfprApFirmwareInstallImpactDn OBJECT-TYPE
    SYNTAX       CfprApManagedObjectDn
    MAX-ACCESS   read-only
    STATUS       current
    DESCRIPTION
        "Cisco Firepower firmware:InstallImpact:dn managed
        object property"
    ::= { cfprApFirmwareInstallImpactEntry 2 }

cfprApFirmwareInstallImpactRn OBJECT-TYPE
    SYNTAX       SnmpAdminString
    MAX-ACCESS   read-only
    STATUS       current
    DESCRIPTION
        "Cisco Firepower firmware:InstallImpact:rn managed
        object property"
    ::= { cfprApFirmwareInstallImpactEntry 3 }

cfprApFirmwareInstallImpactDescr OBJECT-TYPE
    SYNTAX       SnmpAdminString
    MAX-ACCESS   read-only
    STATUS       current
    DESCRIPTION
        "Cisco Firepower firmware:InstallImpact:descr managed
        object property"
    ::= { cfprApFirmwareInstallImpactEntry 4 }

cfprApFirmwareInstallImpactKeyDn OBJECT-TYPE
    SYNTAX       SnmpAdminString
    MAX-ACCESS   read-only
    STATUS       current
    DESCRIPTION
        "Cisco Firepower firmware:InstallImpact:keyDn managed
        object property"
    ::= { cfprApFirmwareInstallImpactEntry 5 }

cfprApFirmwareInstallImpactMaintPolicyDn OBJECT-TYPE
    SYNTAX       SnmpAdminString
    MAX-ACCESS   read-only
    STATUS       current
    DESCRIPTION
        "Cisco Firepower firmware:InstallImpact:maintPolicyDn
        managed object property"
    ::= { cfprApFirmwareInstallImpactEntry 6 }

cfprApFirmwareInstallImpactRebootPolicy OBJECT-TYPE
    SYNTAX       SnmpAdminString
    MAX-ACCESS   read-only
    STATUS       current
    DESCRIPTION
        "Cisco Firepower firmware:InstallImpact:rebootPolicy
        managed object property"
    ::= { cfprApFirmwareInstallImpactEntry 7 }

cfprApFirmwareInstallImpactSubject OBJECT-TYPE
    SYNTAX       CfprApFirmwareEquipmentType
    MAX-ACCESS   read-only
    STATUS       current
    DESCRIPTION
        "Cisco Firepower firmware:InstallImpact:subject
        managed object property"
    ::= { cfprApFirmwareInstallImpactEntry 8 }

cfprApFirmwareInstallImpactType OBJECT-TYPE
    SYNTAX       CfprApFirmwareImpactType
    MAX-ACCESS   read-only
    STATUS       current
    DESCRIPTION
        "Cisco Firepower firmware:InstallImpact:type managed
        object property"
    ::= { cfprApFirmwareInstallImpactEntry 9 }

cfprApFirmwareInstallableTable OBJECT-TYPE
    SYNTAX           SEQUENCE OF CfprApFirmwareInstallableEntry
    MAX-ACCESS       not-accessible
    STATUS           current
    DESCRIPTION
        "Cisco Firepower firmware:Installable managed object table"
    ::= { cfprApFirmwareObjects 44 }

cfprApFirmwareInstallableEntry OBJECT-TYPE
    SYNTAX           CfprApFirmwareInstallableEntry
    MAX-ACCESS       not-accessible
    STATUS           current
    DESCRIPTION
        "Entry for the cfprApFirmwareInstallableTable table."
    INDEX { cfprApFirmwareInstallableInstanceId }
    ::= { cfprApFirmwareInstallableTable 1 }

CfprApFirmwareInstallableEntry ::= SEQUENCE {
    cfprApFirmwareInstallableInstanceId                              CfprApManagedObjectId,
    cfprApFirmwareInstallableDn                                      CfprApManagedObjectDn,
    cfprApFirmwareInstallableRn                                      SnmpAdminString,
    cfprApFirmwareInstallableChecksum                                SnmpAdminString,
    cfprApFirmwareInstallableInProgress                              Gauge32,
    cfprApFirmwareInstallableIsoname                                 SnmpAdminString,
    cfprApFirmwareInstallableLocation                                SnmpAdminString,
    cfprApFirmwareInstallableModel                                   SnmpAdminString,
    cfprApFirmwareInstallableName                                    SnmpAdminString,
    cfprApFirmwareInstallableSize                                    Gauge32,
    cfprApFirmwareInstallableType                                    CfprApFirmwareType,
    cfprApFirmwareInstallableVendor                                  SnmpAdminString,
    cfprApFirmwareInstallableVersion                                 SnmpAdminString
}

cfprApFirmwareInstallableInstanceId OBJECT-TYPE
    SYNTAX       CfprApManagedObjectId
    MAX-ACCESS   not-accessible
    STATUS       current
    DESCRIPTION
        "Instance identifier of the managed object."
    ::= { cfprApFirmwareInstallableEntry 1 }

cfprApFirmwareInstallableDn OBJECT-TYPE
    SYNTAX       CfprApManagedObjectDn
    MAX-ACCESS   read-only
    STATUS       current
    DESCRIPTION
        "Cisco Firepower firmware:Installable:dn managed object property"
    ::= { cfprApFirmwareInstallableEntry 2 }

cfprApFirmwareInstallableRn OBJECT-TYPE
    SYNTAX       SnmpAdminString
    MAX-ACCESS   read-only
    STATUS       current
    DESCRIPTION
        "Cisco Firepower firmware:Installable:rn managed object property"
    ::= { cfprApFirmwareInstallableEntry 3 }

cfprApFirmwareInstallableChecksum OBJECT-TYPE
    SYNTAX       SnmpAdminString
    MAX-ACCESS   read-only
    STATUS       current
    DESCRIPTION
        "Cisco Firepower firmware:Installable:checksum
        managed object property"
    ::= { cfprApFirmwareInstallableEntry 4 }

cfprApFirmwareInstallableInProgress OBJECT-TYPE
    SYNTAX       Gauge32
    MAX-ACCESS   read-only
    STATUS       current
    DESCRIPTION
        "Cisco Firepower firmware:Installable:inProgress
        managed object property"
    ::= { cfprApFirmwareInstallableEntry 5 }

cfprApFirmwareInstallableIsoname OBJECT-TYPE
    SYNTAX       SnmpAdminString
    MAX-ACCESS   read-only
    STATUS       current
    DESCRIPTION
        "Cisco Firepower firmware:Installable:isoname managed
        object property"
    ::= { cfprApFirmwareInstallableEntry 6 }

cfprApFirmwareInstallableLocation OBJECT-TYPE
    SYNTAX       SnmpAdminString
    MAX-ACCESS   read-only
    STATUS       current
    DESCRIPTION
        "Cisco Firepower firmware:Installable:location
        managed object property"
    ::= { cfprApFirmwareInstallableEntry 7 }

cfprApFirmwareInstallableModel OBJECT-TYPE
    SYNTAX       SnmpAdminString
    MAX-ACCESS   read-only
    STATUS       current
    DESCRIPTION
        "Cisco Firepower firmware:Installable:model managed
        object property"
    ::= { cfprApFirmwareInstallableEntry 8 }

cfprApFirmwareInstallableName OBJECT-TYPE
    SYNTAX       SnmpAdminString
    MAX-ACCESS   read-only
    STATUS       current
    DESCRIPTION
        "Cisco Firepower firmware:Installable:name managed
        object property"
    ::= { cfprApFirmwareInstallableEntry 9 }

cfprApFirmwareInstallableSize OBJECT-TYPE
    SYNTAX       Gauge32
    MAX-ACCESS   read-only
    STATUS       current
    DESCRIPTION
        "Cisco Firepower firmware:Installable:size managed
        object property"
    ::= { cfprApFirmwareInstallableEntry 10 }

cfprApFirmwareInstallableType OBJECT-TYPE
    SYNTAX       CfprApFirmwareType
    MAX-ACCESS   read-only
    STATUS       current
    DESCRIPTION
        "Cisco Firepower firmware:Installable:type managed
        object property"
    ::= { cfprApFirmwareInstallableEntry 11 }

cfprApFirmwareInstallableVendor OBJECT-TYPE
    SYNTAX       SnmpAdminString
    MAX-ACCESS   read-only
    STATUS       current
    DESCRIPTION
        "Cisco Firepower firmware:Installable:vendor managed
        object property"
    ::= { cfprApFirmwareInstallableEntry 12 }

cfprApFirmwareInstallableVersion OBJECT-TYPE
    SYNTAX       SnmpAdminString
    MAX-ACCESS   read-only
    STATUS       current
    DESCRIPTION
        "Cisco Firepower firmware:Installable:version managed
        object property"
    ::= { cfprApFirmwareInstallableEntry 13 }

cfprApFirmwarePackItemTable OBJECT-TYPE
    SYNTAX           SEQUENCE OF CfprApFirmwarePackItemEntry
    MAX-ACCESS       not-accessible
    STATUS           current
    DESCRIPTION
        "Cisco Firepower firmware:PackItem managed object table"
    ::= { cfprApFirmwareObjects 45 }

cfprApFirmwarePackItemEntry OBJECT-TYPE
    SYNTAX           CfprApFirmwarePackItemEntry
    MAX-ACCESS       not-accessible
    STATUS           current
    DESCRIPTION
        "Entry for the cfprApFirmwarePackItemTable table."
    INDEX { cfprApFirmwarePackItemInstanceId }
    ::= { cfprApFirmwarePackItemTable 1 }

CfprApFirmwarePackItemEntry ::= SEQUENCE {
    cfprApFirmwarePackItemInstanceId                                 CfprApManagedObjectId,
    cfprApFirmwarePackItemDn                                         CfprApManagedObjectDn,
    cfprApFirmwarePackItemRn                                         SnmpAdminString,
    cfprApFirmwarePackItemHwModel                                    SnmpAdminString,
    cfprApFirmwarePackItemHwVendor                                   SnmpAdminString,
    cfprApFirmwarePackItemPresence                                   CfprApFirmwarePackItemPresence,
    cfprApFirmwarePackItemType                                       CfprApFirmwareItemType,
    cfprApFirmwarePackItemVersion                                    SnmpAdminString
}

cfprApFirmwarePackItemInstanceId OBJECT-TYPE
    SYNTAX       CfprApManagedObjectId
    MAX-ACCESS   not-accessible
    STATUS       current
    DESCRIPTION
        "Instance identifier of the managed object."
    ::= { cfprApFirmwarePackItemEntry 1 }

cfprApFirmwarePackItemDn OBJECT-TYPE
    SYNTAX       CfprApManagedObjectDn
    MAX-ACCESS   read-only
    STATUS       current
    DESCRIPTION
        "Cisco Firepower firmware:PackItem:dn managed object property"
    ::= { cfprApFirmwarePackItemEntry 2 }

cfprApFirmwarePackItemRn OBJECT-TYPE
    SYNTAX       SnmpAdminString
    MAX-ACCESS   read-only
    STATUS       current
    DESCRIPTION
        "Cisco Firepower firmware:PackItem:rn managed object property"
    ::= { cfprApFirmwarePackItemEntry 3 }

cfprApFirmwarePackItemHwModel OBJECT-TYPE
    SYNTAX       SnmpAdminString
    MAX-ACCESS   read-only
    STATUS       current
    DESCRIPTION
        "Cisco Firepower firmware:PackItem:hwModel managed
        object property"
    ::= { cfprApFirmwarePackItemEntry 4 }

cfprApFirmwarePackItemHwVendor OBJECT-TYPE
    SYNTAX       SnmpAdminString
    MAX-ACCESS   read-only
    STATUS       current
    DESCRIPTION
        "Cisco Firepower firmware:PackItem:hwVendor managed
        object property"
    ::= { cfprApFirmwarePackItemEntry 5 }

cfprApFirmwarePackItemPresence OBJECT-TYPE
    SYNTAX       CfprApFirmwarePackItemPresence
    MAX-ACCESS   read-only
    STATUS       current
    DESCRIPTION
        "Cisco Firepower firmware:PackItem:presence managed
        object property"
    ::= { cfprApFirmwarePackItemEntry 6 }

cfprApFirmwarePackItemType OBJECT-TYPE
    SYNTAX       CfprApFirmwareItemType
    MAX-ACCESS   read-only
    STATUS       current
    DESCRIPTION
        "Cisco Firepower firmware:PackItem:type managed object property"
    ::= { cfprApFirmwarePackItemEntry 7 }

cfprApFirmwarePackItemVersion OBJECT-TYPE
    SYNTAX       SnmpAdminString
    MAX-ACCESS   read-only
    STATUS       current
    DESCRIPTION
        "Cisco Firepower firmware:PackItem:version managed
        object property"
    ::= { cfprApFirmwarePackItemEntry 8 }

cfprApFirmwarePlatformTable OBJECT-TYPE
    SYNTAX           SEQUENCE OF CfprApFirmwarePlatformEntry
    MAX-ACCESS       not-accessible
    STATUS           current
    DESCRIPTION
        "Cisco Firepower firmware:Platform managed object table"
    ::= { cfprApFirmwareObjects 46 }

cfprApFirmwarePlatformEntry OBJECT-TYPE
    SYNTAX           CfprApFirmwarePlatformEntry
    MAX-ACCESS       not-accessible
    STATUS           current
    DESCRIPTION
        "Entry for the cfprApFirmwarePlatformTable table."
    INDEX { cfprApFirmwarePlatformInstanceId }
    ::= { cfprApFirmwarePlatformTable 1 }

CfprApFirmwarePlatformEntry ::= SEQUENCE {
    cfprApFirmwarePlatformInstanceId                                 CfprApManagedObjectId,
    cfprApFirmwarePlatformDn                                         CfprApManagedObjectDn,
    cfprApFirmwarePlatformRn                                         SnmpAdminString,
    cfprApFirmwarePlatformAdminState                                 CfprApTrigAdminState,
    cfprApFirmwarePlatformAutoDelete                                 TruthValue,
    cfprApFirmwarePlatformDescr                                      SnmpAdminString,
    cfprApFirmwarePlatformIgnoreCap                                  TruthValue,
    cfprApFirmwarePlatformIntId                                      SnmpAdminString,
    cfprApFirmwarePlatformName                                       SnmpAdminString,
    cfprApFirmwarePlatformOperScheduler                              SnmpAdminString,
    cfprApFirmwarePlatformOperState                                  CfprApTrigTrigOperState,
    cfprApFirmwarePlatformOperVersion                                SnmpAdminString,
    cfprApFirmwarePlatformPolicyLevel                                Gauge32,
    cfprApFirmwarePlatformPolicyOwner                                CfprApPolicyPolicyOwner,
    cfprApFirmwarePlatformScheduler                                  SnmpAdminString
}

cfprApFirmwarePlatformInstanceId OBJECT-TYPE
    SYNTAX       CfprApManagedObjectId
    MAX-ACCESS   not-accessible
    STATUS       current
    DESCRIPTION
        "Instance identifier of the managed object."
    ::= { cfprApFirmwarePlatformEntry 1 }

cfprApFirmwarePlatformDn OBJECT-TYPE
    SYNTAX       CfprApManagedObjectDn
    MAX-ACCESS   read-only
    STATUS       current
    DESCRIPTION
        "Cisco Firepower firmware:Platform:dn managed object property"
    ::= { cfprApFirmwarePlatformEntry 2 }

cfprApFirmwarePlatformRn OBJECT-TYPE
    SYNTAX       SnmpAdminString
    MAX-ACCESS   read-only
    STATUS       current
    DESCRIPTION
        "Cisco Firepower firmware:Platform:rn managed object property"
    ::= { cfprApFirmwarePlatformEntry 3 }

cfprApFirmwarePlatformAdminState OBJECT-TYPE
    SYNTAX       CfprApTrigAdminState
    MAX-ACCESS   read-only
    STATUS       current
    DESCRIPTION
        "Cisco Firepower firmware:Platform:adminState managed
        object property"
    ::= { cfprApFirmwarePlatformEntry 4 }

cfprApFirmwarePlatformAutoDelete OBJECT-TYPE
    SYNTAX       TruthValue
    MAX-ACCESS   read-only
    STATUS       current
    DESCRIPTION
        "Cisco Firepower firmware:Platform:autoDelete managed
        object property"
    ::= { cfprApFirmwarePlatformEntry 5 }

cfprApFirmwarePlatformDescr OBJECT-TYPE
    SYNTAX       SnmpAdminString
    MAX-ACCESS   read-only
    STATUS       current
    DESCRIPTION
        "Cisco Firepower firmware:Platform:descr managed object property"
    ::= { cfprApFirmwarePlatformEntry 6 }

cfprApFirmwarePlatformIgnoreCap OBJECT-TYPE
    SYNTAX       TruthValue
    MAX-ACCESS   read-only
    STATUS       current
    DESCRIPTION
        "Cisco Firepower firmware:Platform:ignoreCap managed
        object property"
    ::= { cfprApFirmwarePlatformEntry 7 }

cfprApFirmwarePlatformIntId OBJECT-TYPE
    SYNTAX       SnmpAdminString
    MAX-ACCESS   read-only
    STATUS       current
    DESCRIPTION
        "Cisco Firepower firmware:Platform:intId managed object property"
    ::= { cfprApFirmwarePlatformEntry 8 }

cfprApFirmwarePlatformName OBJECT-TYPE
    SYNTAX       SnmpAdminString
    MAX-ACCESS   read-only
    STATUS       current
    DESCRIPTION
        "Cisco Firepower firmware:Platform:name managed object property"
    ::= { cfprApFirmwarePlatformEntry 9 }

cfprApFirmwarePlatformOperScheduler OBJECT-TYPE
    SYNTAX       SnmpAdminString
    MAX-ACCESS   read-only
    STATUS       current
    DESCRIPTION
        "Cisco Firepower firmware:Platform:operScheduler
        managed object property"
    ::= { cfprApFirmwarePlatformEntry 10 }

cfprApFirmwarePlatformOperState OBJECT-TYPE
    SYNTAX       CfprApTrigTrigOperState
    MAX-ACCESS   read-only
    STATUS       current
    DESCRIPTION
        "Cisco Firepower firmware:Platform:operState managed
        object property"
    ::= { cfprApFirmwarePlatformEntry 11 }

cfprApFirmwarePlatformOperVersion OBJECT-TYPE
    SYNTAX       SnmpAdminString
    MAX-ACCESS   read-only
    STATUS       current
    DESCRIPTION
        "Cisco Firepower firmware:Platform:operVersion
        managed object property"
    ::= { cfprApFirmwarePlatformEntry 12 }

cfprApFirmwarePlatformPolicyLevel OBJECT-TYPE
    SYNTAX       Gauge32
    MAX-ACCESS   read-only
    STATUS       current
    DESCRIPTION
        "Cisco Firepower firmware:Platform:policyLevel
        managed object property"
    ::= { cfprApFirmwarePlatformEntry 13 }

cfprApFirmwarePlatformPolicyOwner OBJECT-TYPE
    SYNTAX       CfprApPolicyPolicyOwner
    MAX-ACCESS   read-only
    STATUS       current
    DESCRIPTION
        "Cisco Firepower firmware:Platform:policyOwner
        managed object property"
    ::= { cfprApFirmwarePlatformEntry 14 }

cfprApFirmwarePlatformScheduler OBJECT-TYPE
    SYNTAX       SnmpAdminString
    MAX-ACCESS   read-only
    STATUS       current
    DESCRIPTION
        "Cisco Firepower firmware:Platform:scheduler managed
        object property"
    ::= { cfprApFirmwarePlatformEntry 15 }

cfprApFirmwarePlatformBundleTypeCapProviderTable OBJECT-TYPE
    SYNTAX           SEQUENCE OF CfprApFirmwarePlatformBundleTypeCapProviderEntry
    MAX-ACCESS       not-accessible
    STATUS           current
    DESCRIPTION
        "Cisco Firepower firmware:PlatformBundleTypeCapProvider
        managed object table"
    ::= { cfprApFirmwareObjects 47 }

cfprApFirmwarePlatformBundleTypeCapProviderEntry OBJECT-TYPE
    SYNTAX           CfprApFirmwarePlatformBundleTypeCapProviderEntry
    MAX-ACCESS       not-accessible
    STATUS           current
    DESCRIPTION
        "Entry for the cfprApFirmwarePlatformBundleTypeCapProviderTable table."
    INDEX { cfprApFirmwarePlatformBundleTypeCapProviderInstanceId }
    ::= { cfprApFirmwarePlatformBundleTypeCapProviderTable 1 }

CfprApFirmwarePlatformBundleTypeCapProviderEntry ::= SEQUENCE {
    cfprApFirmwarePlatformBundleTypeCapProviderInstanceId            CfprApManagedObjectId,
    cfprApFirmwarePlatformBundleTypeCapProviderDn                    CfprApManagedObjectDn,
    cfprApFirmwarePlatformBundleTypeCapProviderRn                    SnmpAdminString,
    cfprApFirmwarePlatformBundleTypeCapProviderDeleted               TruthValue,
    cfprApFirmwarePlatformBundleTypeCapProviderDeprecated            TruthValue,
    cfprApFirmwarePlatformBundleTypeCapProviderElementLoadFailures   Gauge32,
    cfprApFirmwarePlatformBundleTypeCapProviderElementsLoaded        Gauge32,
    cfprApFirmwarePlatformBundleTypeCapProviderGencount              Gauge32,
    cfprApFirmwarePlatformBundleTypeCapProviderLoadErrors            Gauge32,
    cfprApFirmwarePlatformBundleTypeCapProviderLoadWarnings          Gauge32,
    cfprApFirmwarePlatformBundleTypeCapProviderMgmtPlaneVer          SnmpAdminString,
    cfprApFirmwarePlatformBundleTypeCapProviderModel                 SnmpAdminString,
    cfprApFirmwarePlatformBundleTypeCapProviderPlatformType          CfprApFirmwarePlatformType,
    cfprApFirmwarePlatformBundleTypeCapProviderVendor                SnmpAdminString
}

cfprApFirmwarePlatformBundleTypeCapProviderInstanceId OBJECT-TYPE
    SYNTAX       CfprApManagedObjectId
    MAX-ACCESS   not-accessible
    STATUS       current
    DESCRIPTION
        "Instance identifier of the managed object."
    ::= { cfprApFirmwarePlatformBundleTypeCapProviderEntry 1 }

cfprApFirmwarePlatformBundleTypeCapProviderDn OBJECT-TYPE
    SYNTAX       CfprApManagedObjectDn
    MAX-ACCESS   read-only
    STATUS       current
    DESCRIPTION
        "Cisco Firepower firmware:PlatformBundleTypeCapProvider:dn
        managed object property"
    ::= { cfprApFirmwarePlatformBundleTypeCapProviderEntry 2 }

cfprApFirmwarePlatformBundleTypeCapProviderRn OBJECT-TYPE
    SYNTAX       SnmpAdminString
    MAX-ACCESS   read-only
    STATUS       current
    DESCRIPTION
        "Cisco Firepower firmware:PlatformBundleTypeCapProvider:rn
        managed object property"
    ::= { cfprApFirmwarePlatformBundleTypeCapProviderEntry 3 }

cfprApFirmwarePlatformBundleTypeCapProviderDeleted OBJECT-TYPE
    SYNTAX       TruthValue
    MAX-ACCESS   read-only
    STATUS       current
    DESCRIPTION
        "Cisco Firepower firmware:PlatformBundleTypeCapProvider:deleted
        managed object property"
    ::= { cfprApFirmwarePlatformBundleTypeCapProviderEntry 4 }

cfprApFirmwarePlatformBundleTypeCapProviderDeprecated OBJECT-TYPE
    SYNTAX       TruthValue
    MAX-ACCESS   read-only
    STATUS       current
    DESCRIPTION
        "Cisco Firepower firmware:PlatformBundleTypeCapProvider:deprecated
         managed object property"
    ::= { cfprApFirmwarePlatformBundleTypeCapProviderEntry 5 }

cfprApFirmwarePlatformBundleTypeCapProviderElementLoadFailures OBJECT-TYPE
    SYNTAX       Gauge32
    MAX-ACCESS   read-only
    STATUS       current
    DESCRIPTION
        "Cisco Firepower firmware:PlatformBundleTypeCapProvider:elementLoa
        dFailures managed object property"
    ::= { cfprApFirmwarePlatformBundleTypeCapProviderEntry 6 }

cfprApFirmwarePlatformBundleTypeCapProviderElementsLoaded OBJECT-TYPE
    SYNTAX       Gauge32
    MAX-ACCESS   read-only
    STATUS       current
    DESCRIPTION
        "Cisco Firepower firmware:PlatformBundleTypeCapProvider:elementsLo
        aded managed object property"
    ::= { cfprApFirmwarePlatformBundleTypeCapProviderEntry 7 }

cfprApFirmwarePlatformBundleTypeCapProviderGencount OBJECT-TYPE
    SYNTAX       Gauge32
    MAX-ACCESS   read-only
    STATUS       current
    DESCRIPTION
        "Cisco Firepower firmware:PlatformBundleTypeCapProvider:gencount
        managed object property"
    ::= { cfprApFirmwarePlatformBundleTypeCapProviderEntry 8 }

cfprApFirmwarePlatformBundleTypeCapProviderLoadErrors OBJECT-TYPE
    SYNTAX       Gauge32
    MAX-ACCESS   read-only
    STATUS       current
    DESCRIPTION
        "Cisco Firepower firmware:PlatformBundleTypeCapProvider:loadErrors
         managed object property"
    ::= { cfprApFirmwarePlatformBundleTypeCapProviderEntry 9 }

cfprApFirmwarePlatformBundleTypeCapProviderLoadWarnings OBJECT-TYPE
    SYNTAX       Gauge32
    MAX-ACCESS   read-only
    STATUS       current
    DESCRIPTION
        "Cisco Firepower firmware:PlatformBundleTypeCapProvider:loadWarnin
        gs managed object property"
    ::= { cfprApFirmwarePlatformBundleTypeCapProviderEntry 10 }

cfprApFirmwarePlatformBundleTypeCapProviderMgmtPlaneVer OBJECT-TYPE
    SYNTAX       SnmpAdminString
    MAX-ACCESS   read-only
    STATUS       current
    DESCRIPTION
        "Cisco Firepower firmware:PlatformBundleTypeCapProvider:mgmtPlaneV
        er managed object property"
    ::= { cfprApFirmwarePlatformBundleTypeCapProviderEntry 11 }

cfprApFirmwarePlatformBundleTypeCapProviderModel OBJECT-TYPE
    SYNTAX       SnmpAdminString
    MAX-ACCESS   read-only
    STATUS       current
    DESCRIPTION
        "Cisco Firepower firmware:PlatformBundleTypeCapProvider:model
        managed object property"
    ::= { cfprApFirmwarePlatformBundleTypeCapProviderEntry 12 }

cfprApFirmwarePlatformBundleTypeCapProviderPlatformType OBJECT-TYPE
    SYNTAX       CfprApFirmwarePlatformType
    MAX-ACCESS   read-only
    STATUS       current
    DESCRIPTION
        "Cisco Firepower firmware:PlatformBundleTypeCapProvider:platformTy
        pe managed object property"
    ::= { cfprApFirmwarePlatformBundleTypeCapProviderEntry 13 }

cfprApFirmwarePlatformBundleTypeCapProviderVendor OBJECT-TYPE
    SYNTAX       SnmpAdminString
    MAX-ACCESS   read-only
    STATUS       current
    DESCRIPTION
        "Cisco Firepower firmware:PlatformBundleTypeCapProvider:vendor
        managed object property"
    ::= { cfprApFirmwarePlatformBundleTypeCapProviderEntry 14 }

cfprApFirmwarePlatformPackTable OBJECT-TYPE
    SYNTAX           SEQUENCE OF CfprApFirmwarePlatformPackEntry
    MAX-ACCESS       not-accessible
    STATUS           current
    DESCRIPTION
        "Cisco Firepower firmware:PlatformPack managed object table"
    ::= { cfprApFirmwareObjects 48 }

cfprApFirmwarePlatformPackEntry OBJECT-TYPE
    SYNTAX           CfprApFirmwarePlatformPackEntry
    MAX-ACCESS       not-accessible
    STATUS           current
    DESCRIPTION
        "Entry for the cfprApFirmwarePlatformPackTable table."
    INDEX { cfprApFirmwarePlatformPackInstanceId }
    ::= { cfprApFirmwarePlatformPackTable 1 }

CfprApFirmwarePlatformPackEntry ::= SEQUENCE {
    cfprApFirmwarePlatformPackInstanceId                             CfprApManagedObjectId,
    cfprApFirmwarePlatformPackDn                                     CfprApManagedObjectDn,
    cfprApFirmwarePlatformPackRn                                     SnmpAdminString,
    cfprApFirmwarePlatformPackDescr                                  SnmpAdminString,
    cfprApFirmwarePlatformPackForceDeploy                            TruthValue,
    cfprApFirmwarePlatformPackFsmDescr                               SnmpAdminString,
    cfprApFirmwarePlatformPackFsmFlags                               SnmpAdminString,
    cfprApFirmwarePlatformPackFsmPrev                                SnmpAdminString,
    cfprApFirmwarePlatformPackFsmProgr                               Gauge32,
    cfprApFirmwarePlatformPackFsmRmtInvErrCode                       Gauge32,
    cfprApFirmwarePlatformPackFsmRmtInvErrDescr                      SnmpAdminString,
    cfprApFirmwarePlatformPackFsmRmtInvRslt                          CfprApConditionRemoteInvRslt,
    cfprApFirmwarePlatformPackFsmStageDescr                          SnmpAdminString,
    cfprApFirmwarePlatformPackFsmStamp                               DateAndTime,
    cfprApFirmwarePlatformPackFsmStatus                              SnmpAdminString,
    cfprApFirmwarePlatformPackFsmTry                                 Gauge32,
    cfprApFirmwarePlatformPackIntId                                  SnmpAdminString,
    cfprApFirmwarePlatformPackMode                                   CfprApFirmwarePackMode,
    cfprApFirmwarePlatformPackName                                   SnmpAdminString,
    cfprApFirmwarePlatformPackPlatformBundleName                     SnmpAdminString,
    cfprApFirmwarePlatformPackPlatformBundleVersion                  SnmpAdminString,
    cfprApFirmwarePlatformPackPolicyLevel                            Gauge32,
    cfprApFirmwarePlatformPackPolicyOwner                            CfprApPolicyPolicyOwner,
    cfprApFirmwarePlatformPackPreviousBundleVersion                  SnmpAdminString,
    cfprApFirmwarePlatformPackRestoreVersion                         TruthValue,
    cfprApFirmwarePlatformPackSerializeHostUpgrade                   TruthValue,
    cfprApFirmwarePlatformPackSkipManagerValidation                  TruthValue,
    cfprApFirmwarePlatformPackStageSize                              Gauge32,
    cfprApFirmwarePlatformPackUpdateTrigger                          DateAndTime
}

cfprApFirmwarePlatformPackInstanceId OBJECT-TYPE
    SYNTAX       CfprApManagedObjectId
    MAX-ACCESS   not-accessible
    STATUS       current
    DESCRIPTION
        "Instance identifier of the managed object."
    ::= { cfprApFirmwarePlatformPackEntry 1 }

cfprApFirmwarePlatformPackDn OBJECT-TYPE
    SYNTAX       CfprApManagedObjectDn
    MAX-ACCESS   read-only
    STATUS       current
    DESCRIPTION
        "Cisco Firepower firmware:PlatformPack:dn managed object property"
    ::= { cfprApFirmwarePlatformPackEntry 2 }

cfprApFirmwarePlatformPackRn OBJECT-TYPE
    SYNTAX       SnmpAdminString
    MAX-ACCESS   read-only
    STATUS       current
    DESCRIPTION
        "Cisco Firepower firmware:PlatformPack:rn managed object property"
    ::= { cfprApFirmwarePlatformPackEntry 3 }

cfprApFirmwarePlatformPackDescr OBJECT-TYPE
    SYNTAX       SnmpAdminString
    MAX-ACCESS   read-only
    STATUS       current
    DESCRIPTION
        "Cisco Firepower firmware:PlatformPack:descr managed
        object property"
    ::= { cfprApFirmwarePlatformPackEntry 4 }

cfprApFirmwarePlatformPackForceDeploy OBJECT-TYPE
    SYNTAX       TruthValue
    MAX-ACCESS   read-only
    STATUS       current
    DESCRIPTION
        "Cisco Firepower firmware:PlatformPack:forceDeploy
        managed object property"
    ::= { cfprApFirmwarePlatformPackEntry 5 }

cfprApFirmwarePlatformPackFsmDescr OBJECT-TYPE
    SYNTAX       SnmpAdminString
    MAX-ACCESS   read-only
    STATUS       current
    DESCRIPTION
        "Cisco Firepower firmware:PlatformPack:fsmDescr
        managed object property"
    ::= { cfprApFirmwarePlatformPackEntry 6 }

cfprApFirmwarePlatformPackFsmFlags OBJECT-TYPE
    SYNTAX       SnmpAdminString
    MAX-ACCESS   read-only
    STATUS       current
    DESCRIPTION
        "Cisco Firepower firmware:PlatformPack:fsmFlags
        managed object property"
    ::= { cfprApFirmwarePlatformPackEntry 7 }

cfprApFirmwarePlatformPackFsmPrev OBJECT-TYPE
    SYNTAX       SnmpAdminString
    MAX-ACCESS   read-only
    STATUS       current
    DESCRIPTION
        "Cisco Firepower firmware:PlatformPack:fsmPrev
        managed object property"
    ::= { cfprApFirmwarePlatformPackEntry 8 }

cfprApFirmwarePlatformPackFsmProgr OBJECT-TYPE
    SYNTAX       Gauge32
    MAX-ACCESS   read-only
    STATUS       current
    DESCRIPTION
        "Cisco Firepower firmware:PlatformPack:fsmProgr
        managed object property"
    ::= { cfprApFirmwarePlatformPackEntry 9 }

cfprApFirmwarePlatformPackFsmRmtInvErrCode OBJECT-TYPE
    SYNTAX       Gauge32
    MAX-ACCESS   read-only
    STATUS       current
    DESCRIPTION
        "Cisco Firepower firmware:PlatformPack:fsmRmtInvErrCode
        managed object property"
    ::= { cfprApFirmwarePlatformPackEntry 10 }

cfprApFirmwarePlatformPackFsmRmtInvErrDescr OBJECT-TYPE
    SYNTAX       SnmpAdminString
    MAX-ACCESS   read-only
    STATUS       current
    DESCRIPTION
        "Cisco Firepower firmware:PlatformPack:fsmRmtInvErrDescr
        managed object property"
    ::= { cfprApFirmwarePlatformPackEntry 11 }

cfprApFirmwarePlatformPackFsmRmtInvRslt OBJECT-TYPE
    SYNTAX       CfprApConditionRemoteInvRslt
    MAX-ACCESS   read-only
    STATUS       current
    DESCRIPTION
        "Cisco Firepower firmware:PlatformPack:fsmRmtInvRslt
        managed object property"
    ::= { cfprApFirmwarePlatformPackEntry 12 }

cfprApFirmwarePlatformPackFsmStageDescr OBJECT-TYPE
    SYNTAX       SnmpAdminString
    MAX-ACCESS   read-only
    STATUS       current
    DESCRIPTION
        "Cisco Firepower firmware:PlatformPack:fsmStageDescr
        managed object property"
    ::= { cfprApFirmwarePlatformPackEntry 13 }

cfprApFirmwarePlatformPackFsmStamp OBJECT-TYPE
    SYNTAX       DateAndTime
    MAX-ACCESS   read-only
    STATUS       current
    DESCRIPTION
        "Cisco Firepower firmware:PlatformPack:fsmStamp
        managed object property"
    ::= { cfprApFirmwarePlatformPackEntry 14 }

cfprApFirmwarePlatformPackFsmStatus OBJECT-TYPE
    SYNTAX       SnmpAdminString
    MAX-ACCESS   read-only
    STATUS       current
    DESCRIPTION
        "Cisco Firepower firmware:PlatformPack:fsmStatus
        managed object property"
    ::= { cfprApFirmwarePlatformPackEntry 15 }

cfprApFirmwarePlatformPackFsmTry OBJECT-TYPE
    SYNTAX       Gauge32
    MAX-ACCESS   read-only
    STATUS       current
    DESCRIPTION
        "Cisco Firepower firmware:PlatformPack:fsmTry managed
        object property"
    ::= { cfprApFirmwarePlatformPackEntry 16 }

cfprApFirmwarePlatformPackIntId OBJECT-TYPE
    SYNTAX       SnmpAdminString
    MAX-ACCESS   read-only
    STATUS       current
    DESCRIPTION
        "Cisco Firepower firmware:PlatformPack:intId managed
        object property"
    ::= { cfprApFirmwarePlatformPackEntry 17 }

cfprApFirmwarePlatformPackMode OBJECT-TYPE
    SYNTAX       CfprApFirmwarePackMode
    MAX-ACCESS   read-only
    STATUS       current
    DESCRIPTION
        "Cisco Firepower firmware:PlatformPack:mode managed
        object property"
    ::= { cfprApFirmwarePlatformPackEntry 18 }

cfprApFirmwarePlatformPackName OBJECT-TYPE
    SYNTAX       SnmpAdminString
    MAX-ACCESS   read-only
    STATUS       current
    DESCRIPTION
        "Cisco Firepower firmware:PlatformPack:name managed
        object property"
    ::= { cfprApFirmwarePlatformPackEntry 19 }

cfprApFirmwarePlatformPackPlatformBundleName OBJECT-TYPE
    SYNTAX       SnmpAdminString
    MAX-ACCESS   read-only
    STATUS       current
    DESCRIPTION
        "Cisco Firepower firmware:PlatformPack:platformBundleName
        managed object property"
    ::= { cfprApFirmwarePlatformPackEntry 20 }

cfprApFirmwarePlatformPackPlatformBundleVersion OBJECT-TYPE
    SYNTAX       SnmpAdminString
    MAX-ACCESS   read-only
    STATUS       current
    DESCRIPTION
        "Cisco Firepower firmware:PlatformPack:platformBundleVersion
        managed object property"
    ::= { cfprApFirmwarePlatformPackEntry 21 }

cfprApFirmwarePlatformPackPolicyLevel OBJECT-TYPE
    SYNTAX       Gauge32
    MAX-ACCESS   read-only
    STATUS       current
    DESCRIPTION
        "Cisco Firepower firmware:PlatformPack:policyLevel
        managed object property"
    ::= { cfprApFirmwarePlatformPackEntry 22 }

cfprApFirmwarePlatformPackPolicyOwner OBJECT-TYPE
    SYNTAX       CfprApPolicyPolicyOwner
    MAX-ACCESS   read-only
    STATUS       current
    DESCRIPTION
        "Cisco Firepower firmware:PlatformPack:policyOwner
        managed object property"
    ::= { cfprApFirmwarePlatformPackEntry 23 }

cfprApFirmwarePlatformPackPreviousBundleVersion OBJECT-TYPE
    SYNTAX       SnmpAdminString
    MAX-ACCESS   read-only
    STATUS       current
    DESCRIPTION
        "Cisco Firepower firmware:PlatformPack:previousBundleVersion
        managed object property"
    ::= { cfprApFirmwarePlatformPackEntry 24 }

cfprApFirmwarePlatformPackRestoreVersion OBJECT-TYPE
    SYNTAX       TruthValue
    MAX-ACCESS   read-only
    STATUS       current
    DESCRIPTION
        "Cisco Firepower firmware:PlatformPack:restoreVersion
        managed object property"
    ::= { cfprApFirmwarePlatformPackEntry 25 }

cfprApFirmwarePlatformPackSerializeHostUpgrade OBJECT-TYPE
    SYNTAX       TruthValue
    MAX-ACCESS   read-only
    STATUS       current
    DESCRIPTION
        "Cisco Firepower firmware:PlatformPack:serializeHostUpgrade
        managed object property"
    ::= { cfprApFirmwarePlatformPackEntry 26 }

cfprApFirmwarePlatformPackSkipManagerValidation OBJECT-TYPE
    SYNTAX       TruthValue
    MAX-ACCESS   read-only
    STATUS       current
    DESCRIPTION
        "Cisco Firepower firmware:PlatformPack:skipManagerValidation
        managed object property"
    ::= { cfprApFirmwarePlatformPackEntry 27 }

cfprApFirmwarePlatformPackStageSize OBJECT-TYPE
    SYNTAX       Gauge32
    MAX-ACCESS   read-only
    STATUS       current
    DESCRIPTION
        "Cisco Firepower firmware:PlatformPack:stageSize
        managed object property"
    ::= { cfprApFirmwarePlatformPackEntry 28 }

cfprApFirmwarePlatformPackUpdateTrigger OBJECT-TYPE
    SYNTAX       DateAndTime
    MAX-ACCESS   read-only
    STATUS       current
    DESCRIPTION
        "Cisco Firepower firmware:PlatformPack:updateTrigger
        managed object property"
    ::= { cfprApFirmwarePlatformPackEntry 29 }

cfprApFirmwarePlatformPackFsmTable OBJECT-TYPE
    SYNTAX           SEQUENCE OF CfprApFirmwarePlatformPackFsmEntry
    MAX-ACCESS       not-accessible
    STATUS           current
    DESCRIPTION
        "Cisco Firepower firmware:PlatformPackFsm managed object table"
    ::= { cfprApFirmwareObjects 49 }

cfprApFirmwarePlatformPackFsmEntry OBJECT-TYPE
    SYNTAX           CfprApFirmwarePlatformPackFsmEntry
    MAX-ACCESS       not-accessible
    STATUS           current
    DESCRIPTION
        "Entry for the cfprApFirmwarePlatformPackFsmTable table."
    INDEX { cfprApFirmwarePlatformPackFsmInstanceId }
    ::= { cfprApFirmwarePlatformPackFsmTable 1 }

CfprApFirmwarePlatformPackFsmEntry ::= SEQUENCE {
    cfprApFirmwarePlatformPackFsmInstanceId                          CfprApManagedObjectId,
    cfprApFirmwarePlatformPackFsmDn                                  CfprApManagedObjectDn,
    cfprApFirmwarePlatformPackFsmRn                                  SnmpAdminString,
    cfprApFirmwarePlatformPackFsmCompletionTime                      DateAndTime,
    cfprApFirmwarePlatformPackFsmCurrentFsm                          CfprApFirmwarePlatformPackFsmCurrentFsm,
    cfprApFirmwarePlatformPackFsmDescrData                           SnmpAdminString,
    cfprApFirmwarePlatformPackFsmFsmStatus                           CfprApFsmFsmStageStatus,
    cfprApFirmwarePlatformPackFsmProgress                            Gauge32,
    cfprApFirmwarePlatformPackFsmRmtErrCode                          Gauge32,
    cfprApFirmwarePlatformPackFsmRmtErrDescr                         SnmpAdminString,
    cfprApFirmwarePlatformPackFsmRmtRslt                             CfprApConditionRemoteInvRslt
}

cfprApFirmwarePlatformPackFsmInstanceId OBJECT-TYPE
    SYNTAX       CfprApManagedObjectId
    MAX-ACCESS   not-accessible
    STATUS       current
    DESCRIPTION
        "Instance identifier of the managed object."
    ::= { cfprApFirmwarePlatformPackFsmEntry 1 }

cfprApFirmwarePlatformPackFsmDn OBJECT-TYPE
    SYNTAX       CfprApManagedObjectDn
    MAX-ACCESS   read-only
    STATUS       current
    DESCRIPTION
        "Cisco Firepower firmware:PlatformPackFsm:dn managed
        object property"
    ::= { cfprApFirmwarePlatformPackFsmEntry 2 }

cfprApFirmwarePlatformPackFsmRn OBJECT-TYPE
    SYNTAX       SnmpAdminString
    MAX-ACCESS   read-only
    STATUS       current
    DESCRIPTION
        "Cisco Firepower firmware:PlatformPackFsm:rn managed
        object property"
    ::= { cfprApFirmwarePlatformPackFsmEntry 3 }

cfprApFirmwarePlatformPackFsmCompletionTime OBJECT-TYPE
    SYNTAX       DateAndTime
    MAX-ACCESS   read-only
    STATUS       current
    DESCRIPTION
        "Cisco Firepower firmware:PlatformPackFsm:completionTime
        managed object property"
    ::= { cfprApFirmwarePlatformPackFsmEntry 4 }

cfprApFirmwarePlatformPackFsmCurrentFsm OBJECT-TYPE
    SYNTAX       CfprApFirmwarePlatformPackFsmCurrentFsm
    MAX-ACCESS   read-only
    STATUS       current
    DESCRIPTION
        "Cisco Firepower firmware:PlatformPackFsm:currentFsm
        managed object property"
    ::= { cfprApFirmwarePlatformPackFsmEntry 5 }

cfprApFirmwarePlatformPackFsmDescrData OBJECT-TYPE
    SYNTAX       SnmpAdminString
    MAX-ACCESS   read-only
    STATUS       current
    DESCRIPTION
        "Cisco Firepower firmware:PlatformPackFsm:descr
        managed object property"
    ::= { cfprApFirmwarePlatformPackFsmEntry 6 }

cfprApFirmwarePlatformPackFsmFsmStatus OBJECT-TYPE
    SYNTAX       CfprApFsmFsmStageStatus
    MAX-ACCESS   read-only
    STATUS       current
    DESCRIPTION
        "Cisco Firepower firmware:PlatformPackFsm:fsmStatus
        managed object property"
    ::= { cfprApFirmwarePlatformPackFsmEntry 7 }

cfprApFirmwarePlatformPackFsmProgress OBJECT-TYPE
    SYNTAX       Gauge32
    MAX-ACCESS   read-only
    STATUS       current
    DESCRIPTION
        "Cisco Firepower firmware:PlatformPackFsm:progress
        managed object property"
    ::= { cfprApFirmwarePlatformPackFsmEntry 8 }

cfprApFirmwarePlatformPackFsmRmtErrCode OBJECT-TYPE
    SYNTAX       Gauge32
    MAX-ACCESS   read-only
    STATUS       current
    DESCRIPTION
        "Cisco Firepower firmware:PlatformPackFsm:rmtErrCode
        managed object property"
    ::= { cfprApFirmwarePlatformPackFsmEntry 9 }

cfprApFirmwarePlatformPackFsmRmtErrDescr OBJECT-TYPE
    SYNTAX       SnmpAdminString
    MAX-ACCESS   read-only
    STATUS       current
    DESCRIPTION
        "Cisco Firepower firmware:PlatformPackFsm:rmtErrDescr
        managed object property"
    ::= { cfprApFirmwarePlatformPackFsmEntry 10 }

cfprApFirmwarePlatformPackFsmRmtRslt OBJECT-TYPE
    SYNTAX       CfprApConditionRemoteInvRslt
    MAX-ACCESS   read-only
    STATUS       current
    DESCRIPTION
        "Cisco Firepower firmware:PlatformPackFsm:rmtRslt
        managed object property"
    ::= { cfprApFirmwarePlatformPackFsmEntry 11 }

cfprApFirmwarePlatformPackFsmStageTable OBJECT-TYPE
    SYNTAX           SEQUENCE OF CfprApFirmwarePlatformPackFsmStageEntry
    MAX-ACCESS       not-accessible
    STATUS           current
    DESCRIPTION
        "Cisco Firepower firmware:PlatformPackFsmStage
        managed object table"
    ::= { cfprApFirmwareObjects 50 }

cfprApFirmwarePlatformPackFsmStageEntry OBJECT-TYPE
    SYNTAX           CfprApFirmwarePlatformPackFsmStageEntry
    MAX-ACCESS       not-accessible
    STATUS           current
    DESCRIPTION
        "Entry for the cfprApFirmwarePlatformPackFsmStageTable table."
    INDEX { cfprApFirmwarePlatformPackFsmStageInstanceId }
    ::= { cfprApFirmwarePlatformPackFsmStageTable 1 }

CfprApFirmwarePlatformPackFsmStageEntry ::= SEQUENCE {
    cfprApFirmwarePlatformPackFsmStageInstanceId                     CfprApManagedObjectId,
    cfprApFirmwarePlatformPackFsmStageDn                             CfprApManagedObjectDn,
    cfprApFirmwarePlatformPackFsmStageRn                             SnmpAdminString,
    cfprApFirmwarePlatformPackFsmStageDescrData                      SnmpAdminString,
    cfprApFirmwarePlatformPackFsmStageLastUpdateTime                 DateAndTime,
    cfprApFirmwarePlatformPackFsmStageName                           CfprApFirmwarePlatformPackFsmStageName,
    cfprApFirmwarePlatformPackFsmStageOrder                          Gauge32,
    cfprApFirmwarePlatformPackFsmStageRetry                          Gauge32,
    cfprApFirmwarePlatformPackFsmStageStageStatus                    CfprApFsmFsmStageStatus
}

cfprApFirmwarePlatformPackFsmStageInstanceId OBJECT-TYPE
    SYNTAX       CfprApManagedObjectId
    MAX-ACCESS   not-accessible
    STATUS       current
    DESCRIPTION
        "Instance identifier of the managed object."
    ::= { cfprApFirmwarePlatformPackFsmStageEntry 1 }

cfprApFirmwarePlatformPackFsmStageDn OBJECT-TYPE
    SYNTAX       CfprApManagedObjectDn
    MAX-ACCESS   read-only
    STATUS       current
    DESCRIPTION
        "Cisco Firepower firmware:PlatformPackFsmStage:dn
        managed object property"
    ::= { cfprApFirmwarePlatformPackFsmStageEntry 2 }

cfprApFirmwarePlatformPackFsmStageRn OBJECT-TYPE
    SYNTAX       SnmpAdminString
    MAX-ACCESS   read-only
    STATUS       current
    DESCRIPTION
        "Cisco Firepower firmware:PlatformPackFsmStage:rn
        managed object property"
    ::= { cfprApFirmwarePlatformPackFsmStageEntry 3 }

cfprApFirmwarePlatformPackFsmStageDescrData OBJECT-TYPE
    SYNTAX       SnmpAdminString
    MAX-ACCESS   read-only
    STATUS       current
    DESCRIPTION
        "Cisco Firepower firmware:PlatformPackFsmStage:descr
        managed object property"
    ::= { cfprApFirmwarePlatformPackFsmStageEntry 4 }

cfprApFirmwarePlatformPackFsmStageLastUpdateTime OBJECT-TYPE
    SYNTAX       DateAndTime
    MAX-ACCESS   read-only
    STATUS       current
    DESCRIPTION
        "Cisco Firepower firmware:PlatformPackFsmStage:lastUpdateTime
        managed object property"
    ::= { cfprApFirmwarePlatformPackFsmStageEntry 5 }

cfprApFirmwarePlatformPackFsmStageName OBJECT-TYPE
    SYNTAX       CfprApFirmwarePlatformPackFsmStageName
    MAX-ACCESS   read-only
    STATUS       current
    DESCRIPTION
        "Cisco Firepower firmware:PlatformPackFsmStage:name
        managed object property"
    ::= { cfprApFirmwarePlatformPackFsmStageEntry 6 }

cfprApFirmwarePlatformPackFsmStageOrder OBJECT-TYPE
    SYNTAX       Gauge32
    MAX-ACCESS   read-only
    STATUS       current
    DESCRIPTION
        "Cisco Firepower firmware:PlatformPackFsmStage:order
        managed object property"
    ::= { cfprApFirmwarePlatformPackFsmStageEntry 7 }

cfprApFirmwarePlatformPackFsmStageRetry OBJECT-TYPE
    SYNTAX       Gauge32
    MAX-ACCESS   read-only
    STATUS       current
    DESCRIPTION
        "Cisco Firepower firmware:PlatformPackFsmStage:retry
        managed object property"
    ::= { cfprApFirmwarePlatformPackFsmStageEntry 8 }

cfprApFirmwarePlatformPackFsmStageStageStatus OBJECT-TYPE
    SYNTAX       CfprApFsmFsmStageStatus
    MAX-ACCESS   read-only
    STATUS       current
    DESCRIPTION
        "Cisco Firepower firmware:PlatformPackFsmStage:stageStatus
        managed object property"
    ::= { cfprApFirmwarePlatformPackFsmStageEntry 9 }

cfprApFirmwarePlatformPackFsmTaskTable OBJECT-TYPE
    SYNTAX           SEQUENCE OF CfprApFirmwarePlatformPackFsmTaskEntry
    MAX-ACCESS       not-accessible
    STATUS           current
    DESCRIPTION
        "Cisco Firepower firmware:PlatformPackFsmTask managed
        object table"
    ::= { cfprApFirmwareObjects 51 }

cfprApFirmwarePlatformPackFsmTaskEntry OBJECT-TYPE
    SYNTAX           CfprApFirmwarePlatformPackFsmTaskEntry
    MAX-ACCESS       not-accessible
    STATUS           current
    DESCRIPTION
        "Entry for the cfprApFirmwarePlatformPackFsmTaskTable table."
    INDEX { cfprApFirmwarePlatformPackFsmTaskInstanceId }
    ::= { cfprApFirmwarePlatformPackFsmTaskTable 1 }

CfprApFirmwarePlatformPackFsmTaskEntry ::= SEQUENCE {
    cfprApFirmwarePlatformPackFsmTaskInstanceId                      CfprApManagedObjectId,
    cfprApFirmwarePlatformPackFsmTaskDn                              CfprApManagedObjectDn,
    cfprApFirmwarePlatformPackFsmTaskRn                              SnmpAdminString,
    cfprApFirmwarePlatformPackFsmTaskCompletion                      CfprApFsmCompletion,
    cfprApFirmwarePlatformPackFsmTaskFlags                           CfprApFirmwarePlatformPackFsmTaskFlags,
    cfprApFirmwarePlatformPackFsmTaskItem                            CfprApFirmwarePlatformPackFsmTaskItem,
    cfprApFirmwarePlatformPackFsmTaskSeqId                           Gauge32
}

cfprApFirmwarePlatformPackFsmTaskInstanceId OBJECT-TYPE
    SYNTAX       CfprApManagedObjectId
    MAX-ACCESS   not-accessible
    STATUS       current
    DESCRIPTION
        "Instance identifier of the managed object."
    ::= { cfprApFirmwarePlatformPackFsmTaskEntry 1 }

cfprApFirmwarePlatformPackFsmTaskDn OBJECT-TYPE
    SYNTAX       CfprApManagedObjectDn
    MAX-ACCESS   read-only
    STATUS       current
    DESCRIPTION
        "Cisco Firepower firmware:PlatformPackFsmTask:dn
        managed object property"
    ::= { cfprApFirmwarePlatformPackFsmTaskEntry 2 }

cfprApFirmwarePlatformPackFsmTaskRn OBJECT-TYPE
    SYNTAX       SnmpAdminString
    MAX-ACCESS   read-only
    STATUS       current
    DESCRIPTION
        "Cisco Firepower firmware:PlatformPackFsmTask:rn
        managed object property"
    ::= { cfprApFirmwarePlatformPackFsmTaskEntry 3 }

cfprApFirmwarePlatformPackFsmTaskCompletion OBJECT-TYPE
    SYNTAX       CfprApFsmCompletion
    MAX-ACCESS   read-only
    STATUS       current
    DESCRIPTION
        "Cisco Firepower firmware:PlatformPackFsmTask:completion
        managed object property"
    ::= { cfprApFirmwarePlatformPackFsmTaskEntry 4 }

cfprApFirmwarePlatformPackFsmTaskFlags OBJECT-TYPE
    SYNTAX       CfprApFirmwarePlatformPackFsmTaskFlags
    MAX-ACCESS   read-only
    STATUS       current
    DESCRIPTION
        "Cisco Firepower firmware:PlatformPackFsmTask:flags
        managed object property"
    ::= { cfprApFirmwarePlatformPackFsmTaskEntry 5 }

cfprApFirmwarePlatformPackFsmTaskItem OBJECT-TYPE
    SYNTAX       CfprApFirmwarePlatformPackFsmTaskItem
    MAX-ACCESS   read-only
    STATUS       current
    DESCRIPTION
        "Cisco Firepower firmware:PlatformPackFsmTask:item
        managed object property"
    ::= { cfprApFirmwarePlatformPackFsmTaskEntry 6 }

cfprApFirmwarePlatformPackFsmTaskSeqId OBJECT-TYPE
    SYNTAX       Gauge32
    MAX-ACCESS   read-only
    STATUS       current
    DESCRIPTION
        "Cisco Firepower firmware:PlatformPackFsmTask:seqId
        managed object property"
    ::= { cfprApFirmwarePlatformPackFsmTaskEntry 7 }

cfprApFirmwareRackTable OBJECT-TYPE
    SYNTAX           SEQUENCE OF CfprApFirmwareRackEntry
    MAX-ACCESS       not-accessible
    STATUS           current
    DESCRIPTION
        "Cisco Firepower firmware:Rack managed object table"
    ::= { cfprApFirmwareObjects 52 }

cfprApFirmwareRackEntry OBJECT-TYPE
    SYNTAX           CfprApFirmwareRackEntry
    MAX-ACCESS       not-accessible
    STATUS           current
    DESCRIPTION
        "Entry for the cfprApFirmwareRackTable table."
    INDEX { cfprApFirmwareRackInstanceId }
    ::= { cfprApFirmwareRackTable 1 }

CfprApFirmwareRackEntry ::= SEQUENCE {
    cfprApFirmwareRackInstanceId                                     CfprApManagedObjectId,
    cfprApFirmwareRackDn                                             CfprApManagedObjectDn,
    cfprApFirmwareRackRn                                             SnmpAdminString,
    cfprApFirmwareRackOperVersion                                    SnmpAdminString
}

cfprApFirmwareRackInstanceId OBJECT-TYPE
    SYNTAX       CfprApManagedObjectId
    MAX-ACCESS   not-accessible
    STATUS       current
    DESCRIPTION
        "Instance identifier of the managed object."
    ::= { cfprApFirmwareRackEntry 1 }

cfprApFirmwareRackDn OBJECT-TYPE
    SYNTAX       CfprApManagedObjectDn
    MAX-ACCESS   read-only
    STATUS       current
    DESCRIPTION
        "Cisco Firepower firmware:Rack:dn managed object property"
    ::= { cfprApFirmwareRackEntry 2 }

cfprApFirmwareRackRn OBJECT-TYPE
    SYNTAX       SnmpAdminString
    MAX-ACCESS   read-only
    STATUS       current
    DESCRIPTION
        "Cisco Firepower firmware:Rack:rn managed object property"
    ::= { cfprApFirmwareRackEntry 3 }

cfprApFirmwareRackOperVersion OBJECT-TYPE
    SYNTAX       SnmpAdminString
    MAX-ACCESS   read-only
    STATUS       current
    DESCRIPTION
        "Cisco Firepower firmware:Rack:operVersion managed
        object property"
    ::= { cfprApFirmwareRackEntry 4 }

cfprApFirmwareRommonInfoTable OBJECT-TYPE
    SYNTAX           SEQUENCE OF CfprApFirmwareRommonInfoEntry
    MAX-ACCESS       not-accessible
    STATUS           current
    DESCRIPTION
        "Cisco Firepower firmware:RommonInfo managed object table"
    ::= { cfprApFirmwareObjects 53 }

cfprApFirmwareRommonInfoEntry OBJECT-TYPE
    SYNTAX           CfprApFirmwareRommonInfoEntry
    MAX-ACCESS       not-accessible
    STATUS           current
    DESCRIPTION
        "Entry for the cfprApFirmwareRommonInfoTable table."
    INDEX { cfprApFirmwareRommonInfoInstanceId }
    ::= { cfprApFirmwareRommonInfoTable 1 }

CfprApFirmwareRommonInfoEntry ::= SEQUENCE {
    cfprApFirmwareRommonInfoInstanceId                               CfprApManagedObjectId,
    cfprApFirmwareRommonInfoDn                                       CfprApManagedObjectDn,
    cfprApFirmwareRommonInfoRn                                       SnmpAdminString,
    cfprApFirmwareRommonInfoFirmwareStatus                           SnmpAdminString,
    cfprApFirmwareRommonInfoFirmwareVersion                          SnmpAdminString,
    cfprApFirmwareRommonInfoFpgaVersion                              SnmpAdminString,
    cfprApFirmwareRommonInfoLanSpiVersion                            SnmpAdminString,
    cfprApFirmwareRommonInfoPowerSequencerVersion                    SnmpAdminString,
    cfprApFirmwareRommonInfoRommonVersion                            SnmpAdminString
}

cfprApFirmwareRommonInfoInstanceId OBJECT-TYPE
    SYNTAX       CfprApManagedObjectId
    MAX-ACCESS   not-accessible
    STATUS       current
    DESCRIPTION
        "Instance identifier of the managed object."
    ::= { cfprApFirmwareRommonInfoEntry 1 }

cfprApFirmwareRommonInfoDn OBJECT-TYPE
    SYNTAX       CfprApManagedObjectDn
    MAX-ACCESS   read-only
    STATUS       current
    DESCRIPTION
        "Cisco Firepower firmware:RommonInfo:dn managed object property"
    ::= { cfprApFirmwareRommonInfoEntry 2 }

cfprApFirmwareRommonInfoRn OBJECT-TYPE
    SYNTAX       SnmpAdminString
    MAX-ACCESS   read-only
    STATUS       current
    DESCRIPTION
        "Cisco Firepower firmware:RommonInfo:rn managed object property"
    ::= { cfprApFirmwareRommonInfoEntry 3 }

cfprApFirmwareRommonInfoFirmwareStatus OBJECT-TYPE
    SYNTAX       SnmpAdminString
    MAX-ACCESS   read-only
    STATUS       current
    DESCRIPTION
        "Cisco Firepower firmware:RommonInfo:firmwareStatus
        managed object property"
    ::= { cfprApFirmwareRommonInfoEntry 4 }

cfprApFirmwareRommonInfoFirmwareVersion OBJECT-TYPE
    SYNTAX       SnmpAdminString
    MAX-ACCESS   read-only
    STATUS       current
    DESCRIPTION
        "Cisco Firepower firmware:RommonInfo:firmwareVersion
        managed object property"
    ::= { cfprApFirmwareRommonInfoEntry 5 }

cfprApFirmwareRommonInfoFpgaVersion OBJECT-TYPE
    SYNTAX       SnmpAdminString
    MAX-ACCESS   read-only
    STATUS       current
    DESCRIPTION
        "Cisco Firepower firmware:RommonInfo:fpgaVersion
        managed object property"
    ::= { cfprApFirmwareRommonInfoEntry 6 }

cfprApFirmwareRommonInfoLanSpiVersion OBJECT-TYPE
    SYNTAX       SnmpAdminString
    MAX-ACCESS   read-only
    STATUS       current
    DESCRIPTION
        "Cisco Firepower firmware:RommonInfo:lanSpiVersion
        managed object property"
    ::= { cfprApFirmwareRommonInfoEntry 7 }

cfprApFirmwareRommonInfoPowerSequencerVersion OBJECT-TYPE
    SYNTAX       SnmpAdminString
    MAX-ACCESS   read-only
    STATUS       current
    DESCRIPTION
        "Cisco Firepower firmware:RommonInfo:powerSequencerVersion
        managed object property"
    ::= { cfprApFirmwareRommonInfoEntry 8 }

cfprApFirmwareRommonInfoRommonVersion OBJECT-TYPE
    SYNTAX       SnmpAdminString
    MAX-ACCESS   read-only
    STATUS       current
    DESCRIPTION
        "Cisco Firepower firmware:RommonInfo:rommonVersion
        managed object property"
    ::= { cfprApFirmwareRommonInfoEntry 9 }

cfprApFirmwareRunningTable OBJECT-TYPE
    SYNTAX           SEQUENCE OF CfprApFirmwareRunningEntry
    MAX-ACCESS       not-accessible
    STATUS           current
    DESCRIPTION
        "Cisco Firepower firmware:Running managed object table"
    ::= { cfprApFirmwareObjects 54 }

cfprApFirmwareRunningEntry OBJECT-TYPE
    SYNTAX           CfprApFirmwareRunningEntry
    MAX-ACCESS       not-accessible
    STATUS           current
    DESCRIPTION
        "Entry for the cfprApFirmwareRunningTable table."
    INDEX { cfprApFirmwareRunningInstanceId }
    ::= { cfprApFirmwareRunningTable 1 }

CfprApFirmwareRunningEntry ::= SEQUENCE {
    cfprApFirmwareRunningInstanceId                                  CfprApManagedObjectId,
    cfprApFirmwareRunningDn                                          CfprApManagedObjectDn,
    cfprApFirmwareRunningRn                                          SnmpAdminString,
    cfprApFirmwareRunningDeployment                                  CfprApFirmwareRunningDeployment,
    cfprApFirmwareRunningInvTag                                      SnmpAdminString,
    cfprApFirmwareRunningPackageVersion                              SnmpAdminString,
    cfprApFirmwareRunningPlatformVersion                             SnmpAdminString,
    cfprApFirmwareRunningType                                        CfprApFirmwareType,
    cfprApFirmwareRunningVersion                                     SnmpAdminString
}

cfprApFirmwareRunningInstanceId OBJECT-TYPE
    SYNTAX       CfprApManagedObjectId
    MAX-ACCESS   not-accessible
    STATUS       current
    DESCRIPTION
        "Instance identifier of the managed object."
    ::= { cfprApFirmwareRunningEntry 1 }

cfprApFirmwareRunningDn OBJECT-TYPE
    SYNTAX       CfprApManagedObjectDn
    MAX-ACCESS   read-only
    STATUS       current
    DESCRIPTION
        "Cisco Firepower firmware:Running:dn managed object property"
    ::= { cfprApFirmwareRunningEntry 2 }

cfprApFirmwareRunningRn OBJECT-TYPE
    SYNTAX       SnmpAdminString
    MAX-ACCESS   read-only
    STATUS       current
    DESCRIPTION
        "Cisco Firepower firmware:Running:rn managed object property"
    ::= { cfprApFirmwareRunningEntry 3 }

cfprApFirmwareRunningDeployment OBJECT-TYPE
    SYNTAX       CfprApFirmwareRunningDeployment
    MAX-ACCESS   read-only
    STATUS       current
    DESCRIPTION
        "Cisco Firepower firmware:Running:deployment managed
        object property"
    ::= { cfprApFirmwareRunningEntry 4 }

cfprApFirmwareRunningInvTag OBJECT-TYPE
    SYNTAX       SnmpAdminString
    MAX-ACCESS   read-only
    STATUS       current
    DESCRIPTION
        "Cisco Firepower firmware:Running:invTag managed object property"
    ::= { cfprApFirmwareRunningEntry 5 }

cfprApFirmwareRunningPackageVersion OBJECT-TYPE
    SYNTAX       SnmpAdminString
    MAX-ACCESS   read-only
    STATUS       current
    DESCRIPTION
        "Cisco Firepower firmware:Running:packageVersion
        managed object property"
    ::= { cfprApFirmwareRunningEntry 6 }

cfprApFirmwareRunningPlatformVersion OBJECT-TYPE
    SYNTAX       SnmpAdminString
    MAX-ACCESS   read-only
    STATUS       current
    DESCRIPTION
        "Cisco Firepower firmware:Running:platformVersion
        managed object property"
    ::= { cfprApFirmwareRunningEntry 7 }

cfprApFirmwareRunningType OBJECT-TYPE
    SYNTAX       CfprApFirmwareType
    MAX-ACCESS   read-only
    STATUS       current
    DESCRIPTION
        "Cisco Firepower firmware:Running:type managed object property"
    ::= { cfprApFirmwareRunningEntry 8 }

cfprApFirmwareRunningVersion OBJECT-TYPE
    SYNTAX       SnmpAdminString
    MAX-ACCESS   read-only
    STATUS       current
    DESCRIPTION
        "Cisco Firepower firmware:Running:version managed object property"
    ::= { cfprApFirmwareRunningEntry 9 }

cfprApFirmwareSpecTable OBJECT-TYPE
    SYNTAX           SEQUENCE OF CfprApFirmwareSpecEntry
    MAX-ACCESS       not-accessible
    STATUS           current
    DESCRIPTION
        "Cisco Firepower firmware:Spec managed object table"
    ::= { cfprApFirmwareObjects 55 }

cfprApFirmwareSpecEntry OBJECT-TYPE
    SYNTAX           CfprApFirmwareSpecEntry
    MAX-ACCESS       not-accessible
    STATUS           current
    DESCRIPTION
        "Entry for the cfprApFirmwareSpecTable table."
    INDEX { cfprApFirmwareSpecInstanceId }
    ::= { cfprApFirmwareSpecTable 1 }

CfprApFirmwareSpecEntry ::= SEQUENCE {
    cfprApFirmwareSpecInstanceId                                     CfprApManagedObjectId,
    cfprApFirmwareSpecDn                                             CfprApManagedObjectDn,
    cfprApFirmwareSpecRn                                             SnmpAdminString,
    cfprApFirmwareSpecBundleVersion                                  SnmpAdminString,
    cfprApFirmwareSpecEthEFIVersion                                  SnmpAdminString,
    cfprApFirmwareSpecEthOptionRomVersion                            SnmpAdminString,
    cfprApFirmwareSpecFcFWVersion                                    SnmpAdminString,
    cfprApFirmwareSpecFcOptionRomVersion                             SnmpAdminString
}

cfprApFirmwareSpecInstanceId OBJECT-TYPE
    SYNTAX       CfprApManagedObjectId
    MAX-ACCESS   not-accessible
    STATUS       current
    DESCRIPTION
        "Instance identifier of the managed object."
    ::= { cfprApFirmwareSpecEntry 1 }

cfprApFirmwareSpecDn OBJECT-TYPE
    SYNTAX       CfprApManagedObjectDn
    MAX-ACCESS   read-only
    STATUS       current
    DESCRIPTION
        "Cisco Firepower firmware:Spec:dn managed object property"
    ::= { cfprApFirmwareSpecEntry 2 }

cfprApFirmwareSpecRn OBJECT-TYPE
    SYNTAX       SnmpAdminString
    MAX-ACCESS   read-only
    STATUS       current
    DESCRIPTION
        "Cisco Firepower firmware:Spec:rn managed object property"
    ::= { cfprApFirmwareSpecEntry 3 }

cfprApFirmwareSpecBundleVersion OBJECT-TYPE
    SYNTAX       SnmpAdminString
    MAX-ACCESS   read-only
    STATUS       current
    DESCRIPTION
        "Cisco Firepower firmware:Spec:bundleVersion managed
        object property"
    ::= { cfprApFirmwareSpecEntry 4 }

cfprApFirmwareSpecEthEFIVersion OBJECT-TYPE
    SYNTAX       SnmpAdminString
    MAX-ACCESS   read-only
    STATUS       current
    DESCRIPTION
        "Cisco Firepower firmware:Spec:ethEFIVersion managed
        object property"
    ::= { cfprApFirmwareSpecEntry 5 }

cfprApFirmwareSpecEthOptionRomVersion OBJECT-TYPE
    SYNTAX       SnmpAdminString
    MAX-ACCESS   read-only
    STATUS       current
    DESCRIPTION
        "Cisco Firepower firmware:Spec:ethOptionRomVersion
        managed object property"
    ::= { cfprApFirmwareSpecEntry 6 }

cfprApFirmwareSpecFcFWVersion OBJECT-TYPE
    SYNTAX       SnmpAdminString
    MAX-ACCESS   read-only
    STATUS       current
    DESCRIPTION
        "Cisco Firepower firmware:Spec:fcFWVersion managed
        object property"
    ::= { cfprApFirmwareSpecEntry 7 }

cfprApFirmwareSpecFcOptionRomVersion OBJECT-TYPE
    SYNTAX       SnmpAdminString
    MAX-ACCESS   read-only
    STATUS       current
    DESCRIPTION
        "Cisco Firepower firmware:Spec:fcOptionRomVersion
        managed object property"
    ::= { cfprApFirmwareSpecEntry 8 }

cfprApFirmwareStatusTable OBJECT-TYPE
    SYNTAX           SEQUENCE OF CfprApFirmwareStatusEntry
    MAX-ACCESS       not-accessible
    STATUS           current
    DESCRIPTION
        "Cisco Firepower firmware:Status managed object table"
    ::= { cfprApFirmwareObjects 56 }

cfprApFirmwareStatusEntry OBJECT-TYPE
    SYNTAX           CfprApFirmwareStatusEntry
    MAX-ACCESS       not-accessible
    STATUS           current
    DESCRIPTION
        "Entry for the cfprApFirmwareStatusTable table."
    INDEX { cfprApFirmwareStatusInstanceId }
    ::= { cfprApFirmwareStatusTable 1 }

CfprApFirmwareStatusEntry ::= SEQUENCE {
    cfprApFirmwareStatusInstanceId                                   CfprApManagedObjectId,
    cfprApFirmwareStatusDn                                           CfprApManagedObjectDn,
    cfprApFirmwareStatusRn                                           SnmpAdminString,
    cfprApFirmwareStatusCimcVersion                                  SnmpAdminString,
    cfprApFirmwareStatusFirmwareState                                CfprApFirmwareFirmwareState,
    cfprApFirmwareStatusOperState                                    CfprApFirmwareImageState,
    cfprApFirmwareStatusPackageVersion                               SnmpAdminString,
    cfprApFirmwareStatusPldVersion                                   SnmpAdminString
}

cfprApFirmwareStatusInstanceId OBJECT-TYPE
    SYNTAX       CfprApManagedObjectId
    MAX-ACCESS   not-accessible
    STATUS       current
    DESCRIPTION
        "Instance identifier of the managed object."
    ::= { cfprApFirmwareStatusEntry 1 }

cfprApFirmwareStatusDn OBJECT-TYPE
    SYNTAX       CfprApManagedObjectDn
    MAX-ACCESS   read-only
    STATUS       current
    DESCRIPTION
        "Cisco Firepower firmware:Status:dn managed object property"
    ::= { cfprApFirmwareStatusEntry 2 }

cfprApFirmwareStatusRn OBJECT-TYPE
    SYNTAX       SnmpAdminString
    MAX-ACCESS   read-only
    STATUS       current
    DESCRIPTION
        "Cisco Firepower firmware:Status:rn managed object property"
    ::= { cfprApFirmwareStatusEntry 3 }

cfprApFirmwareStatusCimcVersion OBJECT-TYPE
    SYNTAX       SnmpAdminString
    MAX-ACCESS   read-only
    STATUS       current
    DESCRIPTION
        "Cisco Firepower firmware:Status:cimcVersion managed
        object property"
    ::= { cfprApFirmwareStatusEntry 4 }

cfprApFirmwareStatusFirmwareState OBJECT-TYPE
    SYNTAX       CfprApFirmwareFirmwareState
    MAX-ACCESS   read-only
    STATUS       current
    DESCRIPTION
        "Cisco Firepower firmware:Status:firmwareState
        managed object property"
    ::= { cfprApFirmwareStatusEntry 5 }

cfprApFirmwareStatusOperState OBJECT-TYPE
    SYNTAX       CfprApFirmwareImageState
    MAX-ACCESS   read-only
    STATUS       current
    DESCRIPTION
        "Cisco Firepower firmware:Status:operState managed
        object property"
    ::= { cfprApFirmwareStatusEntry 6 }

cfprApFirmwareStatusPackageVersion OBJECT-TYPE
    SYNTAX       SnmpAdminString
    MAX-ACCESS   read-only
    STATUS       current
    DESCRIPTION
        "Cisco Firepower firmware:Status:packageVersion
        managed object property"
    ::= { cfprApFirmwareStatusEntry 7 }

cfprApFirmwareStatusPldVersion OBJECT-TYPE
    SYNTAX       SnmpAdminString
    MAX-ACCESS   read-only
    STATUS       current
    DESCRIPTION
        "Cisco Firepower firmware:Status:pldVersion managed
        object property"
    ::= { cfprApFirmwareStatusEntry 8 }

cfprApFirmwareSupFirmwareTable OBJECT-TYPE
    SYNTAX           SEQUENCE OF CfprApFirmwareSupFirmwareEntry
    MAX-ACCESS       not-accessible
    STATUS           current
    DESCRIPTION
        "Cisco Firepower firmware:SupFirmware managed object table"
    ::= { cfprApFirmwareObjects 57 }

cfprApFirmwareSupFirmwareEntry OBJECT-TYPE
    SYNTAX           CfprApFirmwareSupFirmwareEntry
    MAX-ACCESS       not-accessible
    STATUS           current
    DESCRIPTION
        "Entry for the cfprApFirmwareSupFirmwareTable table."
    INDEX { cfprApFirmwareSupFirmwareInstanceId }
    ::= { cfprApFirmwareSupFirmwareTable 1 }

CfprApFirmwareSupFirmwareEntry ::= SEQUENCE {
    cfprApFirmwareSupFirmwareInstanceId                              CfprApManagedObjectId,
    cfprApFirmwareSupFirmwareDn                                      CfprApManagedObjectDn,
    cfprApFirmwareSupFirmwareRn                                      SnmpAdminString,
    cfprApFirmwareSupFirmwareFsmDescr                                SnmpAdminString,
    cfprApFirmwareSupFirmwareFsmFlags                                SnmpAdminString,
    cfprApFirmwareSupFirmwareFsmPrev                                 SnmpAdminString,
    cfprApFirmwareSupFirmwareFsmProgr                                Gauge32,
    cfprApFirmwareSupFirmwareFsmRmtInvErrCode                        Gauge32,
    cfprApFirmwareSupFirmwareFsmRmtInvErrDescr                       SnmpAdminString,
    cfprApFirmwareSupFirmwareFsmRmtInvRslt                           CfprApConditionRemoteInvRslt,
    cfprApFirmwareSupFirmwareFsmStageDescr                           SnmpAdminString,
    cfprApFirmwareSupFirmwareFsmStamp                                DateAndTime,
    cfprApFirmwareSupFirmwareFsmStatus                               SnmpAdminString,
    cfprApFirmwareSupFirmwareFsmTry                                  Gauge32,
    cfprApFirmwareSupFirmwareOperState                               CfprApFirmwareFwUpgradeState,
    cfprApFirmwareSupFirmwarePackVersion                             SnmpAdminString,
    cfprApFirmwareSupFirmwareState                                   CfprApFirmwareFwState,
    cfprApFirmwareSupFirmwareUpgradeStatus                           SnmpAdminString
}

cfprApFirmwareSupFirmwareInstanceId OBJECT-TYPE
    SYNTAX       CfprApManagedObjectId
    MAX-ACCESS   not-accessible
    STATUS       current
    DESCRIPTION
        "Instance identifier of the managed object."
    ::= { cfprApFirmwareSupFirmwareEntry 1 }

cfprApFirmwareSupFirmwareDn OBJECT-TYPE
    SYNTAX       CfprApManagedObjectDn
    MAX-ACCESS   read-only
    STATUS       current
    DESCRIPTION
        "Cisco Firepower firmware:SupFirmware:dn managed object property"
    ::= { cfprApFirmwareSupFirmwareEntry 2 }

cfprApFirmwareSupFirmwareRn OBJECT-TYPE
    SYNTAX       SnmpAdminString
    MAX-ACCESS   read-only
    STATUS       current
    DESCRIPTION
        "Cisco Firepower firmware:SupFirmware:rn managed object property"
    ::= { cfprApFirmwareSupFirmwareEntry 3 }

cfprApFirmwareSupFirmwareFsmDescr OBJECT-TYPE
    SYNTAX       SnmpAdminString
    MAX-ACCESS   read-only
    STATUS       current
    DESCRIPTION
        "Cisco Firepower firmware:SupFirmware:fsmDescr
        managed object property"
    ::= { cfprApFirmwareSupFirmwareEntry 4 }

cfprApFirmwareSupFirmwareFsmFlags OBJECT-TYPE
    SYNTAX       SnmpAdminString
    MAX-ACCESS   read-only
    STATUS       current
    DESCRIPTION
        "Cisco Firepower firmware:SupFirmware:fsmFlags
        managed object property"
    ::= { cfprApFirmwareSupFirmwareEntry 5 }

cfprApFirmwareSupFirmwareFsmPrev OBJECT-TYPE
    SYNTAX       SnmpAdminString
    MAX-ACCESS   read-only
    STATUS       current
    DESCRIPTION
        "Cisco Firepower firmware:SupFirmware:fsmPrev managed
        object property"
    ::= { cfprApFirmwareSupFirmwareEntry 6 }

cfprApFirmwareSupFirmwareFsmProgr OBJECT-TYPE
    SYNTAX       Gauge32
    MAX-ACCESS   read-only
    STATUS       current
    DESCRIPTION
        "Cisco Firepower firmware:SupFirmware:fsmProgr
        managed object property"
    ::= { cfprApFirmwareSupFirmwareEntry 7 }

cfprApFirmwareSupFirmwareFsmRmtInvErrCode OBJECT-TYPE
    SYNTAX       Gauge32
    MAX-ACCESS   read-only
    STATUS       current
    DESCRIPTION
        "Cisco Firepower firmware:SupFirmware:fsmRmtInvErrCode
        managed object property"
    ::= { cfprApFirmwareSupFirmwareEntry 8 }

cfprApFirmwareSupFirmwareFsmRmtInvErrDescr OBJECT-TYPE
    SYNTAX       SnmpAdminString
    MAX-ACCESS   read-only
    STATUS       current
    DESCRIPTION
        "Cisco Firepower firmware:SupFirmware:fsmRmtInvErrDescr
        managed object property"
    ::= { cfprApFirmwareSupFirmwareEntry 9 }

cfprApFirmwareSupFirmwareFsmRmtInvRslt OBJECT-TYPE
    SYNTAX       CfprApConditionRemoteInvRslt
    MAX-ACCESS   read-only
    STATUS       current
    DESCRIPTION
        "Cisco Firepower firmware:SupFirmware:fsmRmtInvRslt
        managed object property"
    ::= { cfprApFirmwareSupFirmwareEntry 10 }

cfprApFirmwareSupFirmwareFsmStageDescr OBJECT-TYPE
    SYNTAX       SnmpAdminString
    MAX-ACCESS   read-only
    STATUS       current
    DESCRIPTION
        "Cisco Firepower firmware:SupFirmware:fsmStageDescr
        managed object property"
    ::= { cfprApFirmwareSupFirmwareEntry 11 }

cfprApFirmwareSupFirmwareFsmStamp OBJECT-TYPE
    SYNTAX       DateAndTime
    MAX-ACCESS   read-only
    STATUS       current
    DESCRIPTION
        "Cisco Firepower firmware:SupFirmware:fsmStamp
        managed object property"
    ::= { cfprApFirmwareSupFirmwareEntry 12 }

cfprApFirmwareSupFirmwareFsmStatus OBJECT-TYPE
    SYNTAX       SnmpAdminString
    MAX-ACCESS   read-only
    STATUS       current
    DESCRIPTION
        "Cisco Firepower firmware:SupFirmware:fsmStatus
        managed object property"
    ::= { cfprApFirmwareSupFirmwareEntry 13 }

cfprApFirmwareSupFirmwareFsmTry OBJECT-TYPE
    SYNTAX       Gauge32
    MAX-ACCESS   read-only
    STATUS       current
    DESCRIPTION
        "Cisco Firepower firmware:SupFirmware:fsmTry managed
        object property"
    ::= { cfprApFirmwareSupFirmwareEntry 14 }

cfprApFirmwareSupFirmwareOperState OBJECT-TYPE
    SYNTAX       CfprApFirmwareFwUpgradeState
    MAX-ACCESS   read-only
    STATUS       current
    DESCRIPTION
        "Cisco Firepower firmware:SupFirmware:operState
        managed object property"
    ::= { cfprApFirmwareSupFirmwareEntry 15 }

cfprApFirmwareSupFirmwarePackVersion OBJECT-TYPE
    SYNTAX       SnmpAdminString
    MAX-ACCESS   read-only
    STATUS       current
    DESCRIPTION
        "Cisco Firepower firmware:SupFirmware:packVersion
        managed object property"
    ::= { cfprApFirmwareSupFirmwareEntry 16 }

cfprApFirmwareSupFirmwareState OBJECT-TYPE
    SYNTAX       CfprApFirmwareFwState
    MAX-ACCESS   read-only
    STATUS       current
    DESCRIPTION
        "Cisco Firepower firmware:SupFirmware:state managed
        object property"
    ::= { cfprApFirmwareSupFirmwareEntry 17 }

cfprApFirmwareSupFirmwareUpgradeStatus OBJECT-TYPE
    SYNTAX       SnmpAdminString
    MAX-ACCESS   read-only
    STATUS       current
    DESCRIPTION
        "Cisco Firepower firmware:SupFirmware:upgradeStatus
        managed object property"
    ::= { cfprApFirmwareSupFirmwareEntry 18 }

cfprApFirmwareSupFirmwareFsmTable OBJECT-TYPE
    SYNTAX           SEQUENCE OF CfprApFirmwareSupFirmwareFsmEntry
    MAX-ACCESS       not-accessible
    STATUS           current
    DESCRIPTION
        "Cisco Firepower firmware:SupFirmwareFsm managed object table"
    ::= { cfprApFirmwareObjects 58 }

cfprApFirmwareSupFirmwareFsmEntry OBJECT-TYPE
    SYNTAX           CfprApFirmwareSupFirmwareFsmEntry
    MAX-ACCESS       not-accessible
    STATUS           current
    DESCRIPTION
        "Entry for the cfprApFirmwareSupFirmwareFsmTable table."
    INDEX { cfprApFirmwareSupFirmwareFsmInstanceId }
    ::= { cfprApFirmwareSupFirmwareFsmTable 1 }

CfprApFirmwareSupFirmwareFsmEntry ::= SEQUENCE {
    cfprApFirmwareSupFirmwareFsmInstanceId                           CfprApManagedObjectId,
    cfprApFirmwareSupFirmwareFsmDn                                   CfprApManagedObjectDn,
    cfprApFirmwareSupFirmwareFsmRn                                   SnmpAdminString,
    cfprApFirmwareSupFirmwareFsmCompletionTime                       DateAndTime,
    cfprApFirmwareSupFirmwareFsmCurrentFsm                           CfprApFirmwareSupFirmwareFsmCurrentFsm,
    cfprApFirmwareSupFirmwareFsmDescrData                            SnmpAdminString,
    cfprApFirmwareSupFirmwareFsmFsmStatus                            CfprApFsmFsmStageStatus,
    cfprApFirmwareSupFirmwareFsmProgress                             Gauge32,
    cfprApFirmwareSupFirmwareFsmRmtErrCode                           Gauge32,
    cfprApFirmwareSupFirmwareFsmRmtErrDescr                          SnmpAdminString,
    cfprApFirmwareSupFirmwareFsmRmtRslt                              CfprApConditionRemoteInvRslt
}

cfprApFirmwareSupFirmwareFsmInstanceId OBJECT-TYPE
    SYNTAX       CfprApManagedObjectId
    MAX-ACCESS   not-accessible
    STATUS       current
    DESCRIPTION
        "Instance identifier of the managed object."
    ::= { cfprApFirmwareSupFirmwareFsmEntry 1 }

cfprApFirmwareSupFirmwareFsmDn OBJECT-TYPE
    SYNTAX       CfprApManagedObjectDn
    MAX-ACCESS   read-only
    STATUS       current
    DESCRIPTION
        "Cisco Firepower firmware:SupFirmwareFsm:dn managed
        object property"
    ::= { cfprApFirmwareSupFirmwareFsmEntry 2 }

cfprApFirmwareSupFirmwareFsmRn OBJECT-TYPE
    SYNTAX       SnmpAdminString
    MAX-ACCESS   read-only
    STATUS       current
    DESCRIPTION
        "Cisco Firepower firmware:SupFirmwareFsm:rn managed
        object property"
    ::= { cfprApFirmwareSupFirmwareFsmEntry 3 }

cfprApFirmwareSupFirmwareFsmCompletionTime OBJECT-TYPE
    SYNTAX       DateAndTime
    MAX-ACCESS   read-only
    STATUS       current
    DESCRIPTION
        "Cisco Firepower firmware:SupFirmwareFsm:completionTime
        managed object property"
    ::= { cfprApFirmwareSupFirmwareFsmEntry 4 }

cfprApFirmwareSupFirmwareFsmCurrentFsm OBJECT-TYPE
    SYNTAX       CfprApFirmwareSupFirmwareFsmCurrentFsm
    MAX-ACCESS   read-only
    STATUS       current
    DESCRIPTION
        "Cisco Firepower firmware:SupFirmwareFsm:currentFsm
        managed object property"
    ::= { cfprApFirmwareSupFirmwareFsmEntry 5 }

cfprApFirmwareSupFirmwareFsmDescrData OBJECT-TYPE
    SYNTAX       SnmpAdminString
    MAX-ACCESS   read-only
    STATUS       current
    DESCRIPTION
        "Cisco Firepower firmware:SupFirmwareFsm:descr
        managed object property"
    ::= { cfprApFirmwareSupFirmwareFsmEntry 6 }

cfprApFirmwareSupFirmwareFsmFsmStatus OBJECT-TYPE
    SYNTAX       CfprApFsmFsmStageStatus
    MAX-ACCESS   read-only
    STATUS       current
    DESCRIPTION
        "Cisco Firepower firmware:SupFirmwareFsm:fsmStatus
        managed object property"
    ::= { cfprApFirmwareSupFirmwareFsmEntry 7 }

cfprApFirmwareSupFirmwareFsmProgress OBJECT-TYPE
    SYNTAX       Gauge32
    MAX-ACCESS   read-only
    STATUS       current
    DESCRIPTION
        "Cisco Firepower firmware:SupFirmwareFsm:progress
        managed object property"
    ::= { cfprApFirmwareSupFirmwareFsmEntry 8 }

cfprApFirmwareSupFirmwareFsmRmtErrCode OBJECT-TYPE
    SYNTAX       Gauge32
    MAX-ACCESS   read-only
    STATUS       current
    DESCRIPTION
        "Cisco Firepower firmware:SupFirmwareFsm:rmtErrCode
        managed object property"
    ::= { cfprApFirmwareSupFirmwareFsmEntry 9 }

cfprApFirmwareSupFirmwareFsmRmtErrDescr OBJECT-TYPE
    SYNTAX       SnmpAdminString
    MAX-ACCESS   read-only
    STATUS       current
    DESCRIPTION
        "Cisco Firepower firmware:SupFirmwareFsm:rmtErrDescr
        managed object property"
    ::= { cfprApFirmwareSupFirmwareFsmEntry 10 }

cfprApFirmwareSupFirmwareFsmRmtRslt OBJECT-TYPE
    SYNTAX       CfprApConditionRemoteInvRslt
    MAX-ACCESS   read-only
    STATUS       current
    DESCRIPTION
        "Cisco Firepower firmware:SupFirmwareFsm:rmtRslt
        managed object property"
    ::= { cfprApFirmwareSupFirmwareFsmEntry 11 }

cfprApFirmwareSupFirmwareFsmStageTable OBJECT-TYPE
    SYNTAX           SEQUENCE OF CfprApFirmwareSupFirmwareFsmStageEntry
    MAX-ACCESS       not-accessible
    STATUS           current
    DESCRIPTION
        "Cisco Firepower firmware:SupFirmwareFsmStage managed
        object table"
    ::= { cfprApFirmwareObjects 59 }

cfprApFirmwareSupFirmwareFsmStageEntry OBJECT-TYPE
    SYNTAX           CfprApFirmwareSupFirmwareFsmStageEntry
    MAX-ACCESS       not-accessible
    STATUS           current
    DESCRIPTION
        "Entry for the cfprApFirmwareSupFirmwareFsmStageTable table."
    INDEX { cfprApFirmwareSupFirmwareFsmStageInstanceId }
    ::= { cfprApFirmwareSupFirmwareFsmStageTable 1 }

CfprApFirmwareSupFirmwareFsmStageEntry ::= SEQUENCE {
    cfprApFirmwareSupFirmwareFsmStageInstanceId                      CfprApManagedObjectId,
    cfprApFirmwareSupFirmwareFsmStageDn                              CfprApManagedObjectDn,
    cfprApFirmwareSupFirmwareFsmStageRn                              SnmpAdminString,
    cfprApFirmwareSupFirmwareFsmStageDescrData                       SnmpAdminString,
    cfprApFirmwareSupFirmwareFsmStageLastUpdateTime                  DateAndTime,
    cfprApFirmwareSupFirmwareFsmStageName                            CfprApFirmwareSupFirmwareFsmStageName,
    cfprApFirmwareSupFirmwareFsmStageOrder                           Gauge32,
    cfprApFirmwareSupFirmwareFsmStageRetry                           Gauge32,
    cfprApFirmwareSupFirmwareFsmStageStageStatus                     CfprApFsmFsmStageStatus
}

cfprApFirmwareSupFirmwareFsmStageInstanceId OBJECT-TYPE
    SYNTAX       CfprApManagedObjectId
    MAX-ACCESS   not-accessible
    STATUS       current
    DESCRIPTION
        "Instance identifier of the managed object."
    ::= { cfprApFirmwareSupFirmwareFsmStageEntry 1 }

cfprApFirmwareSupFirmwareFsmStageDn OBJECT-TYPE
    SYNTAX       CfprApManagedObjectDn
    MAX-ACCESS   read-only
    STATUS       current
    DESCRIPTION
        "Cisco Firepower firmware:SupFirmwareFsmStage:dn
        managed object property"
    ::= { cfprApFirmwareSupFirmwareFsmStageEntry 2 }

cfprApFirmwareSupFirmwareFsmStageRn OBJECT-TYPE
    SYNTAX       SnmpAdminString
    MAX-ACCESS   read-only
    STATUS       current
    DESCRIPTION
        "Cisco Firepower firmware:SupFirmwareFsmStage:rn
        managed object property"
    ::= { cfprApFirmwareSupFirmwareFsmStageEntry 3 }

cfprApFirmwareSupFirmwareFsmStageDescrData OBJECT-TYPE
    SYNTAX       SnmpAdminString
    MAX-ACCESS   read-only
    STATUS       current
    DESCRIPTION
        "Cisco Firepower firmware:SupFirmwareFsmStage:descr
        managed object property"
    ::= { cfprApFirmwareSupFirmwareFsmStageEntry 4 }

cfprApFirmwareSupFirmwareFsmStageLastUpdateTime OBJECT-TYPE
    SYNTAX       DateAndTime
    MAX-ACCESS   read-only
    STATUS       current
    DESCRIPTION
        "Cisco Firepower firmware:SupFirmwareFsmStage:lastUpdateTime
        managed object property"
    ::= { cfprApFirmwareSupFirmwareFsmStageEntry 5 }

cfprApFirmwareSupFirmwareFsmStageName OBJECT-TYPE
    SYNTAX       CfprApFirmwareSupFirmwareFsmStageName
    MAX-ACCESS   read-only
    STATUS       current
    DESCRIPTION
        "Cisco Firepower firmware:SupFirmwareFsmStage:name
        managed object property"
    ::= { cfprApFirmwareSupFirmwareFsmStageEntry 6 }

cfprApFirmwareSupFirmwareFsmStageOrder OBJECT-TYPE
    SYNTAX       Gauge32
    MAX-ACCESS   read-only
    STATUS       current
    DESCRIPTION
        "Cisco Firepower firmware:SupFirmwareFsmStage:order
        managed object property"
    ::= { cfprApFirmwareSupFirmwareFsmStageEntry 7 }

cfprApFirmwareSupFirmwareFsmStageRetry OBJECT-TYPE
    SYNTAX       Gauge32
    MAX-ACCESS   read-only
    STATUS       current
    DESCRIPTION
        "Cisco Firepower firmware:SupFirmwareFsmStage:retry
        managed object property"
    ::= { cfprApFirmwareSupFirmwareFsmStageEntry 8 }

cfprApFirmwareSupFirmwareFsmStageStageStatus OBJECT-TYPE
    SYNTAX       CfprApFsmFsmStageStatus
    MAX-ACCESS   read-only
    STATUS       current
    DESCRIPTION
        "Cisco Firepower firmware:SupFirmwareFsmStage:stageStatus
        managed object property"
    ::= { cfprApFirmwareSupFirmwareFsmStageEntry 9 }

cfprApFirmwareSupFirmwareFsmTaskTable OBJECT-TYPE
    SYNTAX           SEQUENCE OF CfprApFirmwareSupFirmwareFsmTaskEntry
    MAX-ACCESS       not-accessible
    STATUS           current
    DESCRIPTION
        "Cisco Firepower firmware:SupFirmwareFsmTask managed object table"
    ::= { cfprApFirmwareObjects 60 }

cfprApFirmwareSupFirmwareFsmTaskEntry OBJECT-TYPE
    SYNTAX           CfprApFirmwareSupFirmwareFsmTaskEntry
    MAX-ACCESS       not-accessible
    STATUS           current
    DESCRIPTION
        "Entry for the cfprApFirmwareSupFirmwareFsmTaskTable table."
    INDEX { cfprApFirmwareSupFirmwareFsmTaskInstanceId }
    ::= { cfprApFirmwareSupFirmwareFsmTaskTable 1 }

CfprApFirmwareSupFirmwareFsmTaskEntry ::= SEQUENCE {
    cfprApFirmwareSupFirmwareFsmTaskInstanceId                       CfprApManagedObjectId,
    cfprApFirmwareSupFirmwareFsmTaskDn                               CfprApManagedObjectDn,
    cfprApFirmwareSupFirmwareFsmTaskRn                               SnmpAdminString,
    cfprApFirmwareSupFirmwareFsmTaskCompletion                       CfprApFsmCompletion,
    cfprApFirmwareSupFirmwareFsmTaskFlags                            CfprApFirmwareSupFirmwareFsmTaskFlags,
    cfprApFirmwareSupFirmwareFsmTaskItem                             CfprApFirmwareSupFirmwareFsmTaskItem,
    cfprApFirmwareSupFirmwareFsmTaskSeqId                            Gauge32
}

cfprApFirmwareSupFirmwareFsmTaskInstanceId OBJECT-TYPE
    SYNTAX       CfprApManagedObjectId
    MAX-ACCESS   not-accessible
    STATUS       current
    DESCRIPTION
        "Instance identifier of the managed object."
    ::= { cfprApFirmwareSupFirmwareFsmTaskEntry 1 }

cfprApFirmwareSupFirmwareFsmTaskDn OBJECT-TYPE
    SYNTAX       CfprApManagedObjectDn
    MAX-ACCESS   read-only
    STATUS       current
    DESCRIPTION
        "Cisco Firepower firmware:SupFirmwareFsmTask:dn
        managed object property"
    ::= { cfprApFirmwareSupFirmwareFsmTaskEntry 2 }

cfprApFirmwareSupFirmwareFsmTaskRn OBJECT-TYPE
    SYNTAX       SnmpAdminString
    MAX-ACCESS   read-only
    STATUS       current
    DESCRIPTION
        "Cisco Firepower firmware:SupFirmwareFsmTask:rn
        managed object property"
    ::= { cfprApFirmwareSupFirmwareFsmTaskEntry 3 }

cfprApFirmwareSupFirmwareFsmTaskCompletion OBJECT-TYPE
    SYNTAX       CfprApFsmCompletion
    MAX-ACCESS   read-only
    STATUS       current
    DESCRIPTION
        "Cisco Firepower firmware:SupFirmwareFsmTask:completion
        managed object property"
    ::= { cfprApFirmwareSupFirmwareFsmTaskEntry 4 }

cfprApFirmwareSupFirmwareFsmTaskFlags OBJECT-TYPE
    SYNTAX       CfprApFirmwareSupFirmwareFsmTaskFlags
    MAX-ACCESS   read-only
    STATUS       current
    DESCRIPTION
        "Cisco Firepower firmware:SupFirmwareFsmTask:flags
        managed object property"
    ::= { cfprApFirmwareSupFirmwareFsmTaskEntry 5 }

cfprApFirmwareSupFirmwareFsmTaskItem OBJECT-TYPE
    SYNTAX       CfprApFirmwareSupFirmwareFsmTaskItem
    MAX-ACCESS   read-only
    STATUS       current
    DESCRIPTION
        "Cisco Firepower firmware:SupFirmwareFsmTask:item
        managed object property"
    ::= { cfprApFirmwareSupFirmwareFsmTaskEntry 6 }

cfprApFirmwareSupFirmwareFsmTaskSeqId OBJECT-TYPE
    SYNTAX       Gauge32
    MAX-ACCESS   read-only
    STATUS       current
    DESCRIPTION
        "Cisco Firepower firmware:SupFirmwareFsmTask:seqId
        managed object property"
    ::= { cfprApFirmwareSupFirmwareFsmTaskEntry 7 }

cfprApFirmwareSystemTable OBJECT-TYPE
    SYNTAX           SEQUENCE OF CfprApFirmwareSystemEntry
    MAX-ACCESS       not-accessible
    STATUS           current
    DESCRIPTION
        "Cisco Firepower firmware:System managed object table"
    ::= { cfprApFirmwareObjects 61 }

cfprApFirmwareSystemEntry OBJECT-TYPE
    SYNTAX           CfprApFirmwareSystemEntry
    MAX-ACCESS       not-accessible
    STATUS           current
    DESCRIPTION
        "Entry for the cfprApFirmwareSystemTable table."
    INDEX { cfprApFirmwareSystemInstanceId }
    ::= { cfprApFirmwareSystemTable 1 }

CfprApFirmwareSystemEntry ::= SEQUENCE {
    cfprApFirmwareSystemInstanceId                                   CfprApManagedObjectId,
    cfprApFirmwareSystemDn                                           CfprApManagedObjectDn,
    cfprApFirmwareSystemRn                                           SnmpAdminString,
    cfprApFirmwareSystemFsmDescr                                     SnmpAdminString,
    cfprApFirmwareSystemFsmFlags                                     SnmpAdminString,
    cfprApFirmwareSystemFsmPrev                                      SnmpAdminString,
    cfprApFirmwareSystemFsmProgr                                     Gauge32,
    cfprApFirmwareSystemFsmRmtInvErrCode                             Gauge32,
    cfprApFirmwareSystemFsmRmtInvErrDescr                            SnmpAdminString,
    cfprApFirmwareSystemFsmRmtInvRslt                                CfprApConditionRemoteInvRslt,
    cfprApFirmwareSystemFsmStageDescr                                SnmpAdminString,
    cfprApFirmwareSystemFsmStamp                                     DateAndTime,
    cfprApFirmwareSystemFsmStatus                                    SnmpAdminString,
    cfprApFirmwareSystemFsmTry                                       Gauge32,
    cfprApFirmwareSystemFwUpgradeBitmap                              Gauge32,
    cfprApFirmwareSystemFwUpgradeStatus                              SnmpAdminString,
    cfprApFirmwareSystemOperState                                    CfprApFirmwareInstallState,
    cfprApFirmwareSystemPackVersion                                  SnmpAdminString,
    cfprApFirmwareSystemScheduledInstallTime                         DateAndTime,
    cfprApFirmwareSystemState                                        CfprApFirmwareFwState,
    cfprApFirmwareSystemUpgradeState                                 CfprApFirmwareUpgradeState,
    cfprApFirmwareSystemUpgradeStatus                                SnmpAdminString
}

cfprApFirmwareSystemInstanceId OBJECT-TYPE
    SYNTAX       CfprApManagedObjectId
    MAX-ACCESS   not-accessible
    STATUS       current
    DESCRIPTION
        "Instance identifier of the managed object."
    ::= { cfprApFirmwareSystemEntry 1 }

cfprApFirmwareSystemDn OBJECT-TYPE
    SYNTAX       CfprApManagedObjectDn
    MAX-ACCESS   read-only
    STATUS       current
    DESCRIPTION
        "Cisco Firepower firmware:System:dn managed object property"
    ::= { cfprApFirmwareSystemEntry 2 }

cfprApFirmwareSystemRn OBJECT-TYPE
    SYNTAX       SnmpAdminString
    MAX-ACCESS   read-only
    STATUS       current
    DESCRIPTION
        "Cisco Firepower firmware:System:rn managed object property"
    ::= { cfprApFirmwareSystemEntry 3 }

cfprApFirmwareSystemFsmDescr OBJECT-TYPE
    SYNTAX       SnmpAdminString
    MAX-ACCESS   read-only
    STATUS       current
    DESCRIPTION
        "Cisco Firepower firmware:System:fsmDescr managed object property"
    ::= { cfprApFirmwareSystemEntry 4 }

cfprApFirmwareSystemFsmFlags OBJECT-TYPE
    SYNTAX       SnmpAdminString
    MAX-ACCESS   read-only
    STATUS       current
    DESCRIPTION
        "Cisco Firepower firmware:System:fsmFlags managed object property"
    ::= { cfprApFirmwareSystemEntry 5 }

cfprApFirmwareSystemFsmPrev OBJECT-TYPE
    SYNTAX       SnmpAdminString
    MAX-ACCESS   read-only
    STATUS       current
    DESCRIPTION
        "Cisco Firepower firmware:System:fsmPrev managed object property"
    ::= { cfprApFirmwareSystemEntry 6 }

cfprApFirmwareSystemFsmProgr OBJECT-TYPE
    SYNTAX       Gauge32
    MAX-ACCESS   read-only
    STATUS       current
    DESCRIPTION
        "Cisco Firepower firmware:System:fsmProgr managed object property"
    ::= { cfprApFirmwareSystemEntry 7 }

cfprApFirmwareSystemFsmRmtInvErrCode OBJECT-TYPE
    SYNTAX       Gauge32
    MAX-ACCESS   read-only
    STATUS       current
    DESCRIPTION
        "Cisco Firepower firmware:System:fsmRmtInvErrCode
        managed object property"
    ::= { cfprApFirmwareSystemEntry 8 }

cfprApFirmwareSystemFsmRmtInvErrDescr OBJECT-TYPE
    SYNTAX       SnmpAdminString
    MAX-ACCESS   read-only
    STATUS       current
    DESCRIPTION
        "Cisco Firepower firmware:System:fsmRmtInvErrDescr
        managed object property"
    ::= { cfprApFirmwareSystemEntry 9 }

cfprApFirmwareSystemFsmRmtInvRslt OBJECT-TYPE
    SYNTAX       CfprApConditionRemoteInvRslt
    MAX-ACCESS   read-only
    STATUS       current
    DESCRIPTION
        "Cisco Firepower firmware:System:fsmRmtInvRslt
        managed object property"
    ::= { cfprApFirmwareSystemEntry 10 }

cfprApFirmwareSystemFsmStageDescr OBJECT-TYPE
    SYNTAX       SnmpAdminString
    MAX-ACCESS   read-only
    STATUS       current
    DESCRIPTION
        "Cisco Firepower firmware:System:fsmStageDescr
        managed object property"
    ::= { cfprApFirmwareSystemEntry 11 }

cfprApFirmwareSystemFsmStamp OBJECT-TYPE
    SYNTAX       DateAndTime
    MAX-ACCESS   read-only
    STATUS       current
    DESCRIPTION
        "Cisco Firepower firmware:System:fsmStamp managed object property"
    ::= { cfprApFirmwareSystemEntry 12 }

cfprApFirmwareSystemFsmStatus OBJECT-TYPE
    SYNTAX       SnmpAdminString
    MAX-ACCESS   read-only
    STATUS       current
    DESCRIPTION
        "Cisco Firepower firmware:System:fsmStatus managed
        object property"
    ::= { cfprApFirmwareSystemEntry 13 }

cfprApFirmwareSystemFsmTry OBJECT-TYPE
    SYNTAX       Gauge32
    MAX-ACCESS   read-only
    STATUS       current
    DESCRIPTION
        "Cisco Firepower firmware:System:fsmTry managed object property"
    ::= { cfprApFirmwareSystemEntry 14 }

cfprApFirmwareSystemFwUpgradeBitmap OBJECT-TYPE
    SYNTAX       Gauge32
    MAX-ACCESS   read-only
    STATUS       current
    DESCRIPTION
        "Cisco Firepower firmware:System:fwUpgradeBitmap
        managed object property"
    ::= { cfprApFirmwareSystemEntry 15 }

cfprApFirmwareSystemFwUpgradeStatus OBJECT-TYPE
    SYNTAX       SnmpAdminString
    MAX-ACCESS   read-only
    STATUS       current
    DESCRIPTION
        "Cisco Firepower firmware:System:fwUpgradeStatus
        managed object property"
    ::= { cfprApFirmwareSystemEntry 16 }

cfprApFirmwareSystemOperState OBJECT-TYPE
    SYNTAX       CfprApFirmwareInstallState
    MAX-ACCESS   read-only
    STATUS       current
    DESCRIPTION
        "Cisco Firepower firmware:System:operState managed
        object property"
    ::= { cfprApFirmwareSystemEntry 17 }

cfprApFirmwareSystemPackVersion OBJECT-TYPE
    SYNTAX       SnmpAdminString
    MAX-ACCESS   read-only
    STATUS       current
    DESCRIPTION
        "Cisco Firepower firmware:System:packVersion managed
        object property"
    ::= { cfprApFirmwareSystemEntry 18 }

cfprApFirmwareSystemScheduledInstallTime OBJECT-TYPE
    SYNTAX       DateAndTime
    MAX-ACCESS   read-only
    STATUS       current
    DESCRIPTION
        "Cisco Firepower firmware:System:scheduledInstallTime
        managed object property"
    ::= { cfprApFirmwareSystemEntry 19 }

cfprApFirmwareSystemState OBJECT-TYPE
    SYNTAX       CfprApFirmwareFwState
    MAX-ACCESS   read-only
    STATUS       current
    DESCRIPTION
        "Cisco Firepower firmware:System:state managed object property"
    ::= { cfprApFirmwareSystemEntry 20 }

cfprApFirmwareSystemUpgradeState OBJECT-TYPE
    SYNTAX       CfprApFirmwareUpgradeState
    MAX-ACCESS   read-only
    STATUS       current
    DESCRIPTION
        "Cisco Firepower firmware:System:upgradeState managed
        object property"
    ::= { cfprApFirmwareSystemEntry 21 }

cfprApFirmwareSystemUpgradeStatus OBJECT-TYPE
    SYNTAX       SnmpAdminString
    MAX-ACCESS   read-only
    STATUS       current
    DESCRIPTION
        "Cisco Firepower firmware:System:upgradeStatus
        managed object property"
    ::= { cfprApFirmwareSystemEntry 22 }

cfprApFirmwareSystemCompCheckResultTable OBJECT-TYPE
    SYNTAX           SEQUENCE OF CfprApFirmwareSystemCompCheckResultEntry
    MAX-ACCESS       not-accessible
    STATUS           current
    DESCRIPTION
        "Cisco Firepower firmware:SystemCompCheckResult
        managed object table"
    ::= { cfprApFirmwareObjects 62 }

cfprApFirmwareSystemCompCheckResultEntry OBJECT-TYPE
    SYNTAX           CfprApFirmwareSystemCompCheckResultEntry
    MAX-ACCESS       not-accessible
    STATUS           current
    DESCRIPTION
        "Entry for the cfprApFirmwareSystemCompCheckResultTable table."
    INDEX { cfprApFirmwareSystemCompCheckResultInstanceId }
    ::= { cfprApFirmwareSystemCompCheckResultTable 1 }

CfprApFirmwareSystemCompCheckResultEntry ::= SEQUENCE {
    cfprApFirmwareSystemCompCheckResultInstanceId                    CfprApManagedObjectId,
    cfprApFirmwareSystemCompCheckResultDn                            CfprApManagedObjectDn,
    cfprApFirmwareSystemCompCheckResultRn                            SnmpAdminString,
    cfprApFirmwareSystemCompCheckResultKeyDescr                      SnmpAdminString,
    cfprApFirmwareSystemCompCheckResultKeyDn                         SnmpAdminString,
    cfprApFirmwareSystemCompCheckResultNonCompDescr                  SnmpAdminString,
    cfprApFirmwareSystemCompCheckResultNonCompDns                    SnmpAdminString,
    cfprApFirmwareSystemCompCheckResultSubject                       CfprApFirmwareEquipmentType
}

cfprApFirmwareSystemCompCheckResultInstanceId OBJECT-TYPE
    SYNTAX       CfprApManagedObjectId
    MAX-ACCESS   not-accessible
    STATUS       current
    DESCRIPTION
        "Instance identifier of the managed object."
    ::= { cfprApFirmwareSystemCompCheckResultEntry 1 }

cfprApFirmwareSystemCompCheckResultDn OBJECT-TYPE
    SYNTAX       CfprApManagedObjectDn
    MAX-ACCESS   read-only
    STATUS       current
    DESCRIPTION
        "Cisco Firepower firmware:SystemCompCheckResult:dn
        managed object property"
    ::= { cfprApFirmwareSystemCompCheckResultEntry 2 }

cfprApFirmwareSystemCompCheckResultRn OBJECT-TYPE
    SYNTAX       SnmpAdminString
    MAX-ACCESS   read-only
    STATUS       current
    DESCRIPTION
        "Cisco Firepower firmware:SystemCompCheckResult:rn
        managed object property"
    ::= { cfprApFirmwareSystemCompCheckResultEntry 3 }

cfprApFirmwareSystemCompCheckResultKeyDescr OBJECT-TYPE
    SYNTAX       SnmpAdminString
    MAX-ACCESS   read-only
    STATUS       current
    DESCRIPTION
        "Cisco Firepower firmware:SystemCompCheckResult:keyDescr
        managed object property"
    ::= { cfprApFirmwareSystemCompCheckResultEntry 4 }

cfprApFirmwareSystemCompCheckResultKeyDn OBJECT-TYPE
    SYNTAX       SnmpAdminString
    MAX-ACCESS   read-only
    STATUS       current
    DESCRIPTION
        "Cisco Firepower firmware:SystemCompCheckResult:keyDn
        managed object property"
    ::= { cfprApFirmwareSystemCompCheckResultEntry 5 }

cfprApFirmwareSystemCompCheckResultNonCompDescr OBJECT-TYPE
    SYNTAX       SnmpAdminString
    MAX-ACCESS   read-only
    STATUS       current
    DESCRIPTION
        "Cisco Firepower firmware:SystemCompCheckResult:nonCompDescr
        managed object property"
    ::= { cfprApFirmwareSystemCompCheckResultEntry 6 }

cfprApFirmwareSystemCompCheckResultNonCompDns OBJECT-TYPE
    SYNTAX       SnmpAdminString
    MAX-ACCESS   read-only
    STATUS       current
    DESCRIPTION
        "Cisco Firepower firmware:SystemCompCheckResult:nonCompDns
        managed object property"
    ::= { cfprApFirmwareSystemCompCheckResultEntry 7 }

cfprApFirmwareSystemCompCheckResultSubject OBJECT-TYPE
    SYNTAX       CfprApFirmwareEquipmentType
    MAX-ACCESS   read-only
    STATUS       current
    DESCRIPTION
        "Cisco Firepower firmware:SystemCompCheckResult:subject
        managed object property"
    ::= { cfprApFirmwareSystemCompCheckResultEntry 8 }

cfprApFirmwareSystemFsmTable OBJECT-TYPE
    SYNTAX           SEQUENCE OF CfprApFirmwareSystemFsmEntry
    MAX-ACCESS       not-accessible
    STATUS           current
    DESCRIPTION
        "Cisco Firepower firmware:SystemFsm managed object table"
    ::= { cfprApFirmwareObjects 63 }

cfprApFirmwareSystemFsmEntry OBJECT-TYPE
    SYNTAX           CfprApFirmwareSystemFsmEntry
    MAX-ACCESS       not-accessible
    STATUS           current
    DESCRIPTION
        "Entry for the cfprApFirmwareSystemFsmTable table."
    INDEX { cfprApFirmwareSystemFsmInstanceId }
    ::= { cfprApFirmwareSystemFsmTable 1 }

CfprApFirmwareSystemFsmEntry ::= SEQUENCE {
    cfprApFirmwareSystemFsmInstanceId                                CfprApManagedObjectId,
    cfprApFirmwareSystemFsmDn                                        CfprApManagedObjectDn,
    cfprApFirmwareSystemFsmRn                                        SnmpAdminString,
    cfprApFirmwareSystemFsmCompletionTime                            DateAndTime,
    cfprApFirmwareSystemFsmCurrentFsm                                CfprApFirmwareSystemFsmCurrentFsm,
    cfprApFirmwareSystemFsmDescrData                                 SnmpAdminString,
    cfprApFirmwareSystemFsmFsmStatus                                 CfprApFsmFsmStageStatus,
    cfprApFirmwareSystemFsmProgress                                  Gauge32,
    cfprApFirmwareSystemFsmRmtErrCode                                Gauge32,
    cfprApFirmwareSystemFsmRmtErrDescr                               SnmpAdminString,
    cfprApFirmwareSystemFsmRmtRslt                                   CfprApConditionRemoteInvRslt
}

cfprApFirmwareSystemFsmInstanceId OBJECT-TYPE
    SYNTAX       CfprApManagedObjectId
    MAX-ACCESS   not-accessible
    STATUS       current
    DESCRIPTION
        "Instance identifier of the managed object."
    ::= { cfprApFirmwareSystemFsmEntry 1 }

cfprApFirmwareSystemFsmDn OBJECT-TYPE
    SYNTAX       CfprApManagedObjectDn
    MAX-ACCESS   read-only
    STATUS       current
    DESCRIPTION
        "Cisco Firepower firmware:SystemFsm:dn managed object property"
    ::= { cfprApFirmwareSystemFsmEntry 2 }

cfprApFirmwareSystemFsmRn OBJECT-TYPE
    SYNTAX       SnmpAdminString
    MAX-ACCESS   read-only
    STATUS       current
    DESCRIPTION
        "Cisco Firepower firmware:SystemFsm:rn managed object property"
    ::= { cfprApFirmwareSystemFsmEntry 3 }

cfprApFirmwareSystemFsmCompletionTime OBJECT-TYPE
    SYNTAX       DateAndTime
    MAX-ACCESS   read-only
    STATUS       current
    DESCRIPTION
        "Cisco Firepower firmware:SystemFsm:completionTime
        managed object property"
    ::= { cfprApFirmwareSystemFsmEntry 4 }

cfprApFirmwareSystemFsmCurrentFsm OBJECT-TYPE
    SYNTAX       CfprApFirmwareSystemFsmCurrentFsm
    MAX-ACCESS   read-only
    STATUS       current
    DESCRIPTION
        "Cisco Firepower firmware:SystemFsm:currentFsm
        managed object property"
    ::= { cfprApFirmwareSystemFsmEntry 5 }

cfprApFirmwareSystemFsmDescrData OBJECT-TYPE
    SYNTAX       SnmpAdminString
    MAX-ACCESS   read-only
    STATUS       current
    DESCRIPTION
        "Cisco Firepower firmware:SystemFsm:descr managed object property"
    ::= { cfprApFirmwareSystemFsmEntry 6 }

cfprApFirmwareSystemFsmFsmStatus OBJECT-TYPE
    SYNTAX       CfprApFsmFsmStageStatus
    MAX-ACCESS   read-only
    STATUS       current
    DESCRIPTION
        "Cisco Firepower firmware:SystemFsm:fsmStatus managed
        object property"
    ::= { cfprApFirmwareSystemFsmEntry 7 }

cfprApFirmwareSystemFsmProgress OBJECT-TYPE
    SYNTAX       Gauge32
    MAX-ACCESS   read-only
    STATUS       current
    DESCRIPTION
        "Cisco Firepower firmware:SystemFsm:progress managed
        object property"
    ::= { cfprApFirmwareSystemFsmEntry 8 }

cfprApFirmwareSystemFsmRmtErrCode OBJECT-TYPE
    SYNTAX       Gauge32
    MAX-ACCESS   read-only
    STATUS       current
    DESCRIPTION
        "Cisco Firepower firmware:SystemFsm:rmtErrCode
        managed object property"
    ::= { cfprApFirmwareSystemFsmEntry 9 }

cfprApFirmwareSystemFsmRmtErrDescr OBJECT-TYPE
    SYNTAX       SnmpAdminString
    MAX-ACCESS   read-only
    STATUS       current
    DESCRIPTION
        "Cisco Firepower firmware:SystemFsm:rmtErrDescr
        managed object property"
    ::= { cfprApFirmwareSystemFsmEntry 10 }

cfprApFirmwareSystemFsmRmtRslt OBJECT-TYPE
    SYNTAX       CfprApConditionRemoteInvRslt
    MAX-ACCESS   read-only
    STATUS       current
    DESCRIPTION
        "Cisco Firepower firmware:SystemFsm:rmtRslt managed
        object property"
    ::= { cfprApFirmwareSystemFsmEntry 11 }

cfprApFirmwareSystemFsmStageTable OBJECT-TYPE
    SYNTAX           SEQUENCE OF CfprApFirmwareSystemFsmStageEntry
    MAX-ACCESS       not-accessible
    STATUS           current
    DESCRIPTION
        "Cisco Firepower firmware:SystemFsmStage managed object table"
    ::= { cfprApFirmwareObjects 64 }

cfprApFirmwareSystemFsmStageEntry OBJECT-TYPE
    SYNTAX           CfprApFirmwareSystemFsmStageEntry
    MAX-ACCESS       not-accessible
    STATUS           current
    DESCRIPTION
        "Entry for the cfprApFirmwareSystemFsmStageTable table."
    INDEX { cfprApFirmwareSystemFsmStageInstanceId }
    ::= { cfprApFirmwareSystemFsmStageTable 1 }

CfprApFirmwareSystemFsmStageEntry ::= SEQUENCE {
    cfprApFirmwareSystemFsmStageInstanceId                           CfprApManagedObjectId,
    cfprApFirmwareSystemFsmStageDn                                   CfprApManagedObjectDn,
    cfprApFirmwareSystemFsmStageRn                                   SnmpAdminString,
    cfprApFirmwareSystemFsmStageDescrData                            SnmpAdminString,
    cfprApFirmwareSystemFsmStageLastUpdateTime                       DateAndTime,
    cfprApFirmwareSystemFsmStageName                                 CfprApFirmwareSystemFsmStageName,
    cfprApFirmwareSystemFsmStageOrder                                Gauge32,
    cfprApFirmwareSystemFsmStageRetry                                Gauge32,
    cfprApFirmwareSystemFsmStageStageStatus                          CfprApFsmFsmStageStatus
}

cfprApFirmwareSystemFsmStageInstanceId OBJECT-TYPE
    SYNTAX       CfprApManagedObjectId
    MAX-ACCESS   not-accessible
    STATUS       current
    DESCRIPTION
        "Instance identifier of the managed object."
    ::= { cfprApFirmwareSystemFsmStageEntry 1 }

cfprApFirmwareSystemFsmStageDn OBJECT-TYPE
    SYNTAX       CfprApManagedObjectDn
    MAX-ACCESS   read-only
    STATUS       current
    DESCRIPTION
        "Cisco Firepower firmware:SystemFsmStage:dn managed
        object property"
    ::= { cfprApFirmwareSystemFsmStageEntry 2 }

cfprApFirmwareSystemFsmStageRn OBJECT-TYPE
    SYNTAX       SnmpAdminString
    MAX-ACCESS   read-only
    STATUS       current
    DESCRIPTION
        "Cisco Firepower firmware:SystemFsmStage:rn managed
        object property"
    ::= { cfprApFirmwareSystemFsmStageEntry 3 }

cfprApFirmwareSystemFsmStageDescrData OBJECT-TYPE
    SYNTAX       SnmpAdminString
    MAX-ACCESS   read-only
    STATUS       current
    DESCRIPTION
        "Cisco Firepower firmware:SystemFsmStage:descr
        managed object property"
    ::= { cfprApFirmwareSystemFsmStageEntry 4 }

cfprApFirmwareSystemFsmStageLastUpdateTime OBJECT-TYPE
    SYNTAX       DateAndTime
    MAX-ACCESS   read-only
    STATUS       current
    DESCRIPTION
        "Cisco Firepower firmware:SystemFsmStage:lastUpdateTime
        managed object property"
    ::= { cfprApFirmwareSystemFsmStageEntry 5 }

cfprApFirmwareSystemFsmStageName OBJECT-TYPE
    SYNTAX       CfprApFirmwareSystemFsmStageName
    MAX-ACCESS   read-only
    STATUS       current
    DESCRIPTION
        "Cisco Firepower firmware:SystemFsmStage:name managed
        object property"
    ::= { cfprApFirmwareSystemFsmStageEntry 6 }

cfprApFirmwareSystemFsmStageOrder OBJECT-TYPE
    SYNTAX       Gauge32
    MAX-ACCESS   read-only
    STATUS       current
    DESCRIPTION
        "Cisco Firepower firmware:SystemFsmStage:order
        managed object property"
    ::= { cfprApFirmwareSystemFsmStageEntry 7 }

cfprApFirmwareSystemFsmStageRetry OBJECT-TYPE
    SYNTAX       Gauge32
    MAX-ACCESS   read-only
    STATUS       current
    DESCRIPTION
        "Cisco Firepower firmware:SystemFsmStage:retry
        managed object property"
    ::= { cfprApFirmwareSystemFsmStageEntry 8 }

cfprApFirmwareSystemFsmStageStageStatus OBJECT-TYPE
    SYNTAX       CfprApFsmFsmStageStatus
    MAX-ACCESS   read-only
    STATUS       current
    DESCRIPTION
        "Cisco Firepower firmware:SystemFsmStage:stageStatus
        managed object property"
    ::= { cfprApFirmwareSystemFsmStageEntry 9 }

cfprApFirmwareSystemFsmTaskTable OBJECT-TYPE
    SYNTAX           SEQUENCE OF CfprApFirmwareSystemFsmTaskEntry
    MAX-ACCESS       not-accessible
    STATUS           current
    DESCRIPTION
        "Cisco Firepower firmware:SystemFsmTask managed object table"
    ::= { cfprApFirmwareObjects 65 }

cfprApFirmwareSystemFsmTaskEntry OBJECT-TYPE
    SYNTAX           CfprApFirmwareSystemFsmTaskEntry
    MAX-ACCESS       not-accessible
    STATUS           current
    DESCRIPTION
        "Entry for the cfprApFirmwareSystemFsmTaskTable table."
    INDEX { cfprApFirmwareSystemFsmTaskInstanceId }
    ::= { cfprApFirmwareSystemFsmTaskTable 1 }

CfprApFirmwareSystemFsmTaskEntry ::= SEQUENCE {
    cfprApFirmwareSystemFsmTaskInstanceId                            CfprApManagedObjectId,
    cfprApFirmwareSystemFsmTaskDn                                    CfprApManagedObjectDn,
    cfprApFirmwareSystemFsmTaskRn                                    SnmpAdminString,
    cfprApFirmwareSystemFsmTaskCompletion                            CfprApFsmCompletion,
    cfprApFirmwareSystemFsmTaskFlags                                 CfprApFirmwareSystemFsmTaskFlags,
    cfprApFirmwareSystemFsmTaskItem                                  CfprApFirmwareSystemFsmTaskItem,
    cfprApFirmwareSystemFsmTaskSeqId                                 Gauge32
}

cfprApFirmwareSystemFsmTaskInstanceId OBJECT-TYPE
    SYNTAX       CfprApManagedObjectId
    MAX-ACCESS   not-accessible
    STATUS       current
    DESCRIPTION
        "Instance identifier of the managed object."
    ::= { cfprApFirmwareSystemFsmTaskEntry 1 }

cfprApFirmwareSystemFsmTaskDn OBJECT-TYPE
    SYNTAX       CfprApManagedObjectDn
    MAX-ACCESS   read-only
    STATUS       current
    DESCRIPTION
        "Cisco Firepower firmware:SystemFsmTask:dn managed
        object property"
    ::= { cfprApFirmwareSystemFsmTaskEntry 2 }

cfprApFirmwareSystemFsmTaskRn OBJECT-TYPE
    SYNTAX       SnmpAdminString
    MAX-ACCESS   read-only
    STATUS       current
    DESCRIPTION
        "Cisco Firepower firmware:SystemFsmTask:rn managed
        object property"
    ::= { cfprApFirmwareSystemFsmTaskEntry 3 }

cfprApFirmwareSystemFsmTaskCompletion OBJECT-TYPE
    SYNTAX       CfprApFsmCompletion
    MAX-ACCESS   read-only
    STATUS       current
    DESCRIPTION
        "Cisco Firepower firmware:SystemFsmTask:completion
        managed object property"
    ::= { cfprApFirmwareSystemFsmTaskEntry 4 }

cfprApFirmwareSystemFsmTaskFlags OBJECT-TYPE
    SYNTAX       CfprApFirmwareSystemFsmTaskFlags
    MAX-ACCESS   read-only
    STATUS       current
    DESCRIPTION
        "Cisco Firepower firmware:SystemFsmTask:flags managed
        object property"
    ::= { cfprApFirmwareSystemFsmTaskEntry 5 }

cfprApFirmwareSystemFsmTaskItem OBJECT-TYPE
    SYNTAX       CfprApFirmwareSystemFsmTaskItem
    MAX-ACCESS   read-only
    STATUS       current
    DESCRIPTION
        "Cisco Firepower firmware:SystemFsmTask:item managed
        object property"
    ::= { cfprApFirmwareSystemFsmTaskEntry 6 }

cfprApFirmwareSystemFsmTaskSeqId OBJECT-TYPE
    SYNTAX       Gauge32
    MAX-ACCESS   read-only
    STATUS       current
    DESCRIPTION
        "Cisco Firepower firmware:SystemFsmTask:seqId managed
        object property"
    ::= { cfprApFirmwareSystemFsmTaskEntry 7 }

cfprApFirmwareTypeTable OBJECT-TYPE
    SYNTAX           SEQUENCE OF CfprApFirmwareTypeEntry
    MAX-ACCESS       not-accessible
    STATUS           current
    DESCRIPTION
        "Cisco Firepower firmware:Type managed object table"
    ::= { cfprApFirmwareObjects 66 }

cfprApFirmwareTypeEntry OBJECT-TYPE
    SYNTAX           CfprApFirmwareTypeEntry
    MAX-ACCESS       not-accessible
    STATUS           current
    DESCRIPTION
        "Entry for the cfprApFirmwareTypeTable table."
    INDEX { cfprApFirmwareTypeInstanceId }
    ::= { cfprApFirmwareTypeTable 1 }

CfprApFirmwareTypeEntry ::= SEQUENCE {
    cfprApFirmwareTypeInstanceId                                     CfprApManagedObjectId,
    cfprApFirmwareTypeDn                                             CfprApManagedObjectDn,
    cfprApFirmwareTypeRn                                             SnmpAdminString,
    cfprApFirmwareTypeEp                                             CfprApFirmwareType,
    cfprApFirmwareTypeInvTag                                         SnmpAdminString,
    cfprApFirmwareTypeMaxVer                                         SnmpAdminString,
    cfprApFirmwareTypeMinVer                                         SnmpAdminString,
    cfprApFirmwareTypeScheduledInstallTime                           DateAndTime
}

cfprApFirmwareTypeInstanceId OBJECT-TYPE
    SYNTAX       CfprApManagedObjectId
    MAX-ACCESS   not-accessible
    STATUS       current
    DESCRIPTION
        "Instance identifier of the managed object."
    ::= { cfprApFirmwareTypeEntry 1 }

cfprApFirmwareTypeDn OBJECT-TYPE
    SYNTAX       CfprApManagedObjectDn
    MAX-ACCESS   read-only
    STATUS       current
    DESCRIPTION
        "Cisco Firepower firmware:Type:dn managed object property"
    ::= { cfprApFirmwareTypeEntry 2 }

cfprApFirmwareTypeRn OBJECT-TYPE
    SYNTAX       SnmpAdminString
    MAX-ACCESS   read-only
    STATUS       current
    DESCRIPTION
        "Cisco Firepower firmware:Type:rn managed object property"
    ::= { cfprApFirmwareTypeEntry 3 }

cfprApFirmwareTypeEp OBJECT-TYPE
    SYNTAX       CfprApFirmwareType
    MAX-ACCESS   read-only
    STATUS       current
    DESCRIPTION
        "Cisco Firepower firmware:Type:ep managed object property"
    ::= { cfprApFirmwareTypeEntry 4 }

cfprApFirmwareTypeInvTag OBJECT-TYPE
    SYNTAX       SnmpAdminString
    MAX-ACCESS   read-only
    STATUS       current
    DESCRIPTION
        "Cisco Firepower firmware:Type:invTag managed object property"
    ::= { cfprApFirmwareTypeEntry 5 }

cfprApFirmwareTypeMaxVer OBJECT-TYPE
    SYNTAX       SnmpAdminString
    MAX-ACCESS   read-only
    STATUS       current
    DESCRIPTION
        "Cisco Firepower firmware:Type:maxVer managed object property"
    ::= { cfprApFirmwareTypeEntry 6 }

cfprApFirmwareTypeMinVer OBJECT-TYPE
    SYNTAX       SnmpAdminString
    MAX-ACCESS   read-only
    STATUS       current
    DESCRIPTION
        "Cisco Firepower firmware:Type:minVer managed object property"
    ::= { cfprApFirmwareTypeEntry 7 }

cfprApFirmwareTypeScheduledInstallTime OBJECT-TYPE
    SYNTAX       DateAndTime
    MAX-ACCESS   read-only
    STATUS       current
    DESCRIPTION
        "Cisco Firepower firmware:Type:scheduledInstallTime
        managed object property"
    ::= { cfprApFirmwareTypeEntry 8 }

cfprApFirmwareUcscInfoTable OBJECT-TYPE
    SYNTAX           SEQUENCE OF CfprApFirmwareUcscInfoEntry
    MAX-ACCESS       not-accessible
    STATUS           current
    DESCRIPTION
        "Cisco Firepower firmware:UcscInfo managed object table"
    ::= { cfprApFirmwareObjects 67 }

cfprApFirmwareUcscInfoEntry OBJECT-TYPE
    SYNTAX           CfprApFirmwareUcscInfoEntry
    MAX-ACCESS       not-accessible
    STATUS           current
    DESCRIPTION
        "Entry for the cfprApFirmwareUcscInfoTable table."
    INDEX { cfprApFirmwareUcscInfoInstanceId }
    ::= { cfprApFirmwareUcscInfoTable 1 }

CfprApFirmwareUcscInfoEntry ::= SEQUENCE {
    cfprApFirmwareUcscInfoInstanceId                                 CfprApManagedObjectId,
    cfprApFirmwareUcscInfoDn                                         CfprApManagedObjectDn,
    cfprApFirmwareUcscInfoRn                                         SnmpAdminString,
    cfprApFirmwareUcscInfoConnProtocol                               CfprApExtpolConnProtocol,
    cfprApFirmwareUcscInfoHost                                       SnmpAdminString,
    cfprApFirmwareUcscInfoVersion                                    SnmpAdminString
}

cfprApFirmwareUcscInfoInstanceId OBJECT-TYPE
    SYNTAX       CfprApManagedObjectId
    MAX-ACCESS   not-accessible
    STATUS       current
    DESCRIPTION
        "Instance identifier of the managed object."
    ::= { cfprApFirmwareUcscInfoEntry 1 }

cfprApFirmwareUcscInfoDn OBJECT-TYPE
    SYNTAX       CfprApManagedObjectDn
    MAX-ACCESS   read-only
    STATUS       current
    DESCRIPTION
        "Cisco Firepower firmware:UcscInfo:dn managed object property"
    ::= { cfprApFirmwareUcscInfoEntry 2 }

cfprApFirmwareUcscInfoRn OBJECT-TYPE
    SYNTAX       SnmpAdminString
    MAX-ACCESS   read-only
    STATUS       current
    DESCRIPTION
        "Cisco Firepower firmware:UcscInfo:rn managed object property"
    ::= { cfprApFirmwareUcscInfoEntry 3 }

cfprApFirmwareUcscInfoConnProtocol OBJECT-TYPE
    SYNTAX       CfprApExtpolConnProtocol
    MAX-ACCESS   read-only
    STATUS       current
    DESCRIPTION
        "Cisco Firepower firmware:UcscInfo:connProtocol
        managed object property"
    ::= { cfprApFirmwareUcscInfoEntry 4 }

cfprApFirmwareUcscInfoHost OBJECT-TYPE
    SYNTAX       SnmpAdminString
    MAX-ACCESS   read-only
    STATUS       current
    DESCRIPTION
        "Cisco Firepower firmware:UcscInfo:host managed object property"
    ::= { cfprApFirmwareUcscInfoEntry 5 }

cfprApFirmwareUcscInfoVersion OBJECT-TYPE
    SYNTAX       SnmpAdminString
    MAX-ACCESS   read-only
    STATUS       current
    DESCRIPTION
        "Cisco Firepower firmware:UcscInfo:version managed
        object property"
    ::= { cfprApFirmwareUcscInfoEntry 6 }

cfprApFirmwareUpdatableTable OBJECT-TYPE
    SYNTAX           SEQUENCE OF CfprApFirmwareUpdatableEntry
    MAX-ACCESS       not-accessible
    STATUS           current
    DESCRIPTION
        "Cisco Firepower firmware:Updatable managed object table"
    ::= { cfprApFirmwareObjects 68 }

cfprApFirmwareUpdatableEntry OBJECT-TYPE
    SYNTAX           CfprApFirmwareUpdatableEntry
    MAX-ACCESS       not-accessible
    STATUS           current
    DESCRIPTION
        "Entry for the cfprApFirmwareUpdatableTable table."
    INDEX { cfprApFirmwareUpdatableInstanceId }
    ::= { cfprApFirmwareUpdatableTable 1 }

CfprApFirmwareUpdatableEntry ::= SEQUENCE {
    cfprApFirmwareUpdatableInstanceId                                CfprApManagedObjectId,
    cfprApFirmwareUpdatableDn                                        CfprApManagedObjectDn,
    cfprApFirmwareUpdatableRn                                        SnmpAdminString,
    cfprApFirmwareUpdatableAdminState                                CfprApFirmwareTriggerState,
    cfprApFirmwareUpdatableDeployment                                CfprApFirmwareUpdatableDeployment,
    cfprApFirmwareUpdatableOperState                                 CfprApFirmwareImageState,
    cfprApFirmwareUpdatableOperStateQual                             CfprApFirmwareImageError,
    cfprApFirmwareUpdatablePrevVersion                               SnmpAdminString,
    cfprApFirmwareUpdatableVersion                                   SnmpAdminString
}

cfprApFirmwareUpdatableInstanceId OBJECT-TYPE
    SYNTAX       CfprApManagedObjectId
    MAX-ACCESS   not-accessible
    STATUS       current
    DESCRIPTION
        "Instance identifier of the managed object."
    ::= { cfprApFirmwareUpdatableEntry 1 }

cfprApFirmwareUpdatableDn OBJECT-TYPE
    SYNTAX       CfprApManagedObjectDn
    MAX-ACCESS   read-only
    STATUS       current
    DESCRIPTION
        "Cisco Firepower firmware:Updatable:dn managed object property"
    ::= { cfprApFirmwareUpdatableEntry 2 }

cfprApFirmwareUpdatableRn OBJECT-TYPE
    SYNTAX       SnmpAdminString
    MAX-ACCESS   read-only
    STATUS       current
    DESCRIPTION
        "Cisco Firepower firmware:Updatable:rn managed object property"
    ::= { cfprApFirmwareUpdatableEntry 3 }

cfprApFirmwareUpdatableAdminState OBJECT-TYPE
    SYNTAX       CfprApFirmwareTriggerState
    MAX-ACCESS   read-only
    STATUS       current
    DESCRIPTION
        "Cisco Firepower firmware:Updatable:adminState
        managed object property"
    ::= { cfprApFirmwareUpdatableEntry 4 }

cfprApFirmwareUpdatableDeployment OBJECT-TYPE
    SYNTAX       CfprApFirmwareUpdatableDeployment
    MAX-ACCESS   read-only
    STATUS       current
    DESCRIPTION
        "Cisco Firepower firmware:Updatable:deployment
        managed object property"
    ::= { cfprApFirmwareUpdatableEntry 5 }

cfprApFirmwareUpdatableOperState OBJECT-TYPE
    SYNTAX       CfprApFirmwareImageState
    MAX-ACCESS   read-only
    STATUS       current
    DESCRIPTION
        "Cisco Firepower firmware:Updatable:operState managed
        object property"
    ::= { cfprApFirmwareUpdatableEntry 6 }

cfprApFirmwareUpdatableOperStateQual OBJECT-TYPE
    SYNTAX       CfprApFirmwareImageError
    MAX-ACCESS   read-only
    STATUS       current
    DESCRIPTION
        "Cisco Firepower firmware:Updatable:operStateQual
        managed object property"
    ::= { cfprApFirmwareUpdatableEntry 7 }

cfprApFirmwareUpdatablePrevVersion OBJECT-TYPE
    SYNTAX       SnmpAdminString
    MAX-ACCESS   read-only
    STATUS       current
    DESCRIPTION
        "Cisco Firepower firmware:Updatable:prevVersion
        managed object property"
    ::= { cfprApFirmwareUpdatableEntry 8 }

cfprApFirmwareUpdatableVersion OBJECT-TYPE
    SYNTAX       SnmpAdminString
    MAX-ACCESS   read-only
    STATUS       current
    DESCRIPTION
        "Cisco Firepower firmware:Updatable:version managed
        object property"
    ::= { cfprApFirmwareUpdatableEntry 9 }

cfprApFirmwareUpgradeConstraintTable OBJECT-TYPE
    SYNTAX           SEQUENCE OF CfprApFirmwareUpgradeConstraintEntry
    MAX-ACCESS       not-accessible
    STATUS           current
    DESCRIPTION
        "Cisco Firepower firmware:UpgradeConstraint managed object table"
    ::= { cfprApFirmwareObjects 69 }

cfprApFirmwareUpgradeConstraintEntry OBJECT-TYPE
    SYNTAX           CfprApFirmwareUpgradeConstraintEntry
    MAX-ACCESS       not-accessible
    STATUS           current
    DESCRIPTION
        "Entry for the cfprApFirmwareUpgradeConstraintTable table."
    INDEX { cfprApFirmwareUpgradeConstraintInstanceId }
    ::= { cfprApFirmwareUpgradeConstraintTable 1 }

CfprApFirmwareUpgradeConstraintEntry ::= SEQUENCE {
    cfprApFirmwareUpgradeConstraintInstanceId                        CfprApManagedObjectId,
    cfprApFirmwareUpgradeConstraintDn                                CfprApManagedObjectDn,
    cfprApFirmwareUpgradeConstraintRn                                SnmpAdminString,
    cfprApFirmwareUpgradeConstraintMinVer                            SnmpAdminString
}

cfprApFirmwareUpgradeConstraintInstanceId OBJECT-TYPE
    SYNTAX       CfprApManagedObjectId
    MAX-ACCESS   not-accessible
    STATUS       current
    DESCRIPTION
        "Instance identifier of the managed object."
    ::= { cfprApFirmwareUpgradeConstraintEntry 1 }

cfprApFirmwareUpgradeConstraintDn OBJECT-TYPE
    SYNTAX       CfprApManagedObjectDn
    MAX-ACCESS   read-only
    STATUS       current
    DESCRIPTION
        "Cisco Firepower firmware:UpgradeConstraint:dn
        managed object property"
    ::= { cfprApFirmwareUpgradeConstraintEntry 2 }

cfprApFirmwareUpgradeConstraintRn OBJECT-TYPE
    SYNTAX       SnmpAdminString
    MAX-ACCESS   read-only
    STATUS       current
    DESCRIPTION
        "Cisco Firepower firmware:UpgradeConstraint:rn
        managed object property"
    ::= { cfprApFirmwareUpgradeConstraintEntry 3 }

cfprApFirmwareUpgradeConstraintMinVer OBJECT-TYPE
    SYNTAX       SnmpAdminString
    MAX-ACCESS   read-only
    STATUS       current
    DESCRIPTION
        "Cisco Firepower firmware:UpgradeConstraint:minVer
        managed object property"
    ::= { cfprApFirmwareUpgradeConstraintEntry 4 }

cfprApFirmwareUpgradeDetailTable OBJECT-TYPE
    SYNTAX           SEQUENCE OF CfprApFirmwareUpgradeDetailEntry
    MAX-ACCESS       not-accessible
    STATUS           current
    DESCRIPTION
        "Cisco Firepower firmware:UpgradeDetail managed object table"
    ::= { cfprApFirmwareObjects 70 }

cfprApFirmwareUpgradeDetailEntry OBJECT-TYPE
    SYNTAX           CfprApFirmwareUpgradeDetailEntry
    MAX-ACCESS       not-accessible
    STATUS           current
    DESCRIPTION
        "Entry for the cfprApFirmwareUpgradeDetailTable table."
    INDEX { cfprApFirmwareUpgradeDetailInstanceId }
    ::= { cfprApFirmwareUpgradeDetailTable 1 }

CfprApFirmwareUpgradeDetailEntry ::= SEQUENCE {
    cfprApFirmwareUpgradeDetailInstanceId                            CfprApManagedObjectId,
    cfprApFirmwareUpgradeDetailDn                                    CfprApManagedObjectDn,
    cfprApFirmwareUpgradeDetailRn                                    SnmpAdminString,
    cfprApFirmwareUpgradeDetailCategory                              CfprApFirmwareUpgradeCategory,
    cfprApFirmwareUpgradeDetailDescription                           SnmpAdminString,
    cfprApFirmwareUpgradeDetailId                                    Gauge32,
    cfprApFirmwareUpgradeDetailSeverity                              CfprApFirmwareUpgradeSeverity
}

cfprApFirmwareUpgradeDetailInstanceId OBJECT-TYPE
    SYNTAX       CfprApManagedObjectId
    MAX-ACCESS   not-accessible
    STATUS       current
    DESCRIPTION
        "Instance identifier of the managed object."
    ::= { cfprApFirmwareUpgradeDetailEntry 1 }

cfprApFirmwareUpgradeDetailDn OBJECT-TYPE
    SYNTAX       CfprApManagedObjectDn
    MAX-ACCESS   read-only
    STATUS       current
    DESCRIPTION
        "Cisco Firepower firmware:UpgradeDetail:dn managed
        object property"
    ::= { cfprApFirmwareUpgradeDetailEntry 2 }

cfprApFirmwareUpgradeDetailRn OBJECT-TYPE
    SYNTAX       SnmpAdminString
    MAX-ACCESS   read-only
    STATUS       current
    DESCRIPTION
        "Cisco Firepower firmware:UpgradeDetail:rn managed
        object property"
    ::= { cfprApFirmwareUpgradeDetailEntry 3 }

cfprApFirmwareUpgradeDetailCategory OBJECT-TYPE
    SYNTAX       CfprApFirmwareUpgradeCategory
    MAX-ACCESS   read-only
    STATUS       current
    DESCRIPTION
        "Cisco Firepower firmware:UpgradeDetail:category
        managed object property"
    ::= { cfprApFirmwareUpgradeDetailEntry 4 }

cfprApFirmwareUpgradeDetailDescription OBJECT-TYPE
    SYNTAX       SnmpAdminString
    MAX-ACCESS   read-only
    STATUS       current
    DESCRIPTION
        "Cisco Firepower firmware:UpgradeDetail:description
        managed object property"
    ::= { cfprApFirmwareUpgradeDetailEntry 5 }

cfprApFirmwareUpgradeDetailId OBJECT-TYPE
    SYNTAX       Gauge32
    MAX-ACCESS   read-only
    STATUS       current
    DESCRIPTION
        "Cisco Firepower firmware:UpgradeDetail:id managed
        object property"
    ::= { cfprApFirmwareUpgradeDetailEntry 6 }

cfprApFirmwareUpgradeDetailSeverity OBJECT-TYPE
    SYNTAX       CfprApFirmwareUpgradeSeverity
    MAX-ACCESS   read-only
    STATUS       current
    DESCRIPTION
        "Cisco Firepower firmware:UpgradeDetail:severity
        managed object property"
    ::= { cfprApFirmwareUpgradeDetailEntry 7 }

cfprApFirmwareUpgradeInfoTable OBJECT-TYPE
    SYNTAX           SEQUENCE OF CfprApFirmwareUpgradeInfoEntry
    MAX-ACCESS       not-accessible
    STATUS           current
    DESCRIPTION
        "Cisco Firepower firmware:UpgradeInfo managed object table"
    ::= { cfprApFirmwareObjects 71 }

cfprApFirmwareUpgradeInfoEntry OBJECT-TYPE
    SYNTAX           CfprApFirmwareUpgradeInfoEntry
    MAX-ACCESS       not-accessible
    STATUS           current
    DESCRIPTION
        "Entry for the cfprApFirmwareUpgradeInfoTable table."
    INDEX { cfprApFirmwareUpgradeInfoInstanceId }
    ::= { cfprApFirmwareUpgradeInfoTable 1 }

CfprApFirmwareUpgradeInfoEntry ::= SEQUENCE {
    cfprApFirmwareUpgradeInfoInstanceId                              CfprApManagedObjectId,
    cfprApFirmwareUpgradeInfoDn                                      CfprApManagedObjectDn,
    cfprApFirmwareUpgradeInfoRn                                      SnmpAdminString,
    cfprApFirmwareUpgradeInfoMessage                                 SnmpAdminString,
    cfprApFirmwareUpgradeInfoTimeStamp                               DateAndTime,
    cfprApFirmwareUpgradeInfoValidateStatus                          CfprApFirmwareUpgradeStatus,
    cfprApFirmwareUpgradeInfoVersion                                 SnmpAdminString
}

cfprApFirmwareUpgradeInfoInstanceId OBJECT-TYPE
    SYNTAX       CfprApManagedObjectId
    MAX-ACCESS   not-accessible
    STATUS       current
    DESCRIPTION
        "Instance identifier of the managed object."
    ::= { cfprApFirmwareUpgradeInfoEntry 1 }

cfprApFirmwareUpgradeInfoDn OBJECT-TYPE
    SYNTAX       CfprApManagedObjectDn
    MAX-ACCESS   read-only
    STATUS       current
    DESCRIPTION
        "Cisco Firepower firmware:UpgradeInfo:dn managed object property"
    ::= { cfprApFirmwareUpgradeInfoEntry 2 }

cfprApFirmwareUpgradeInfoRn OBJECT-TYPE
    SYNTAX       SnmpAdminString
    MAX-ACCESS   read-only
    STATUS       current
    DESCRIPTION
        "Cisco Firepower firmware:UpgradeInfo:rn managed object property"
    ::= { cfprApFirmwareUpgradeInfoEntry 3 }

cfprApFirmwareUpgradeInfoMessage OBJECT-TYPE
    SYNTAX       SnmpAdminString
    MAX-ACCESS   read-only
    STATUS       current
    DESCRIPTION
        "Cisco Firepower firmware:UpgradeInfo:message managed
        object property"
    ::= { cfprApFirmwareUpgradeInfoEntry 4 }

cfprApFirmwareUpgradeInfoTimeStamp OBJECT-TYPE
    SYNTAX       DateAndTime
    MAX-ACCESS   read-only
    STATUS       current
    DESCRIPTION
        "Cisco Firepower firmware:UpgradeInfo:timeStamp
        managed object property"
    ::= { cfprApFirmwareUpgradeInfoEntry 5 }

cfprApFirmwareUpgradeInfoValidateStatus OBJECT-TYPE
    SYNTAX       CfprApFirmwareUpgradeStatus
    MAX-ACCESS   read-only
    STATUS       current
    DESCRIPTION
        "Cisco Firepower firmware:UpgradeInfo:validateStatus
        managed object property"
    ::= { cfprApFirmwareUpgradeInfoEntry 6 }

cfprApFirmwareUpgradeInfoVersion OBJECT-TYPE
    SYNTAX       SnmpAdminString
    MAX-ACCESS   read-only
    STATUS       current
    DESCRIPTION
        "Cisco Firepower firmware:UpgradeInfo:version managed
        object property"
    ::= { cfprApFirmwareUpgradeInfoEntry 7 }

END
