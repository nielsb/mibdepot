-- *********************************************************************
-- CISCO-FIREPOWER-AP-FABRIC-MIB.my
-- 
-- MIB representation of the Cisco Firepower
-- FABRIC management information model package
-- 
-- Created July 2022 by Charles Bullis
-- 
-- Copyright (c) 2005-2022 Cisco Systems, Inc. All rights reserved.
-- 
-- *********************************************************************

CISCO-FIREPOWER-AP-FABRIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApComputeDiscovery,
    CfprApConditionRemoteInvRslt,
    CfprApEquipmentBoardAggregationRole,
    CfprApEquipmentConnectionStatus,
    CfprApEquipmentFabricEpType,
    CfprApEquipmentSlotStatus,
    CfprApFabricADceSwSrvEpTransport,
    CfprApFabricAEthEstcEpIfRole,
    CfprApFabricAEthEstcEpTransport,
    CfprApFabricAEthEstcEpType,
    CfprApFabricAEthLanEpTransport,
    CfprApFabricAFcSanEpTransport,
    CfprApFabricAFcoeSanEpTransport,
    CfprApFabricAVlanAssocPrimaryVlanSwitchId,
    CfprApFabricAVlanSharing,
    CfprApFabricAVlanTransport,
    CfprApFabricAVlanType,
    CfprApFabricAVsanTransport,
    CfprApFabricAVsanType,
    CfprApFabricAccessType,
    CfprApFabricAdminState,
    CfprApFabricBHVlanSwitchId,
    CfprApFabricBladeLifeCycle,
    CfprApFabricBreakoutPortId,
    CfprApFabricBreakoutSlotId,
    CfprApFabricBreakoutType,
    CfprApFabricCIoEpAdminState,
    CfprApFabricCIoEpIfType,
    CfprApFabricCdpLinkPolicyAdminState,
    CfprApFabricCloudType,
    CfprApFabricComputeEpIfRole,
    CfprApFabricComputeEpType,
    CfprApFabricComputePhEpAdminState,
    CfprApFabricComputeSlotEpSlotId,
    CfprApFabricConfMode,
    CfprApFabricConfState,
    CfprApFabricConfigState,
    CfprApFabricDceSwSrvEpPortId,
    CfprApFabricDceSwSrvEpSlotId,
    CfprApFabricDceSwSrvPcAdminState,
    CfprApFabricDceSwSrvPcEpPortId,
    CfprApFabricDceSwSrvPcEpSlotId,
    CfprApFabricDceSwSrvPcPortId,
    CfprApFabricDceSwSrvPcTransport,
    CfprApFabricDefaultZoningState,
    CfprApFabricEpMgrFsmCurrentFsm,
    CfprApFabricEpMgrFsmStageName,
    CfprApFabricEpMgrFsmTaskFlags,
    CfprApFabricEpMgrFsmTaskItem,
    CfprApFabricEstcPcIfRole,
    CfprApFabricEstcPcType,
    CfprApFabricEthCdpPolicyProtocol,
    CfprApFabricEthEstcEpPortId,
    CfprApFabricEthEstcEpPrio,
    CfprApFabricEthEstcEpSlotId,
    CfprApFabricEthEstcEpTransport,
    CfprApFabricEthEstcEpType,
    CfprApFabricEthEstcOperPortMode,
    CfprApFabricEthEstcPcEpPortId,
    CfprApFabricEthEstcPcEpSlotId,
    CfprApFabricEthEstcPcTransport,
    CfprApFabricEthEstcPortMode,
    CfprApFabricEthEstcTransport,
    CfprApFabricEthEstcType,
    CfprApFabricEthLanEpAdminState,
    CfprApFabricEthLanEpSpeedCap,
    CfprApFabricEthLanEpVlanStatus,
    CfprApFabricEthLanPcAdminState,
    CfprApFabricEthLanPcLacpDetach,
    CfprApFabricEthLanPcSpeedCap,
    CfprApFabricEthLanPcTransport,
    CfprApFabricEthLanPcVlanStatus,
    CfprApFabricEthLanTransport,
    CfprApFabricEthLinkPolicyType,
    CfprApFabricEthMonDestEpAdminSpeed,
    CfprApFabricEthMonDestEpIfRole,
    CfprApFabricEthMonDestEpPortId,
    CfprApFabricEthMonDestEpSlotId,
    CfprApFabricEthMonDestEpType,
    CfprApFabricEthMonFiltEpType,
    CfprApFabricEthMonFiltRefType,
    CfprApFabricEthMonLanTransport,
    CfprApFabricEthMonLanType,
    CfprApFabricEthMonSrcEpType,
    CfprApFabricEthMonSrcRefType,
    CfprApFabricEthMonTransport,
    CfprApFabricEthMonType,
    CfprApFabricEthPcProtocol,
    CfprApFabricEthSourceType,
    CfprApFabricEthTargetEpTransport,
    CfprApFabricEthUdldPolicyProtocol,
    CfprApFabricEthVlanPcTransport,
    CfprApFabricExternalEpAdminState,
    CfprApFabricExternalEpLocale,
    CfprApFabricExternalLocale,
    CfprApFabricExternalPcLocale,
    CfprApFabricFcSanEpPortId,
    CfprApFabricFcSanEpSlotId,
    CfprApFabricFcSanPcEpPortId,
    CfprApFabricFcSanPcEpSlotId,
    CfprApFabricFcSanPcTransport,
    CfprApFabricFcSanTransport,
    CfprApFabricFcSanUplinkTrunking,
    CfprApFabricFcVsanPcTransport,
    CfprApFabricFcVsanPortEpPortId,
    CfprApFabricFcVsanPortEpSlotId,
    CfprApFabricFcZoneSharingMode,
    CfprApFabricFcoeSanEpPortId,
    CfprApFabricFcoeSanEpSlotId,
    CfprApFabricFcoeSanPcEpPortId,
    CfprApFabricFcoeSanPcEpSlotId,
    CfprApFabricFcoeSanPcTransport,
    CfprApFabricFcoeVsanPcTransport,
    CfprApFabricFcoeVsanPortEpPortId,
    CfprApFabricFcoeVsanPortEpSlotId,
    CfprApFabricFillPattern,
    CfprApFabricInternalDceSrvTransport,
    CfprApFabricInternalDceSrvType,
    CfprApFabricInternalEpAdminState,
    CfprApFabricInternalEpLocale,
    CfprApFabricInternalLocale,
    CfprApFabricInternalPcLocale,
    CfprApFabricLacpMode,
    CfprApFabricLacpRate,
    CfprApFabricLacpSuspend,
    CfprApFabricLanCloudFsmCurrentFsm,
    CfprApFabricLanCloudFsmStageName,
    CfprApFabricLanCloudFsmTaskItem,
    CfprApFabricLanCloudVlanCompression,
    CfprApFabricLanEpIfRole,
    CfprApFabricLanEpType,
    CfprApFabricLanPcIfRole,
    CfprApFabricLanPcType,
    CfprApFabricLanType,
    CfprApFabricLifeCycle,
    CfprApFabricMemberStatus,
    CfprApFabricMembershipStatus,
    CfprApFabricMonAdminState,
    CfprApFabricMonOperState,
    CfprApFabricMonOperStateReason,
    CfprApFabricNetGroupSwitchId,
    CfprApFabricNetGroupType,
    CfprApFabricOwner,
    CfprApFabricPIoEpIfType,
    CfprApFabricPIoEpOperState,
    CfprApFabricPIoEpPortId,
    CfprApFabricPIoEpSlotId,
    CfprApFabricPathEpIfType,
    CfprApFabricPathEpLocale,
    CfprApFabricPcConfigStatus,
    CfprApFabricPktCaptureAppSlotId,
    CfprApFabricPoolMemberConfigIssues,
    CfprApFabricQosPrio,
    CfprApFabricQuerierType,
    CfprApFabricRecoveryAction,
    CfprApFabricReqIssues,
    CfprApFabricSSAPortType,
    CfprApFabricSanCloudFsmCurrentFsm,
    CfprApFabricSanCloudFsmStageName,
    CfprApFabricSanCloudFsmTaskItem,
    CfprApFabricSanEpIfRole,
    CfprApFabricSanEpType,
    CfprApFabricSanPcIfRole,
    CfprApFabricSanPcType,
    CfprApFabricSanType,
    CfprApFabricSlotAdminState,
    CfprApFabricSnoopingType,
    CfprApFabricSpannedCluster,
    CfprApFabricSspEthMonAppendFlag,
    CfprApFabricSspMonAdminState,
    CfprApFabricSspMonDelPcap,
    CfprApFabricSspMonOperState,
    CfprApFabricSspMonOperStateReason,
    CfprApFabricStatus,
    CfprApFabricSubGroupAggrPortId,
    CfprApFabricSubGroupConfigState,
    CfprApFabricSubGroupSlotId,
    CfprApFabricSwChEpIfRole,
    CfprApFabricSwChEpType,
    CfprApFabricSwChPhEpAdminState,
    CfprApFabricSwSrvEpIfRole,
    CfprApFabricSwSrvEpType,
    CfprApFabricSwSrvPcIfRole,
    CfprApFabricSwSrvPcType,
    CfprApFabricSwSubGroupAggrPortId,
    CfprApFabricSwSubGroupConfigState,
    CfprApFabricSwSubGroupSlotId,
    CfprApFabricSwitchingMode,
    CfprApFabricTargetEpType,
    CfprApFabricTargetStatus,
    CfprApFabricTrafficDirection,
    CfprApFabricUdldLinkPolicyAdminState,
    CfprApFabricUdldLinkPolicyMode,
    CfprApFabricUdldOperState,
    CfprApFabricVConInstType,
    CfprApFabricVConMappingScheme,
    CfprApFabricVConPlacementPref,
    CfprApFabricVConSelectPref,
    CfprApFabricVConSharePref,
    CfprApFabricVConTransportPref,
    CfprApFabricVlanAssocPrimaryVlanState,
    CfprApFabricVlanCompType,
    CfprApFabricVlanConfigIssues,
    CfprApFabricVlanOperState,
    CfprApFabricVlanOverlapState,
    CfprApFabricVlanSwitchId,
    CfprApFabricVnetEpIfRole,
    CfprApFabricVnetEpLocale,
    CfprApFabricVnetEpPolicyOwner,
    CfprApFabricVnetEpSyncEpFsmCurrentFsm,
    CfprApFabricVnetEpSyncEpFsmStageName,
    CfprApFabricVnetEpSyncEpFsmTaskItem,
    CfprApFabricVsanOperState,
    CfprApFabricVsanSwitchId,
    CfprApFabricWarnings,
    CfprApFabricZoningState,
    CfprApFsmCompletion,
    CfprApFsmFlags,
    CfprApFsmFsmStageStatus,
    CfprApLicenseState,
    CfprApNetworkConnectionType,
    CfprApNetworkLocale,
    CfprApNetworkPortOperState,
    CfprApNetworkPortRole,
    CfprApNetworkSide,
    CfprApNetworkSwitchId,
    CfprApNetworkTransport,
    CfprApNetworkVnetEpIfType,
    CfprApNhTpHashType,
    CfprApPolicyPolicyOwner,
    CfprApPoolPoolAssignmentOrder,
    CfprApPortDuplex,
    CfprApPortEthSpeed,
    CfprApPortSpeed,
    CfprApQosPriority,
    CfprApSwPktCaptureLifeCycle
        FROM CISCO-FIREPOWER-AP-TC-MIB;

cfprApFabricObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FABRIC management information model package"
    ::= { ciscoFirepowerApMIBObjects 26 }

cfprApFabricBHVlanTable OBJECT-TYPE
    SYNTAX           SEQUENCE OF CfprApFabricBHVlanEntry
    MAX-ACCESS       not-accessible
    STATUS           current
    DESCRIPTION
        "Cisco Firepower fabric:BHVlan managed object table"
    ::= { cfprApFabricObjects 1 }

cfprApFabricBHVlanEntry OBJECT-TYPE
    SYNTAX           CfprApFabricBHVlanEntry
    MAX-ACCESS       not-accessible
    STATUS           current
    DESCRIPTION
        "Entry for the cfprApFabricBHVlanTable table."
    INDEX { cfprApFabricBHVlanInstanceId }
    ::= { cfprApFabricBHVlanTable 1 }

CfprApFabricBHVlanEntry ::= SEQUENCE {
    cfprApFabricBHVlanInstanceId                                     CfprApManagedObjectId,
    cfprApFabricBHVlanDn                                             CfprApManagedObjectDn,
    cfprApFabricBHVlanRn                                             SnmpAdminString,
    cfprApFabricBHVlanAssocPrimaryVlanState                          CfprApFabricVlanAssocPrimaryVlanState,
    cfprApFabricBHVlanAssocPrimaryVlanSwitchId                       CfprApFabricAVlanAssocPrimaryVlanSwitchId,
    cfprApFabricBHVlanEpDn                                           SnmpAdminString,
    cfprApFabricBHVlanId                                             Gauge32,
    cfprApFabricBHVlanIfRole                                         CfprApFabricVnetEpIfRole,
    cfprApFabricBHVlanIfType                                         CfprApNetworkVnetEpIfType,
    cfprApFabricBHVlanLocale                                         CfprApFabricVnetEpLocale,
    cfprApFabricBHVlanName                                           SnmpAdminString,
    cfprApFabricBHVlanOperState                                      CfprApFabricVlanOperState,
    cfprApFabricBHVlanOverlapStateForA                               CfprApFabricVlanOverlapState,
    cfprApFabricBHVlanOverlapStateForB                               CfprApFabricVlanOverlapState,
    cfprApFabricBHVlanPeerDn                                         SnmpAdminString,
    cfprApFabricBHVlanPolicyOwner                                    CfprApFabricVnetEpPolicyOwner,
    cfprApFabricBHVlanPubNwDn                                        SnmpAdminString,
    cfprApFabricBHVlanPubNwId                                        Gauge32,
    cfprApFabricBHVlanPubNwName                                      SnmpAdminString,
    cfprApFabricBHVlanSharing                                        CfprApFabricAVlanSharing,
    cfprApFabricBHVlanSwitchId                                       CfprApFabricBHVlanSwitchId,
    cfprApFabricBHVlanTransport                                      CfprApFabricAVlanTransport,
    cfprApFabricBHVlanType                                           CfprApFabricAVlanType
}

cfprApFabricBHVlanInstanceId OBJECT-TYPE
    SYNTAX       CfprApManagedObjectId
    MAX-ACCESS   not-accessible
    STATUS       current
    DESCRIPTION
        "Instance identifier of the managed object."
    ::= { cfprApFabricBHVlanEntry 1 }

cfprApFabricBHVlanDn OBJECT-TYPE
    SYNTAX       CfprApManagedObjectDn
    MAX-ACCESS   read-only
    STATUS       current
    DESCRIPTION
        "Cisco Firepower fabric:BHVlan:dn managed object property"
    ::= { cfprApFabricBHVlanEntry 2 }

cfprApFabricBHVlanRn OBJECT-TYPE
    SYNTAX       SnmpAdminString
    MAX-ACCESS   read-only
    STATUS       current
    DESCRIPTION
        "Cisco Firepower fabric:BHVlan:rn managed object property"
    ::= { cfprApFabricBHVlanEntry 3 }

cfprApFabricBHVlanAssocPrimaryVlanState OBJECT-TYPE
    SYNTAX       CfprApFabricVlanAssocPrimaryVlanState
    MAX-ACCESS   read-only
    STATUS       current
    DESCRIPTION
        "Cisco Firepower fabric:BHVlan:assocPrimaryVlanState
        managed object property"
    ::= { cfprApFabricBHVlanEntry 4 }

cfprApFabricBHVlanAssocPrimaryVlanSwitchId OBJECT-TYPE
    SYNTAX       CfprApFabricAVlanAssocPrimaryVlanSwitchId
    MAX-ACCESS   read-only
    STATUS       current
    DESCRIPTION
        "Cisco Firepower fabric:BHVlan:assocPrimaryVlanSwitchId
        managed object property"
    ::= { cfprApFabricBHVlanEntry 5 }

cfprApFabricBHVlanEpDn OBJECT-TYPE
    SYNTAX       SnmpAdminString
    MAX-ACCESS   read-only
    STATUS       current
    DESCRIPTION
        "Cisco Firepower fabric:BHVlan:epDn managed object property"
    ::= { cfprApFabricBHVlanEntry 6 }

cfprApFabricBHVlanId OBJECT-TYPE
    SYNTAX       Gauge32
    MAX-ACCESS   read-only
    STATUS       current
    DESCRIPTION
        "Cisco Firepower fabric:BHVlan:id managed object property"
    ::= { cfprApFabricBHVlanEntry 7 }

cfprApFabricBHVlanIfRole OBJECT-TYPE
    SYNTAX       CfprApFabricVnetEpIfRole
    MAX-ACCESS   read-only
    STATUS       current
    DESCRIPTION
        "Cisco Firepower fabric:BHVlan:ifRole managed object property"
    ::= { cfprApFabricBHVlanEntry 8 }

cfprApFabricBHVlanIfType OBJECT-TYPE
    SYNTAX       CfprApNetworkVnetEpIfType
    MAX-ACCESS   read-only
    STATUS       current
    DESCRIPTION
        "Cisco Firepower fabric:BHVlan:ifType managed object property"
    ::= { cfprApFabricBHVlanEntry 9 }

cfprApFabricBHVlanLocale OBJECT-TYPE
    SYNTAX       CfprApFabricVnetEpLocale
    MAX-ACCESS   read-only
    STATUS       current
    DESCRIPTION
        "Cisco Firepower fabric:BHVlan:locale managed object property"
    ::= { cfprApFabricBHVlanEntry 10 }

cfprApFabricBHVlanName OBJECT-TYPE
    SYNTAX       SnmpAdminString
    MAX-ACCESS   read-only
    STATUS       current
    DESCRIPTION
        "Cisco Firepower fabric:BHVlan:name managed object property"
    ::= { cfprApFabricBHVlanEntry 11 }

cfprApFabricBHVlanOperState OBJECT-TYPE
    SYNTAX       CfprApFabricVlanOperState
    MAX-ACCESS   read-only
    STATUS       current
    DESCRIPTION
        "Cisco Firepower fabric:BHVlan:operState managed object property"
    ::= { cfprApFabricBHVlanEntry 12 }

cfprApFabricBHVlanOverlapStateForA OBJECT-TYPE
    SYNTAX       CfprApFabricVlanOverlapState
    MAX-ACCESS   read-only
    STATUS       current
    DESCRIPTION
        "Cisco Firepower fabric:BHVlan:overlapStateForA
        managed object property"
    ::= { cfprApFabricBHVlanEntry 13 }

cfprApFabricBHVlanOverlapStateForB OBJECT-TYPE
    SYNTAX       CfprApFabricVlanOverlapState
    MAX-ACCESS   read-only
    STATUS       current
    DESCRIPTION
        "Cisco Firepower fabric:BHVlan:overlapStateForB
        managed object property"
    ::= { cfprApFabricBHVlanEntry 14 }

cfprApFabricBHVlanPeerDn OBJECT-TYPE
    SYNTAX       SnmpAdminString
    MAX-ACCESS   read-only
    STATUS       current
    DESCRIPTION
        "Cisco Firepower fabric:BHVlan:peerDn managed object property"
    ::= { cfprApFabricBHVlanEntry 15 }

cfprApFabricBHVlanPolicyOwner OBJECT-TYPE
    SYNTAX       CfprApFabricVnetEpPolicyOwner
    MAX-ACCESS   read-only
    STATUS       current
    DESCRIPTION
        "Cisco Firepower fabric:BHVlan:policyOwner managed
        object property"
    ::= { cfprApFabricBHVlanEntry 16 }

cfprApFabricBHVlanPubNwDn OBJECT-TYPE
    SYNTAX       SnmpAdminString
    MAX-ACCESS   read-only
    STATUS       current
    DESCRIPTION
        "Cisco Firepower fabric:BHVlan:pubNwDn managed object property"
    ::= { cfprApFabricBHVlanEntry 17 }

cfprApFabricBHVlanPubNwId OBJECT-TYPE
    SYNTAX       Gauge32
    MAX-ACCESS   read-only
    STATUS       current
    DESCRIPTION
        "Cisco Firepower fabric:BHVlan:pubNwId managed object property"
    ::= { cfprApFabricBHVlanEntry 18 }

cfprApFabricBHVlanPubNwName OBJECT-TYPE
    SYNTAX       SnmpAdminString
    MAX-ACCESS   read-only
    STATUS       current
    DESCRIPTION
        "Cisco Firepower fabric:BHVlan:pubNwName managed object property"
    ::= { cfprApFabricBHVlanEntry 19 }

cfprApFabricBHVlanSharing OBJECT-TYPE
    SYNTAX       CfprApFabricAVlanSharing
    MAX-ACCESS   read-only
    STATUS       current
    DESCRIPTION
        "Cisco Firepower fabric:BHVlan:sharing managed object property"
    ::= { cfprApFabricBHVlanEntry 20 }

cfprApFabricBHVlanSwitchId OBJECT-TYPE
    SYNTAX       CfprApFabricBHVlanSwitchId
    MAX-ACCESS   read-only
    STATUS       current
    DESCRIPTION
        "Cisco Firepower fabric:BHVlan:switchId managed object property"
    ::= { cfprApFabricBHVlanEntry 21 }

cfprApFabricBHVlanTransport OBJECT-TYPE
    SYNTAX       CfprApFabricAVlanTransport
    MAX-ACCESS   read-only
    STATUS       current
    DESCRIPTION
        "Cisco Firepower fabric:BHVlan:transport managed object property"
    ::= { cfprApFabricBHVlanEntry 22 }

cfprApFabricBHVlanType OBJECT-TYPE
    SYNTAX       CfprApFabricAVlanType
    MAX-ACCESS   read-only
    STATUS       current
    DESCRIPTION
        "Cisco Firepower fabric:BHVlan:type managed object property"
    ::= { cfprApFabricBHVlanEntry 23 }

cfprApFabricBreakoutTable OBJECT-TYPE
    SYNTAX           SEQUENCE OF CfprApFabricBreakoutEntry
    MAX-ACCESS       not-accessible
    STATUS           current
    DESCRIPTION
        "Cisco Firepower fabric:Breakout managed object table"
    ::= { cfprApFabricObjects 2 }

cfprApFabricBreakoutEntry OBJECT-TYPE
    SYNTAX           CfprApFabricBreakoutEntry
    MAX-ACCESS       not-accessible
    STATUS           current
    DESCRIPTION
        "Entry for the cfprApFabricBreakoutTable table."
    INDEX { cfprApFabricBreakoutInstanceId }
    ::= { cfprApFabricBreakoutTable 1 }

CfprApFabricBreakoutEntry ::= SEQUENCE {
    cfprApFabricBreakoutInstanceId                                   CfprApManagedObjectId,
    cfprApFabricBreakoutDn                                           CfprApManagedObjectDn,
    cfprApFabricBreakoutRn                                           SnmpAdminString,
    cfprApFabricBreakoutBreakoutType                                 CfprApFabricBreakoutType,
    cfprApFabricBreakoutPortId                                       CfprApFabricBreakoutPortId,
    cfprApFabricBreakoutSlotId                                       CfprApFabricBreakoutSlotId
}

cfprApFabricBreakoutInstanceId OBJECT-TYPE
    SYNTAX       CfprApManagedObjectId
    MAX-ACCESS   not-accessible
    STATUS       current
    DESCRIPTION
        "Instance identifier of the managed object."
    ::= { cfprApFabricBreakoutEntry 1 }

cfprApFabricBreakoutDn OBJECT-TYPE
    SYNTAX       CfprApManagedObjectDn
    MAX-ACCESS   read-only
    STATUS       current
    DESCRIPTION
        "Cisco Firepower fabric:Breakout:dn managed object property"
    ::= { cfprApFabricBreakoutEntry 2 }

cfprApFabricBreakoutRn OBJECT-TYPE
    SYNTAX       SnmpAdminString
    MAX-ACCESS   read-only
    STATUS       current
    DESCRIPTION
        "Cisco Firepower fabric:Breakout:rn managed object property"
    ::= { cfprApFabricBreakoutEntry 3 }

cfprApFabricBreakoutBreakoutType OBJECT-TYPE
    SYNTAX       CfprApFabricBreakoutType
    MAX-ACCESS   read-only
    STATUS       current
    DESCRIPTION
        "Cisco Firepower fabric:Breakout:breakoutType managed
        object property"
    ::= { cfprApFabricBreakoutEntry 4 }

cfprApFabricBreakoutPortId OBJECT-TYPE
    SYNTAX       CfprApFabricBreakoutPortId
    MAX-ACCESS   read-only
    STATUS       current
    DESCRIPTION
        "Cisco Firepower fabric:Breakout:portId managed object property"
    ::= { cfprApFabricBreakoutEntry 5 }

cfprApFabricBreakoutSlotId OBJECT-TYPE
    SYNTAX       CfprApFabricBreakoutSlotId
    MAX-ACCESS   read-only
    STATUS       current
    DESCRIPTION
        "Cisco Firepower fabric:Breakout:slotId managed object property"
    ::= { cfprApFabricBreakoutEntry 6 }

cfprApFabricCablingSwTable OBJECT-TYPE
    SYNTAX           SEQUENCE OF CfprApFabricCablingSwEntry
    MAX-ACCESS       not-accessible
    STATUS           current
    DESCRIPTION
        "Cisco Firepower fabric:CablingSw managed object table"
    ::= { cfprApFabricObjects 4 }

cfprApFabricCablingSwEntry OBJECT-TYPE
    SYNTAX           CfprApFabricCablingSwEntry
    MAX-ACCESS       not-accessible
    STATUS           current
    DESCRIPTION
        "Entry for the cfprApFabricCablingSwTable table."
    INDEX { cfprApFabricCablingSwInstanceId }
    ::= { cfprApFabricCablingSwTable 1 }

CfprApFabricCablingSwEntry ::= SEQUENCE {
    cfprApFabricCablingSwInstanceId                                  CfprApManagedObjectId,
    cfprApFabricCablingSwDn                                          CfprApManagedObjectDn,
    cfprApFabricCablingSwRn                                          SnmpAdminString,
    cfprApFabricCablingSwId                                          CfprApNetworkSwitchId,
    cfprApFabricCablingSwLocale                                      CfprApFabricExternalLocale,
    cfprApFabricCablingSwName                                        SnmpAdminString,
    cfprApFabricCablingSwTransport                                   CfprApNetworkTransport,
    cfprApFabricCablingSwType                                        CfprApNetworkConnectionType
}

cfprApFabricCablingSwInstanceId OBJECT-TYPE
    SYNTAX       CfprApManagedObjectId
    MAX-ACCESS   not-accessible
    STATUS       current
    DESCRIPTION
        "Instance identifier of the managed object."
    ::= { cfprApFabricCablingSwEntry 1 }

cfprApFabricCablingSwDn OBJECT-TYPE
    SYNTAX       CfprApManagedObjectDn
    MAX-ACCESS   read-only
    STATUS       current
    DESCRIPTION
        "Cisco Firepower fabric:CablingSw:dn managed object property"
    ::= { cfprApFabricCablingSwEntry 2 }

cfprApFabricCablingSwRn OBJECT-TYPE
    SYNTAX       SnmpAdminString
    MAX-ACCESS   read-only
    STATUS       current
    DESCRIPTION
        "Cisco Firepower fabric:CablingSw:rn managed object property"
    ::= { cfprApFabricCablingSwEntry 3 }

cfprApFabricCablingSwId OBJECT-TYPE
    SYNTAX       CfprApNetworkSwitchId
    MAX-ACCESS   read-only
    STATUS       current
    DESCRIPTION
        "Cisco Firepower fabric:CablingSw:id managed object property"
    ::= { cfprApFabricCablingSwEntry 4 }

cfprApFabricCablingSwLocale OBJECT-TYPE
    SYNTAX       CfprApFabricExternalLocale
    MAX-ACCESS   read-only
    STATUS       current
    DESCRIPTION
        "Cisco Firepower fabric:CablingSw:locale managed object property"
    ::= { cfprApFabricCablingSwEntry 5 }

cfprApFabricCablingSwName OBJECT-TYPE
    SYNTAX       SnmpAdminString
    MAX-ACCESS   read-only
    STATUS       current
    DESCRIPTION
        "Cisco Firepower fabric:CablingSw:name managed object property"
    ::= { cfprApFabricCablingSwEntry 6 }

cfprApFabricCablingSwTransport OBJECT-TYPE
    SYNTAX       CfprApNetworkTransport
    MAX-ACCESS   read-only
    STATUS       current
    DESCRIPTION
        "Cisco Firepower fabric:CablingSw:transport managed
        object property"
    ::= { cfprApFabricCablingSwEntry 7 }

cfprApFabricCablingSwType OBJECT-TYPE
    SYNTAX       CfprApNetworkConnectionType
    MAX-ACCESS   read-only
    STATUS       current
    DESCRIPTION
        "Cisco Firepower fabric:CablingSw:type managed object property"
    ::= { cfprApFabricCablingSwEntry 8 }

cfprApFabricCdpLinkPolicyTable OBJECT-TYPE
    SYNTAX           SEQUENCE OF CfprApFabricCdpLinkPolicyEntry
    MAX-ACCESS       not-accessible
    STATUS           current
    DESCRIPTION
        "Cisco Firepower fabric:CdpLinkPolicy managed object table"
    ::= { cfprApFabricObjects 5 }

cfprApFabricCdpLinkPolicyEntry OBJECT-TYPE
    SYNTAX           CfprApFabricCdpLinkPolicyEntry
    MAX-ACCESS       not-accessible
    STATUS           current
    DESCRIPTION
        "Entry for the cfprApFabricCdpLinkPolicyTable table."
    INDEX { cfprApFabricCdpLinkPolicyInstanceId }
    ::= { cfprApFabricCdpLinkPolicyTable 1 }

CfprApFabricCdpLinkPolicyEntry ::= SEQUENCE {
    cfprApFabricCdpLinkPolicyInstanceId                              CfprApManagedObjectId,
    cfprApFabricCdpLinkPolicyDn                                      CfprApManagedObjectDn,
    cfprApFabricCdpLinkPolicyRn                                      SnmpAdminString,
    cfprApFabricCdpLinkPolicyAdminState                              CfprApFabricCdpLinkPolicyAdminState,
    cfprApFabricCdpLinkPolicyDescr                                   SnmpAdminString,
    cfprApFabricCdpLinkPolicyIntId                                   SnmpAdminString,
    cfprApFabricCdpLinkPolicyName                                    SnmpAdminString,
    cfprApFabricCdpLinkPolicyPolicyLevel                             Gauge32,
    cfprApFabricCdpLinkPolicyPolicyOwner                             CfprApPolicyPolicyOwner,
    cfprApFabricCdpLinkPolicyProtocol                                CfprApFabricEthCdpPolicyProtocol,
    cfprApFabricCdpLinkPolicyType                                    CfprApFabricEthLinkPolicyType
}

cfprApFabricCdpLinkPolicyInstanceId OBJECT-TYPE
    SYNTAX       CfprApManagedObjectId
    MAX-ACCESS   not-accessible
    STATUS       current
    DESCRIPTION
        "Instance identifier of the managed object."
    ::= { cfprApFabricCdpLinkPolicyEntry 1 }

cfprApFabricCdpLinkPolicyDn OBJECT-TYPE
    SYNTAX       CfprApManagedObjectDn
    MAX-ACCESS   read-only
    STATUS       current
    DESCRIPTION
        "Cisco Firepower fabric:CdpLinkPolicy:dn managed object property"
    ::= { cfprApFabricCdpLinkPolicyEntry 2 }

cfprApFabricCdpLinkPolicyRn OBJECT-TYPE
    SYNTAX       SnmpAdminString
    MAX-ACCESS   read-only
    STATUS       current
    DESCRIPTION
        "Cisco Firepower fabric:CdpLinkPolicy:rn managed object property"
    ::= { cfprApFabricCdpLinkPolicyEntry 3 }

cfprApFabricCdpLinkPolicyAdminState OBJECT-TYPE
    SYNTAX       CfprApFabricCdpLinkPolicyAdminState
    MAX-ACCESS   read-only
    STATUS       current
    DESCRIPTION
        "Cisco Firepower fabric:CdpLinkPolicy:adminState
        managed object property"
    ::= { cfprApFabricCdpLinkPolicyEntry 4 }

cfprApFabricCdpLinkPolicyDescr OBJECT-TYPE
    SYNTAX       SnmpAdminString
    MAX-ACCESS   read-only
    STATUS       current
    DESCRIPTION
        "Cisco Firepower fabric:CdpLinkPolicy:descr managed
        object property"
    ::= { cfprApFabricCdpLinkPolicyEntry 5 }

cfprApFabricCdpLinkPolicyIntId OBJECT-TYPE
    SYNTAX       SnmpAdminString
    MAX-ACCESS   read-only
    STATUS       current
    DESCRIPTION
        "Cisco Firepower fabric:CdpLinkPolicy:intId managed
        object property"
    ::= { cfprApFabricCdpLinkPolicyEntry 6 }

cfprApFabricCdpLinkPolicyName OBJECT-TYPE
    SYNTAX       SnmpAdminString
    MAX-ACCESS   read-only
    STATUS       current
    DESCRIPTION
        "Cisco Firepower fabric:CdpLinkPolicy:name managed
        object property"
    ::= { cfprApFabricCdpLinkPolicyEntry 7 }

cfprApFabricCdpLinkPolicyPolicyLevel OBJECT-TYPE
    SYNTAX       Gauge32
    MAX-ACCESS   read-only
    STATUS       current
    DESCRIPTION
        "Cisco Firepower fabric:CdpLinkPolicy:policyLevel
        managed object property"
    ::= { cfprApFabricCdpLinkPolicyEntry 8 }

cfprApFabricCdpLinkPolicyPolicyOwner OBJECT-TYPE
    SYNTAX       CfprApPolicyPolicyOwner
    MAX-ACCESS   read-only
    STATUS       current
    DESCRIPTION
        "Cisco Firepower fabric:CdpLinkPolicy:policyOwner
        managed object property"
    ::= { cfprApFabricCdpLinkPolicyEntry 9 }

cfprApFabricCdpLinkPolicyProtocol OBJECT-TYPE
    SYNTAX       CfprApFabricEthCdpPolicyProtocol
    MAX-ACCESS   read-only
    STATUS       current
    DESCRIPTION
        "Cisco Firepower fabric:CdpLinkPolicy:protocol
        managed object property"
    ::= { cfprApFabricCdpLinkPolicyEntry 10 }

cfprApFabricCdpLinkPolicyType OBJECT-TYPE
    SYNTAX       CfprApFabricEthLinkPolicyType
    MAX-ACCESS   read-only
    STATUS       current
    DESCRIPTION
        "Cisco Firepower fabric:CdpLinkPolicy:type managed
        object property"
    ::= { cfprApFabricCdpLinkPolicyEntry 11 }

cfprApFabricChangedObjectRefTable OBJECT-TYPE
    SYNTAX           SEQUENCE OF CfprApFabricChangedObjectRefEntry
    MAX-ACCESS       not-accessible
    STATUS           current
    DESCRIPTION
        "Cisco Firepower fabric:ChangedObjectRef managed object table"
    ::= { cfprApFabricObjects 6 }

cfprApFabricChangedObjectRefEntry OBJECT-TYPE
    SYNTAX           CfprApFabricChangedObjectRefEntry
    MAX-ACCESS       not-accessible
    STATUS           current
    DESCRIPTION
        "Entry for the cfprApFabricChangedObjectRefTable table."
    INDEX { cfprApFabricChangedObjectRefInstanceId }
    ::= { cfprApFabricChangedObjectRefTable 1 }

CfprApFabricChangedObjectRefEntry ::= SEQUENCE {
    cfprApFabricChangedObjectRefInstanceId                           CfprApManagedObjectId,
    cfprApFabricChangedObjectRefDn                                   CfprApManagedObjectDn,
    cfprApFabricChangedObjectRefRn                                   SnmpAdminString,
    cfprApFabricChangedObjectRefCentraleVnetEpDn                     SnmpAdminString,
    cfprApFabricChangedObjectRefId                                   Gauge32,
    cfprApFabricChangedObjectRefOldCentraleVnetEpDn                  SnmpAdminString,
    cfprApFabricChangedObjectRefRefObjStatus                         CfprApFabricStatus,
    cfprApFabricChangedObjectRefUcsmVnetEpDn                         SnmpAdminString
}

cfprApFabricChangedObjectRefInstanceId OBJECT-TYPE
    SYNTAX       CfprApManagedObjectId
    MAX-ACCESS   not-accessible
    STATUS       current
    DESCRIPTION
        "Instance identifier of the managed object."
    ::= { cfprApFabricChangedObjectRefEntry 1 }

cfprApFabricChangedObjectRefDn OBJECT-TYPE
    SYNTAX       CfprApManagedObjectDn
    MAX-ACCESS   read-only
    STATUS       current
    DESCRIPTION
        "Cisco Firepower fabric:ChangedObjectRef:dn managed
        object property"
    ::= { cfprApFabricChangedObjectRefEntry 2 }

cfprApFabricChangedObjectRefRn OBJECT-TYPE
    SYNTAX       SnmpAdminString
    MAX-ACCESS   read-only
    STATUS       current
    DESCRIPTION
        "Cisco Firepower fabric:ChangedObjectRef:rn managed
        object property"
    ::= { cfprApFabricChangedObjectRefEntry 3 }

cfprApFabricChangedObjectRefCentraleVnetEpDn OBJECT-TYPE
    SYNTAX       SnmpAdminString
    MAX-ACCESS   read-only
    STATUS       current
    DESCRIPTION
        "Cisco Firepower fabric:ChangedObjectRef:centraleVnetEpDn
        managed object property"
    ::= { cfprApFabricChangedObjectRefEntry 4 }

cfprApFabricChangedObjectRefId OBJECT-TYPE
    SYNTAX       Gauge32
    MAX-ACCESS   read-only
    STATUS       current
    DESCRIPTION
        "Cisco Firepower fabric:ChangedObjectRef:id managed
        object property"
    ::= { cfprApFabricChangedObjectRefEntry 5 }

cfprApFabricChangedObjectRefOldCentraleVnetEpDn OBJECT-TYPE
    SYNTAX       SnmpAdminString
    MAX-ACCESS   read-only
    STATUS       current
    DESCRIPTION
        "Cisco Firepower fabric:ChangedObjectRef:oldCentraleVnetEpDn
        managed object property"
    ::= { cfprApFabricChangedObjectRefEntry 6 }

cfprApFabricChangedObjectRefRefObjStatus OBJECT-TYPE
    SYNTAX       CfprApFabricStatus
    MAX-ACCESS   read-only
    STATUS       current
    DESCRIPTION
        "Cisco Firepower fabric:ChangedObjectRef:refObjStatus
        managed object property"
    ::= { cfprApFabricChangedObjectRefEntry 7 }

cfprApFabricChangedObjectRefUcsmVnetEpDn OBJECT-TYPE
    SYNTAX       SnmpAdminString
    MAX-ACCESS   read-only
    STATUS       current
    DESCRIPTION
        "Cisco Firepower fabric:ChangedObjectRef:ucsmVnetEpDn
        managed object property"
    ::= { cfprApFabricChangedObjectRefEntry 8 }

cfprApFabricChassisEpTable OBJECT-TYPE
    SYNTAX           SEQUENCE OF CfprApFabricChassisEpEntry
    MAX-ACCESS       not-accessible
    STATUS           current
    DESCRIPTION
        "Cisco Firepower fabric:ChassisEp managed object table"
    ::= { cfprApFabricObjects 7 }

cfprApFabricChassisEpEntry OBJECT-TYPE
    SYNTAX           CfprApFabricChassisEpEntry
    MAX-ACCESS       not-accessible
    STATUS           current
    DESCRIPTION
        "Entry for the cfprApFabricChassisEpTable table."
    INDEX { cfprApFabricChassisEpInstanceId }
    ::= { cfprApFabricChassisEpTable 1 }

CfprApFabricChassisEpEntry ::= SEQUENCE {
    cfprApFabricChassisEpInstanceId                                  CfprApManagedObjectId,
    cfprApFabricChassisEpDn                                          CfprApManagedObjectDn,
    cfprApFabricChassisEpRn                                          SnmpAdminString,
    cfprApFabricChassisEpAdminState                                  CfprApFabricInternalEpAdminState,
    cfprApFabricChassisEpAggrPortId                                  Gauge32,
    cfprApFabricChassisEpChassisDn                                   SnmpAdminString,
    cfprApFabricChassisEpChassisId                                   Gauge32,
    cfprApFabricChassisEpEpDn                                        SnmpAdminString,
    cfprApFabricChassisEpFltAggr                                     Unsigned64,
    cfprApFabricChassisEpIfRole                                      CfprApFabricComputeEpIfRole,
    cfprApFabricChassisEpIfType                                      CfprApFabricPIoEpIfType,
    cfprApFabricChassisEpLicGP                                       Unsigned64,
    cfprApFabricChassisEpLicState                                    CfprApLicenseState,
    cfprApFabricChassisEpLocale                                      CfprApFabricInternalEpLocale,
    cfprApFabricChassisEpModel                                       SnmpAdminString,
    cfprApFabricChassisEpName                                        SnmpAdminString,
    cfprApFabricChassisEpOperState                                   CfprApFabricPIoEpOperState,
    cfprApFabricChassisEpOperStateReason                             SnmpAdminString,
    cfprApFabricChassisEpPeerAggrPortId                              Gauge32,
    cfprApFabricChassisEpPeerChassisId                               Gauge32,
    cfprApFabricChassisEpPeerDn                                      SnmpAdminString,
    cfprApFabricChassisEpPeerPortId                                  Gauge32,
    cfprApFabricChassisEpPeerSlotId                                  Gauge32,
    cfprApFabricChassisEpPortId                                      CfprApFabricPIoEpPortId,
    cfprApFabricChassisEpRevision                                    SnmpAdminString,
    cfprApFabricChassisEpSerial                                      SnmpAdminString,
    cfprApFabricChassisEpSlotId                                      CfprApFabricPIoEpSlotId,
    cfprApFabricChassisEpSwitchId                                    CfprApNetworkSwitchId,
    cfprApFabricChassisEpTransport                                   CfprApNetworkTransport,
    cfprApFabricChassisEpType                                        CfprApFabricComputeEpType,
    cfprApFabricChassisEpVendor                                      SnmpAdminString
}

cfprApFabricChassisEpInstanceId OBJECT-TYPE
    SYNTAX       CfprApManagedObjectId
    MAX-ACCESS   not-accessible
    STATUS       current
    DESCRIPTION
        "Instance identifier of the managed object."
    ::= { cfprApFabricChassisEpEntry 1 }

cfprApFabricChassisEpDn OBJECT-TYPE
    SYNTAX       CfprApManagedObjectDn
    MAX-ACCESS   read-only
    STATUS       current
    DESCRIPTION
        "Cisco Firepower fabric:ChassisEp:dn managed object property"
    ::= { cfprApFabricChassisEpEntry 2 }

cfprApFabricChassisEpRn OBJECT-TYPE
    SYNTAX       SnmpAdminString
    MAX-ACCESS   read-only
    STATUS       current
    DESCRIPTION
        "Cisco Firepower fabric:ChassisEp:rn managed object property"
    ::= { cfprApFabricChassisEpEntry 3 }

cfprApFabricChassisEpAdminState OBJECT-TYPE
    SYNTAX       CfprApFabricInternalEpAdminState
    MAX-ACCESS   read-only
    STATUS       current
    DESCRIPTION
        "Cisco Firepower fabric:ChassisEp:adminState managed
        object property"
    ::= { cfprApFabricChassisEpEntry 4 }

cfprApFabricChassisEpAggrPortId OBJECT-TYPE
    SYNTAX       Gauge32
    MAX-ACCESS   read-only
    STATUS       current
    DESCRIPTION
        "Cisco Firepower fabric:ChassisEp:aggrPortId managed
        object property"
    ::= { cfprApFabricChassisEpEntry 5 }

cfprApFabricChassisEpChassisDn OBJECT-TYPE
    SYNTAX       SnmpAdminString
    MAX-ACCESS   read-only
    STATUS       current
    DESCRIPTION
        "Cisco Firepower fabric:ChassisEp:chassisDn managed
        object property"
    ::= { cfprApFabricChassisEpEntry 6 }

cfprApFabricChassisEpChassisId OBJECT-TYPE
    SYNTAX       Gauge32
    MAX-ACCESS   read-only
    STATUS       current
    DESCRIPTION
        "Cisco Firepower fabric:ChassisEp:chassisId managed
        object property"
    ::= { cfprApFabricChassisEpEntry 7 }

cfprApFabricChassisEpEpDn OBJECT-TYPE
    SYNTAX       SnmpAdminString
    MAX-ACCESS   read-only
    STATUS       current
    DESCRIPTION
        "Cisco Firepower fabric:ChassisEp:epDn managed object property"
    ::= { cfprApFabricChassisEpEntry 8 }

cfprApFabricChassisEpFltAggr OBJECT-TYPE
    SYNTAX       Unsigned64
    MAX-ACCESS   read-only
    STATUS       current
    DESCRIPTION
        "Cisco Firepower fabric:ChassisEp:fltAggr managed object property"
    ::= { cfprApFabricChassisEpEntry 9 }

cfprApFabricChassisEpIfRole OBJECT-TYPE
    SYNTAX       CfprApFabricComputeEpIfRole
    MAX-ACCESS   read-only
    STATUS       current
    DESCRIPTION
        "Cisco Firepower fabric:ChassisEp:ifRole managed object property"
    ::= { cfprApFabricChassisEpEntry 10 }

cfprApFabricChassisEpIfType OBJECT-TYPE
    SYNTAX       CfprApFabricPIoEpIfType
    MAX-ACCESS   read-only
    STATUS       current
    DESCRIPTION
        "Cisco Firepower fabric:ChassisEp:ifType managed object property"
    ::= { cfprApFabricChassisEpEntry 11 }

cfprApFabricChassisEpLicGP OBJECT-TYPE
    SYNTAX       Unsigned64
    MAX-ACCESS   read-only
    STATUS       current
    DESCRIPTION
        "Cisco Firepower fabric:ChassisEp:licGP managed object property"
    ::= { cfprApFabricChassisEpEntry 12 }

cfprApFabricChassisEpLicState OBJECT-TYPE
    SYNTAX       CfprApLicenseState
    MAX-ACCESS   read-only
    STATUS       current
    DESCRIPTION
        "Cisco Firepower fabric:ChassisEp:licState managed
        object property"
    ::= { cfprApFabricChassisEpEntry 13 }

cfprApFabricChassisEpLocale OBJECT-TYPE
    SYNTAX       CfprApFabricInternalEpLocale
    MAX-ACCESS   read-only
    STATUS       current
    DESCRIPTION
        "Cisco Firepower fabric:ChassisEp:locale managed object property"
    ::= { cfprApFabricChassisEpEntry 14 }

cfprApFabricChassisEpModel OBJECT-TYPE
    SYNTAX       SnmpAdminString
    MAX-ACCESS   read-only
    STATUS       current
    DESCRIPTION
        "Cisco Firepower fabric:ChassisEp:model managed object property"
    ::= { cfprApFabricChassisEpEntry 15 }

cfprApFabricChassisEpName OBJECT-TYPE
    SYNTAX       SnmpAdminString
    MAX-ACCESS   read-only
    STATUS       current
    DESCRIPTION
        "Cisco Firepower fabric:ChassisEp:name managed object property"
    ::= { cfprApFabricChassisEpEntry 16 }

cfprApFabricChassisEpOperState OBJECT-TYPE
    SYNTAX       CfprApFabricPIoEpOperState
    MAX-ACCESS   read-only
    STATUS       current
    DESCRIPTION
        "Cisco Firepower fabric:ChassisEp:operState managed
        object property"
    ::= { cfprApFabricChassisEpEntry 17 }

cfprApFabricChassisEpOperStateReason OBJECT-TYPE
    SYNTAX       SnmpAdminString
    MAX-ACCESS   read-only
    STATUS       current
    DESCRIPTION
        "Cisco Firepower fabric:ChassisEp:operStateReason
        managed object property"
    ::= { cfprApFabricChassisEpEntry 18 }

cfprApFabricChassisEpPeerAggrPortId OBJECT-TYPE
    SYNTAX       Gauge32
    MAX-ACCESS   read-only
    STATUS       current
    DESCRIPTION
        "Cisco Firepower fabric:ChassisEp:peerAggrPortId
        managed object property"
    ::= { cfprApFabricChassisEpEntry 19 }

cfprApFabricChassisEpPeerChassisId OBJECT-TYPE
    SYNTAX       Gauge32
    MAX-ACCESS   read-only
    STATUS       current
    DESCRIPTION
        "Cisco Firepower fabric:ChassisEp:peerChassisId
        managed object property"
    ::= { cfprApFabricChassisEpEntry 20 }

cfprApFabricChassisEpPeerDn OBJECT-TYPE
    SYNTAX       SnmpAdminString
    MAX-ACCESS   read-only
    STATUS       current
    DESCRIPTION
        "Cisco Firepower fabric:ChassisEp:peerDn managed object property"
    ::= { cfprApFabricChassisEpEntry 21 }

cfprApFabricChassisEpPeerPortId OBJECT-TYPE
    SYNTAX       Gauge32
    MAX-ACCESS   read-only
    STATUS       current
    DESCRIPTION
        "Cisco Firepower fabric:ChassisEp:peerPortId managed
        object property"
    ::= { cfprApFabricChassisEpEntry 22 }

cfprApFabricChassisEpPeerSlotId OBJECT-TYPE
    SYNTAX       Gauge32
    MAX-ACCESS   read-only
    STATUS       current
    DESCRIPTION
        "Cisco Firepower fabric:ChassisEp:peerSlotId managed
        object property"
    ::= { cfprApFabricChassisEpEntry 23 }

cfprApFabricChassisEpPortId OBJECT-TYPE
    SYNTAX       CfprApFabricPIoEpPortId
    MAX-ACCESS   read-only
    STATUS       current
    DESCRIPTION
        "Cisco Firepower fabric:ChassisEp:portId managed object property"
    ::= { cfprApFabricChassisEpEntry 24 }

cfprApFabricChassisEpRevision OBJECT-TYPE
    SYNTAX       SnmpAdminString
    MAX-ACCESS   read-only
    STATUS       current
    DESCRIPTION
        "Cisco Firepower fabric:ChassisEp:revision managed
        object property"
    ::= { cfprApFabricChassisEpEntry 25 }

cfprApFabricChassisEpSerial OBJECT-TYPE
    SYNTAX       SnmpAdminString
    MAX-ACCESS   read-only
    STATUS       current
    DESCRIPTION
        "Cisco Firepower fabric:ChassisEp:serial managed object property"
    ::= { cfprApFabricChassisEpEntry 26 }

cfprApFabricChassisEpSlotId OBJECT-TYPE
    SYNTAX       CfprApFabricPIoEpSlotId
    MAX-ACCESS   read-only
    STATUS       current
    DESCRIPTION
        "Cisco Firepower fabric:ChassisEp:slotId managed object property"
    ::= { cfprApFabricChassisEpEntry 27 }

cfprApFabricChassisEpSwitchId OBJECT-TYPE
    SYNTAX       CfprApNetworkSwitchId
    MAX-ACCESS   read-only
    STATUS       current
    DESCRIPTION
        "Cisco Firepower fabric:ChassisEp:switchId managed
        object property"
    ::= { cfprApFabricChassisEpEntry 28 }

cfprApFabricChassisEpTransport OBJECT-TYPE
    SYNTAX       CfprApNetworkTransport
    MAX-ACCESS   read-only
    STATUS       current
    DESCRIPTION
        "Cisco Firepower fabric:ChassisEp:transport managed
        object property"
    ::= { cfprApFabricChassisEpEntry 29 }

cfprApFabricChassisEpType OBJECT-TYPE
    SYNTAX       CfprApFabricComputeEpType
    MAX-ACCESS   read-only
    STATUS       current
    DESCRIPTION
        "Cisco Firepower fabric:ChassisEp:type managed object property"
    ::= { cfprApFabricChassisEpEntry 30 }

cfprApFabricChassisEpVendor OBJECT-TYPE
    SYNTAX       SnmpAdminString
    MAX-ACCESS   read-only
    STATUS       current
    DESCRIPTION
        "Cisco Firepower fabric:ChassisEp:vendor managed object property"
    ::= { cfprApFabricChassisEpEntry 31 }

cfprApFabricComputePhEpTable OBJECT-TYPE
    SYNTAX           SEQUENCE OF CfprApFabricComputePhEpEntry
    MAX-ACCESS       not-accessible
    STATUS           current
    DESCRIPTION
        "Cisco Firepower fabric:ComputePhEp managed object table"
    ::= { cfprApFabricObjects 8 }

cfprApFabricComputePhEpEntry OBJECT-TYPE
    SYNTAX           CfprApFabricComputePhEpEntry
    MAX-ACCESS       not-accessible
    STATUS           current
    DESCRIPTION
        "Entry for the cfprApFabricComputePhEpTable table."
    INDEX { cfprApFabricComputePhEpInstanceId }
    ::= { cfprApFabricComputePhEpTable 1 }

CfprApFabricComputePhEpEntry ::= SEQUENCE {
    cfprApFabricComputePhEpInstanceId                                CfprApManagedObjectId,
    cfprApFabricComputePhEpDn                                        CfprApManagedObjectDn,
    cfprApFabricComputePhEpRn                                        SnmpAdminString,
    cfprApFabricComputePhEpAdminState                                CfprApFabricComputePhEpAdminState,
    cfprApFabricComputePhEpAggrPortId                                Gauge32,
    cfprApFabricComputePhEpBoardAggregationRole                      CfprApEquipmentBoardAggregationRole,
    cfprApFabricComputePhEpChassisId                                 Gauge32,
    cfprApFabricComputePhEpCheckpointTrigTs                          Unsigned64,
    cfprApFabricComputePhEpDeepCheckpointTrigTs                      Unsigned64,
    cfprApFabricComputePhEpDiscTrigTs                                Unsigned64,
    cfprApFabricComputePhEpEpDn                                      SnmpAdminString,
    cfprApFabricComputePhEpEqType                                    CfprApEquipmentFabricEpType,
    cfprApFabricComputePhEpFltAggr                                   Unsigned64,
    cfprApFabricComputePhEpIfRole                                    CfprApFabricComputeEpIfRole,
    cfprApFabricComputePhEpIfType                                    CfprApFabricPIoEpIfType,
    cfprApFabricComputePhEpLc                                        CfprApFabricBladeLifeCycle,
    cfprApFabricComputePhEpLicGP                                     Unsigned64,
    cfprApFabricComputePhEpLicState                                  CfprApLicenseState,
    cfprApFabricComputePhEpLocale                                    CfprApFabricInternalEpLocale,
    cfprApFabricComputePhEpModel                                     SnmpAdminString,
    cfprApFabricComputePhEpName                                      SnmpAdminString,
    cfprApFabricComputePhEpOperState                                 CfprApFabricPIoEpOperState,
    cfprApFabricComputePhEpOperStateReason                           SnmpAdminString,
    cfprApFabricComputePhEpPeerAggrPortId                            Gauge32,
    cfprApFabricComputePhEpPeerChassisId                             Gauge32,
    cfprApFabricComputePhEpPeerDn                                    SnmpAdminString,
    cfprApFabricComputePhEpPeerPortId                                Gauge32,
    cfprApFabricComputePhEpPeerSlotId                                Gauge32,
    cfprApFabricComputePhEpPortId                                    CfprApFabricPIoEpPortId,
    cfprApFabricComputePhEpProfileDn                                 SnmpAdminString,
    cfprApFabricComputePhEpRevision                                  SnmpAdminString,
    cfprApFabricComputePhEpSerial                                    SnmpAdminString,
    cfprApFabricComputePhEpSlotId                                    CfprApFabricPIoEpSlotId,
    cfprApFabricComputePhEpSwitchId                                  CfprApNetworkSwitchId,
    cfprApFabricComputePhEpTransport                                 CfprApNetworkTransport,
    cfprApFabricComputePhEpType                                      CfprApFabricComputeEpType,
    cfprApFabricComputePhEpVendor                                    SnmpAdminString
}

cfprApFabricComputePhEpInstanceId OBJECT-TYPE
    SYNTAX       CfprApManagedObjectId
    MAX-ACCESS   not-accessible
    STATUS       current
    DESCRIPTION
        "Instance identifier of the managed object."
    ::= { cfprApFabricComputePhEpEntry 1 }

cfprApFabricComputePhEpDn OBJECT-TYPE
    SYNTAX       CfprApManagedObjectDn
    MAX-ACCESS   read-only
    STATUS       current
    DESCRIPTION
        "Cisco Firepower fabric:ComputePhEp:dn managed object property"
    ::= { cfprApFabricComputePhEpEntry 2 }

cfprApFabricComputePhEpRn OBJECT-TYPE
    SYNTAX       SnmpAdminString
    MAX-ACCESS   read-only
    STATUS       current
    DESCRIPTION
        "Cisco Firepower fabric:ComputePhEp:rn managed object property"
    ::= { cfprApFabricComputePhEpEntry 3 }

cfprApFabricComputePhEpAdminState OBJECT-TYPE
    SYNTAX       CfprApFabricComputePhEpAdminState
    MAX-ACCESS   read-only
    STATUS       current
    DESCRIPTION
        "Cisco Firepower fabric:ComputePhEp:adminState
        managed object property"
    ::= { cfprApFabricComputePhEpEntry 4 }

cfprApFabricComputePhEpAggrPortId OBJECT-TYPE
    SYNTAX       Gauge32
    MAX-ACCESS   read-only
    STATUS       current
    DESCRIPTION
        "Cisco Firepower fabric:ComputePhEp:aggrPortId
        managed object property"
    ::= { cfprApFabricComputePhEpEntry 5 }

cfprApFabricComputePhEpBoardAggregationRole OBJECT-TYPE
    SYNTAX       CfprApEquipmentBoardAggregationRole
    MAX-ACCESS   read-only
    STATUS       current
    DESCRIPTION
        "Cisco Firepower fabric:ComputePhEp:boardAggregationRole
        managed object property"
    ::= { cfprApFabricComputePhEpEntry 6 }

cfprApFabricComputePhEpChassisId OBJECT-TYPE
    SYNTAX       Gauge32
    MAX-ACCESS   read-only
    STATUS       current
    DESCRIPTION
        "Cisco Firepower fabric:ComputePhEp:chassisId managed
        object property"
    ::= { cfprApFabricComputePhEpEntry 7 }

cfprApFabricComputePhEpCheckpointTrigTs OBJECT-TYPE
    SYNTAX       Unsigned64
    MAX-ACCESS   read-only
    STATUS       current
    DESCRIPTION
        "Cisco Firepower fabric:ComputePhEp:checkpointTrigTs
        managed object property"
    ::= { cfprApFabricComputePhEpEntry 8 }

cfprApFabricComputePhEpDeepCheckpointTrigTs OBJECT-TYPE
    SYNTAX       Unsigned64
    MAX-ACCESS   read-only
    STATUS       current
    DESCRIPTION
        "Cisco Firepower fabric:ComputePhEp:deepCheckpointTrigTs
        managed object property"
    ::= { cfprApFabricComputePhEpEntry 9 }

cfprApFabricComputePhEpDiscTrigTs OBJECT-TYPE
    SYNTAX       Unsigned64
    MAX-ACCESS   read-only
    STATUS       current
    DESCRIPTION
        "Cisco Firepower fabric:ComputePhEp:discTrigTs
        managed object property"
    ::= { cfprApFabricComputePhEpEntry 10 }

cfprApFabricComputePhEpEpDn OBJECT-TYPE
    SYNTAX       SnmpAdminString
    MAX-ACCESS   read-only
    STATUS       current
    DESCRIPTION
        "Cisco Firepower fabric:ComputePhEp:epDn managed object property"
    ::= { cfprApFabricComputePhEpEntry 11 }

cfprApFabricComputePhEpEqType OBJECT-TYPE
    SYNTAX       CfprApEquipmentFabricEpType
    MAX-ACCESS   read-only
    STATUS       current
    DESCRIPTION
        "Cisco Firepower fabric:ComputePhEp:eqType managed
        object property"
    ::= { cfprApFabricComputePhEpEntry 12 }

cfprApFabricComputePhEpFltAggr OBJECT-TYPE
    SYNTAX       Unsigned64
    MAX-ACCESS   read-only
    STATUS       current
    DESCRIPTION
        "Cisco Firepower fabric:ComputePhEp:fltAggr managed
        object property"
    ::= { cfprApFabricComputePhEpEntry 13 }

cfprApFabricComputePhEpIfRole OBJECT-TYPE
    SYNTAX       CfprApFabricComputeEpIfRole
    MAX-ACCESS   read-only
    STATUS       current
    DESCRIPTION
        "Cisco Firepower fabric:ComputePhEp:ifRole managed
        object property"
    ::= { cfprApFabricComputePhEpEntry 14 }

cfprApFabricComputePhEpIfType OBJECT-TYPE
    SYNTAX       CfprApFabricPIoEpIfType
    MAX-ACCESS   read-only
    STATUS       current
    DESCRIPTION
        "Cisco Firepower fabric:ComputePhEp:ifType managed
        object property"
    ::= { cfprApFabricComputePhEpEntry 15 }

cfprApFabricComputePhEpLc OBJECT-TYPE
    SYNTAX       CfprApFabricBladeLifeCycle
    MAX-ACCESS   read-only
    STATUS       current
    DESCRIPTION
        "Cisco Firepower fabric:ComputePhEp:lc managed object property"
    ::= { cfprApFabricComputePhEpEntry 16 }

cfprApFabricComputePhEpLicGP OBJECT-TYPE
    SYNTAX       Unsigned64
    MAX-ACCESS   read-only
    STATUS       current
    DESCRIPTION
        "Cisco Firepower fabric:ComputePhEp:licGP managed object property"
    ::= { cfprApFabricComputePhEpEntry 17 }

cfprApFabricComputePhEpLicState OBJECT-TYPE
    SYNTAX       CfprApLicenseState
    MAX-ACCESS   read-only
    STATUS       current
    DESCRIPTION
        "Cisco Firepower fabric:ComputePhEp:licState managed
        object property"
    ::= { cfprApFabricComputePhEpEntry 18 }

cfprApFabricComputePhEpLocale OBJECT-TYPE
    SYNTAX       CfprApFabricInternalEpLocale
    MAX-ACCESS   read-only
    STATUS       current
    DESCRIPTION
        "Cisco Firepower fabric:ComputePhEp:locale managed
        object property"
    ::= { cfprApFabricComputePhEpEntry 19 }

cfprApFabricComputePhEpModel OBJECT-TYPE
    SYNTAX       SnmpAdminString
    MAX-ACCESS   read-only
    STATUS       current
    DESCRIPTION
        "Cisco Firepower fabric:ComputePhEp:model managed object property"
    ::= { cfprApFabricComputePhEpEntry 20 }

cfprApFabricComputePhEpName OBJECT-TYPE
    SYNTAX       SnmpAdminString
    MAX-ACCESS   read-only
    STATUS       current
    DESCRIPTION
        "Cisco Firepower fabric:ComputePhEp:name managed object property"
    ::= { cfprApFabricComputePhEpEntry 21 }

cfprApFabricComputePhEpOperState OBJECT-TYPE
    SYNTAX       CfprApFabricPIoEpOperState
    MAX-ACCESS   read-only
    STATUS       current
    DESCRIPTION
        "Cisco Firepower fabric:ComputePhEp:operState managed
        object property"
    ::= { cfprApFabricComputePhEpEntry 22 }

cfprApFabricComputePhEpOperStateReason OBJECT-TYPE
    SYNTAX       SnmpAdminString
    MAX-ACCESS   read-only
    STATUS       current
    DESCRIPTION
        "Cisco Firepower fabric:ComputePhEp:operStateReason
        managed object property"
    ::= { cfprApFabricComputePhEpEntry 23 }

cfprApFabricComputePhEpPeerAggrPortId OBJECT-TYPE
    SYNTAX       Gauge32
    MAX-ACCESS   read-only
    STATUS       current
    DESCRIPTION
        "Cisco Firepower fabric:ComputePhEp:peerAggrPortId
        managed object property"
    ::= { cfprApFabricComputePhEpEntry 24 }

cfprApFabricComputePhEpPeerChassisId OBJECT-TYPE
    SYNTAX       Gauge32
    MAX-ACCESS   read-only
    STATUS       current
    DESCRIPTION
        "Cisco Firepower fabric:ComputePhEp:peerChassisId
        managed object property"
    ::= { cfprApFabricComputePhEpEntry 25 }

cfprApFabricComputePhEpPeerDn OBJECT-TYPE
    SYNTAX       SnmpAdminString
    MAX-ACCESS   read-only
    STATUS       current
    DESCRIPTION
        "Cisco Firepower fabric:ComputePhEp:peerDn managed
        object property"
    ::= { cfprApFabricComputePhEpEntry 26 }

cfprApFabricComputePhEpPeerPortId OBJECT-TYPE
    SYNTAX       Gauge32
    MAX-ACCESS   read-only
    STATUS       current
    DESCRIPTION
        "Cisco Firepower fabric:ComputePhEp:peerPortId
        managed object property"
    ::= { cfprApFabricComputePhEpEntry 27 }

cfprApFabricComputePhEpPeerSlotId OBJECT-TYPE
    SYNTAX       Gauge32
    MAX-ACCESS   read-only
    STATUS       current
    DESCRIPTION
        "Cisco Firepower fabric:ComputePhEp:peerSlotId
        managed object property"
    ::= { cfprApFabricComputePhEpEntry 28 }

cfprApFabricComputePhEpPortId OBJECT-TYPE
    SYNTAX       CfprApFabricPIoEpPortId
    MAX-ACCESS   read-only
    STATUS       current
    DESCRIPTION
        "Cisco Firepower fabric:ComputePhEp:portId managed
        object property"
    ::= { cfprApFabricComputePhEpEntry 29 }

cfprApFabricComputePhEpProfileDn OBJECT-TYPE
    SYNTAX       SnmpAdminString
    MAX-ACCESS   read-only
    STATUS       current
    DESCRIPTION
        "Cisco Firepower fabric:ComputePhEp:profileDn managed
        object property"
    ::= { cfprApFabricComputePhEpEntry 30 }

cfprApFabricComputePhEpRevision OBJECT-TYPE
    SYNTAX       SnmpAdminString
    MAX-ACCESS   read-only
    STATUS       current
    DESCRIPTION
        "Cisco Firepower fabric:ComputePhEp:revision managed
        object property"
    ::= { cfprApFabricComputePhEpEntry 31 }

cfprApFabricComputePhEpSerial OBJECT-TYPE
    SYNTAX       SnmpAdminString
    MAX-ACCESS   read-only
    STATUS       current
    DESCRIPTION
        "Cisco Firepower fabric:ComputePhEp:serial managed
        object property"
    ::= { cfprApFabricComputePhEpEntry 32 }

cfprApFabricComputePhEpSlotId OBJECT-TYPE
    SYNTAX       CfprApFabricPIoEpSlotId
    MAX-ACCESS   read-only
    STATUS       current
    DESCRIPTION
        "Cisco Firepower fabric:ComputePhEp:slotId managed
        object property"
    ::= { cfprApFabricComputePhEpEntry 33 }

cfprApFabricComputePhEpSwitchId OBJECT-TYPE
    SYNTAX       CfprApNetworkSwitchId
    MAX-ACCESS   read-only
    STATUS       current
    DESCRIPTION
        "Cisco Firepower fabric:ComputePhEp:switchId managed
        object property"
    ::= { cfprApFabricComputePhEpEntry 34 }

cfprApFabricComputePhEpTransport OBJECT-TYPE
    SYNTAX       CfprApNetworkTransport
    MAX-ACCESS   read-only
    STATUS       current
    DESCRIPTION
        "Cisco Firepower fabric:ComputePhEp:transport managed
        object property"
    ::= { cfprApFabricComputePhEpEntry 35 }

cfprApFabricComputePhEpType OBJECT-TYPE
    SYNTAX       CfprApFabricComputeEpType
    MAX-ACCESS   read-only
    STATUS       current
    DESCRIPTION
        "Cisco Firepower fabric:ComputePhEp:type managed object property"
    ::= { cfprApFabricComputePhEpEntry 36 }

cfprApFabricComputePhEpVendor OBJECT-TYPE
    SYNTAX       SnmpAdminString
    MAX-ACCESS   read-only
    STATUS       current
    DESCRIPTION
        "Cisco Firepower fabric:ComputePhEp:vendor managed
        object property"
    ::= { cfprApFabricComputePhEpEntry 37 }

cfprApFabricComputeSlotEpTable OBJECT-TYPE
    SYNTAX           SEQUENCE OF CfprApFabricComputeSlotEpEntry
    MAX-ACCESS       not-accessible
    STATUS           current
    DESCRIPTION
        "Cisco Firepower fabric:ComputeSlotEp managed object table"
    ::= { cfprApFabricObjects 9 }

cfprApFabricComputeSlotEpEntry OBJECT-TYPE
    SYNTAX           CfprApFabricComputeSlotEpEntry
    MAX-ACCESS       not-accessible
    STATUS           current
    DESCRIPTION
        "Entry for the cfprApFabricComputeSlotEpTable table."
    INDEX { cfprApFabricComputeSlotEpInstanceId }
    ::= { cfprApFabricComputeSlotEpTable 1 }

CfprApFabricComputeSlotEpEntry ::= SEQUENCE {
    cfprApFabricComputeSlotEpInstanceId                              CfprApManagedObjectId,
    cfprApFabricComputeSlotEpDn                                      CfprApManagedObjectDn,
    cfprApFabricComputeSlotEpRn                                      SnmpAdminString,
    cfprApFabricComputeSlotEpAdminState                              CfprApFabricSlotAdminState,
    cfprApFabricComputeSlotEpAggrPortId                              Gauge32,
    cfprApFabricComputeSlotEpBoardAggregationRole                    CfprApEquipmentBoardAggregationRole,
    cfprApFabricComputeSlotEpChassisId                               Gauge32,
    cfprApFabricComputeSlotEpConnPath                                CfprApEquipmentConnectionStatus,
    cfprApFabricComputeSlotEpConnStatus                              CfprApEquipmentConnectionStatus,
    cfprApFabricComputeSlotEpDiscovery                               CfprApComputeDiscovery,
    cfprApFabricComputeSlotEpEpDn                                    SnmpAdminString,
    cfprApFabricComputeSlotEpFactoryResetFlag                        TruthValue,
    cfprApFabricComputeSlotEpFltAggr                                 Unsigned64,
    cfprApFabricComputeSlotEpFruIdentTrigTs                          Unsigned64,
    cfprApFabricComputeSlotEpIfRole                                  CfprApFabricComputeEpIfRole,
    cfprApFabricComputeSlotEpIfType                                  CfprApFabricPIoEpIfType,
    cfprApFabricComputeSlotEpLcTs                                    DateAndTime,
    cfprApFabricComputeSlotEpLicGP                                   Unsigned64,
    cfprApFabricComputeSlotEpLicState                                CfprApLicenseState,
    cfprApFabricComputeSlotEpLocale                                  CfprApFabricInternalEpLocale,
    cfprApFabricComputeSlotEpManagingInst                            CfprApNetworkSwitchId,
    cfprApFabricComputeSlotEpModel                                   SnmpAdminString,
    cfprApFabricComputeSlotEpName                                    SnmpAdminString,
    cfprApFabricComputeSlotEpOperState                               CfprApFabricPIoEpOperState,
    cfprApFabricComputeSlotEpOperStateReason                         SnmpAdminString,
    cfprApFabricComputeSlotEpPeerAggrPortId                          Gauge32,
    cfprApFabricComputeSlotEpPeerChassisId                           Gauge32,
    cfprApFabricComputeSlotEpPeerDn                                  SnmpAdminString,
    cfprApFabricComputeSlotEpPeerPortId                              Gauge32,
    cfprApFabricComputeSlotEpPeerSlotEpDn                            SnmpAdminString,
    cfprApFabricComputeSlotEpPeerSlotId                              Gauge32,
    cfprApFabricComputeSlotEpPortId                                  CfprApFabricPIoEpPortId,
    cfprApFabricComputeSlotEpPresence                                CfprApEquipmentSlotStatus,
    cfprApFabricComputeSlotEpPresencePath                            CfprApEquipmentConnectionStatus,
    cfprApFabricComputeSlotEpRevision                                SnmpAdminString,
    cfprApFabricComputeSlotEpSerial                                  SnmpAdminString,
    cfprApFabricComputeSlotEpSlotId                                  CfprApFabricComputeSlotEpSlotId,
    cfprApFabricComputeSlotEpSwitchId                                CfprApNetworkSwitchId,
    cfprApFabricComputeSlotEpTransport                               CfprApNetworkTransport,
    cfprApFabricComputeSlotEpType                                    CfprApFabricComputeEpType,
    cfprApFabricComputeSlotEpVendor                                  SnmpAdminString
}

cfprApFabricComputeSlotEpInstanceId OBJECT-TYPE
    SYNTAX       CfprApManagedObjectId
    MAX-ACCESS   not-accessible
    STATUS       current
    DESCRIPTION
        "Instance identifier of the managed object."
    ::= { cfprApFabricComputeSlotEpEntry 1 }

cfprApFabricComputeSlotEpDn OBJECT-TYPE
    SYNTAX       CfprApManagedObjectDn
    MAX-ACCESS   read-only
    STATUS       current
    DESCRIPTION
        "Cisco Firepower fabric:ComputeSlotEp:dn managed object property"
    ::= { cfprApFabricComputeSlotEpEntry 2 }

cfprApFabricComputeSlotEpRn OBJECT-TYPE
    SYNTAX       SnmpAdminString
    MAX-ACCESS   read-only
    STATUS       current
    DESCRIPTION
        "Cisco Firepower fabric:ComputeSlotEp:rn managed object property"
    ::= { cfprApFabricComputeSlotEpEntry 3 }

cfprApFabricComputeSlotEpAdminState OBJECT-TYPE
    SYNTAX       CfprApFabricSlotAdminState
    MAX-ACCESS   read-only
    STATUS       current
    DESCRIPTION
        "Cisco Firepower fabric:ComputeSlotEp:adminState
        managed object property"
    ::= { cfprApFabricComputeSlotEpEntry 4 }

cfprApFabricComputeSlotEpAggrPortId OBJECT-TYPE
    SYNTAX       Gauge32
    MAX-ACCESS   read-only
    STATUS       current
    DESCRIPTION
        "Cisco Firepower fabric:ComputeSlotEp:aggrPortId
        managed object property"
    ::= { cfprApFabricComputeSlotEpEntry 5 }

cfprApFabricComputeSlotEpBoardAggregationRole OBJECT-TYPE
    SYNTAX       CfprApEquipmentBoardAggregationRole
    MAX-ACCESS   read-only
    STATUS       current
    DESCRIPTION
        "Cisco Firepower fabric:ComputeSlotEp:boardAggregationRole
        managed object property"
    ::= { cfprApFabricComputeSlotEpEntry 6 }

cfprApFabricComputeSlotEpChassisId OBJECT-TYPE
    SYNTAX       Gauge32
    MAX-ACCESS   read-only
    STATUS       current
    DESCRIPTION
        "Cisco Firepower fabric:ComputeSlotEp:chassisId
        managed object property"
    ::= { cfprApFabricComputeSlotEpEntry 7 }

cfprApFabricComputeSlotEpConnPath OBJECT-TYPE
    SYNTAX       CfprApEquipmentConnectionStatus
    MAX-ACCESS   read-only
    STATUS       current
    DESCRIPTION
        "Cisco Firepower fabric:ComputeSlotEp:connPath
        managed object property"
    ::= { cfprApFabricComputeSlotEpEntry 8 }

cfprApFabricComputeSlotEpConnStatus OBJECT-TYPE
    SYNTAX       CfprApEquipmentConnectionStatus
    MAX-ACCESS   read-only
    STATUS       current
    DESCRIPTION
        "Cisco Firepower fabric:ComputeSlotEp:connStatus
        managed object property"
    ::= { cfprApFabricComputeSlotEpEntry 9 }

cfprApFabricComputeSlotEpDiscovery OBJECT-TYPE
    SYNTAX       CfprApComputeDiscovery
    MAX-ACCESS   read-only
    STATUS       current
    DESCRIPTION
        "Cisco Firepower fabric:ComputeSlotEp:discovery
        managed object property"
    ::= { cfprApFabricComputeSlotEpEntry 10 }

cfprApFabricComputeSlotEpEpDn OBJECT-TYPE
    SYNTAX       SnmpAdminString
    MAX-ACCESS   read-only
    STATUS       current
    DESCRIPTION
        "Cisco Firepower fabric:ComputeSlotEp:epDn managed
        object property"
    ::= { cfprApFabricComputeSlotEpEntry 11 }

cfprApFabricComputeSlotEpFactoryResetFlag OBJECT-TYPE
    SYNTAX       TruthValue
    MAX-ACCESS   read-only
    STATUS       current
    DESCRIPTION
        "Cisco Firepower fabric:ComputeSlotEp:factoryResetFlag
        managed object property"
    ::= { cfprApFabricComputeSlotEpEntry 12 }

cfprApFabricComputeSlotEpFltAggr OBJECT-TYPE
    SYNTAX       Unsigned64
    MAX-ACCESS   read-only
    STATUS       current
    DESCRIPTION
        "Cisco Firepower fabric:ComputeSlotEp:fltAggr managed
        object property"
    ::= { cfprApFabricComputeSlotEpEntry 13 }

cfprApFabricComputeSlotEpFruIdentTrigTs OBJECT-TYPE
    SYNTAX       Unsigned64
    MAX-ACCESS   read-only
    STATUS       current
    DESCRIPTION
        "Cisco Firepower fabric:ComputeSlotEp:fruIdentTrigTs
        managed object property"
    ::= { cfprApFabricComputeSlotEpEntry 14 }

cfprApFabricComputeSlotEpIfRole OBJECT-TYPE
    SYNTAX       CfprApFabricComputeEpIfRole
    MAX-ACCESS   read-only
    STATUS       current
    DESCRIPTION
        "Cisco Firepower fabric:ComputeSlotEp:ifRole managed
        object property"
    ::= { cfprApFabricComputeSlotEpEntry 15 }

cfprApFabricComputeSlotEpIfType OBJECT-TYPE
    SYNTAX       CfprApFabricPIoEpIfType
    MAX-ACCESS   read-only
    STATUS       current
    DESCRIPTION
        "Cisco Firepower fabric:ComputeSlotEp:ifType managed
        object property"
    ::= { cfprApFabricComputeSlotEpEntry 16 }

cfprApFabricComputeSlotEpLcTs OBJECT-TYPE
    SYNTAX       DateAndTime
    MAX-ACCESS   read-only
    STATUS       current
    DESCRIPTION
        "Cisco Firepower fabric:ComputeSlotEp:lcTs managed
        object property"
    ::= { cfprApFabricComputeSlotEpEntry 17 }

cfprApFabricComputeSlotEpLicGP OBJECT-TYPE
    SYNTAX       Unsigned64
    MAX-ACCESS   read-only
    STATUS       current
    DESCRIPTION
        "Cisco Firepower fabric:ComputeSlotEp:licGP managed
        object property"
    ::= { cfprApFabricComputeSlotEpEntry 18 }

cfprApFabricComputeSlotEpLicState OBJECT-TYPE
    SYNTAX       CfprApLicenseState
    MAX-ACCESS   read-only
    STATUS       current
    DESCRIPTION
        "Cisco Firepower fabric:ComputeSlotEp:licState
        managed object property"
    ::= { cfprApFabricComputeSlotEpEntry 19 }

cfprApFabricComputeSlotEpLocale OBJECT-TYPE
    SYNTAX       CfprApFabricInternalEpLocale
    MAX-ACCESS   read-only
    STATUS       current
    DESCRIPTION
        "Cisco Firepower fabric:ComputeSlotEp:locale managed
        object property"
    ::= { cfprApFabricComputeSlotEpEntry 20 }

cfprApFabricComputeSlotEpManagingInst OBJECT-TYPE
    SYNTAX       CfprApNetworkSwitchId
    MAX-ACCESS   read-only
    STATUS       current
    DESCRIPTION
        "Cisco Firepower fabric:ComputeSlotEp:managingInst
        managed object property"
    ::= { cfprApFabricComputeSlotEpEntry 21 }

cfprApFabricComputeSlotEpModel OBJECT-TYPE
    SYNTAX       SnmpAdminString
    MAX-ACCESS   read-only
    STATUS       current
    DESCRIPTION
        "Cisco Firepower fabric:ComputeSlotEp:model managed
        object property"
    ::= { cfprApFabricComputeSlotEpEntry 22 }

cfprApFabricComputeSlotEpName OBJECT-TYPE
    SYNTAX       SnmpAdminString
    MAX-ACCESS   read-only
    STATUS       current
    DESCRIPTION
        "Cisco Firepower fabric:ComputeSlotEp:name managed
        object property"
    ::= { cfprApFabricComputeSlotEpEntry 23 }

cfprApFabricComputeSlotEpOperState OBJECT-TYPE
    SYNTAX       CfprApFabricPIoEpOperState
    MAX-ACCESS   read-only
    STATUS       current
    DESCRIPTION
        "Cisco Firepower fabric:ComputeSlotEp:operState
        managed object property"
    ::= { cfprApFabricComputeSlotEpEntry 24 }

cfprApFabricComputeSlotEpOperStateReason OBJECT-TYPE
    SYNTAX       SnmpAdminString
    MAX-ACCESS   read-only
    STATUS       current
    DESCRIPTION
        "Cisco Firepower fabric:ComputeSlotEp:operStateReason
        managed object property"
    ::= { cfprApFabricComputeSlotEpEntry 25 }

cfprApFabricComputeSlotEpPeerAggrPortId OBJECT-TYPE
    SYNTAX       Gauge32
    MAX-ACCESS   read-only
    STATUS       current
    DESCRIPTION
        "Cisco Firepower fabric:ComputeSlotEp:peerAggrPortId
        managed object property"
    ::= { cfprApFabricComputeSlotEpEntry 26 }

cfprApFabricComputeSlotEpPeerChassisId OBJECT-TYPE
    SYNTAX       Gauge32
    MAX-ACCESS   read-only
    STATUS       current
    DESCRIPTION
        "Cisco Firepower fabric:ComputeSlotEp:peerChassisId
        managed object property"
    ::= { cfprApFabricComputeSlotEpEntry 27 }

cfprApFabricComputeSlotEpPeerDn OBJECT-TYPE
    SYNTAX       SnmpAdminString
    MAX-ACCESS   read-only
    STATUS       current
    DESCRIPTION
        "Cisco Firepower fabric:ComputeSlotEp:peerDn managed
        object property"
    ::= { cfprApFabricComputeSlotEpEntry 28 }

cfprApFabricComputeSlotEpPeerPortId OBJECT-TYPE
    SYNTAX       Gauge32
    MAX-ACCESS   read-only
    STATUS       current
    DESCRIPTION
        "Cisco Firepower fabric:ComputeSlotEp:peerPortId
        managed object property"
    ::= { cfprApFabricComputeSlotEpEntry 29 }

cfprApFabricComputeSlotEpPeerSlotEpDn OBJECT-TYPE
    SYNTAX       SnmpAdminString
    MAX-ACCESS   read-only
    STATUS       current
    DESCRIPTION
        "Cisco Firepower fabric:ComputeSlotEp:peerSlotEpDn
        managed object property"
    ::= { cfprApFabricComputeSlotEpEntry 30 }

cfprApFabricComputeSlotEpPeerSlotId OBJECT-TYPE
    SYNTAX       Gauge32
    MAX-ACCESS   read-only
    STATUS       current
    DESCRIPTION
        "Cisco Firepower fabric:ComputeSlotEp:peerSlotId
        managed object property"
    ::= { cfprApFabricComputeSlotEpEntry 31 }

cfprApFabricComputeSlotEpPortId OBJECT-TYPE
    SYNTAX       CfprApFabricPIoEpPortId
    MAX-ACCESS   read-only
    STATUS       current
    DESCRIPTION
        "Cisco Firepower fabric:ComputeSlotEp:portId managed
        object property"
    ::= { cfprApFabricComputeSlotEpEntry 32 }

cfprApFabricComputeSlotEpPresence OBJECT-TYPE
    SYNTAX       CfprApEquipmentSlotStatus
    MAX-ACCESS   read-only
    STATUS       current
    DESCRIPTION
        "Cisco Firepower fabric:ComputeSlotEp:presence
        managed object property"
    ::= { cfprApFabricComputeSlotEpEntry 33 }

cfprApFabricComputeSlotEpPresencePath OBJECT-TYPE
    SYNTAX       CfprApEquipmentConnectionStatus
    MAX-ACCESS   read-only
    STATUS       current
    DESCRIPTION
        "Cisco Firepower fabric:ComputeSlotEp:presencePath
        managed object property"
    ::= { cfprApFabricComputeSlotEpEntry 34 }

cfprApFabricComputeSlotEpRevision OBJECT-TYPE
    SYNTAX       SnmpAdminString
    MAX-ACCESS   read-only
    STATUS       current
    DESCRIPTION
        "Cisco Firepower fabric:ComputeSlotEp:revision
        managed object property"
    ::= { cfprApFabricComputeSlotEpEntry 35 }

cfprApFabricComputeSlotEpSerial OBJECT-TYPE
    SYNTAX       SnmpAdminString
    MAX-ACCESS   read-only
    STATUS       current
    DESCRIPTION
        "Cisco Firepower fabric:ComputeSlotEp:serial managed
        object property"
    ::= { cfprApFabricComputeSlotEpEntry 36 }

cfprApFabricComputeSlotEpSlotId OBJECT-TYPE
    SYNTAX       CfprApFabricComputeSlotEpSlotId
    MAX-ACCESS   read-only
    STATUS       current
    DESCRIPTION
        "Cisco Firepower fabric:ComputeSlotEp:slotId managed
        object property"
    ::= { cfprApFabricComputeSlotEpEntry 37 }

cfprApFabricComputeSlotEpSwitchId OBJECT-TYPE
    SYNTAX       CfprApNetworkSwitchId
    MAX-ACCESS   read-only
    STATUS       current
    DESCRIPTION
        "Cisco Firepower fabric:ComputeSlotEp:switchId
        managed object property"
    ::= { cfprApFabricComputeSlotEpEntry 38 }

cfprApFabricComputeSlotEpTransport OBJECT-TYPE
    SYNTAX       CfprApNetworkTransport
    MAX-ACCESS   read-only
    STATUS       current
    DESCRIPTION
        "Cisco Firepower fabric:ComputeSlotEp:transport
        managed object property"
    ::= { cfprApFabricComputeSlotEpEntry 39 }

cfprApFabricComputeSlotEpType OBJECT-TYPE
    SYNTAX       CfprApFabricComputeEpType
    MAX-ACCESS   read-only
    STATUS       current
    DESCRIPTION
        "Cisco Firepower fabric:ComputeSlotEp:type managed
        object property"
    ::= { cfprApFabricComputeSlotEpEntry 40 }

cfprApFabricComputeSlotEpVendor OBJECT-TYPE
    SYNTAX       SnmpAdminString
    MAX-ACCESS   read-only
    STATUS       current
    DESCRIPTION
        "Cisco Firepower fabric:ComputeSlotEp:vendor managed
        object property"
    ::= { cfprApFabricComputeSlotEpEntry 41 }

cfprApFabricDceSrvTable OBJECT-TYPE
    SYNTAX           SEQUENCE OF CfprApFabricDceSrvEntry
    MAX-ACCESS       not-accessible
    STATUS           current
    DESCRIPTION
        "Cisco Firepower fabric:DceSrv managed object table"
    ::= { cfprApFabricObjects 10 }

cfprApFabricDceSrvEntry OBJECT-TYPE
    SYNTAX           CfprApFabricDceSrvEntry
    MAX-ACCESS       not-accessible
    STATUS           current
    DESCRIPTION
        "Entry for the cfprApFabricDceSrvTable table."
    INDEX { cfprApFabricDceSrvInstanceId }
    ::= { cfprApFabricDceSrvTable 1 }

CfprApFabricDceSrvEntry ::= SEQUENCE {
    cfprApFabricDceSrvInstanceId                                     CfprApManagedObjectId,
    cfprApFabricDceSrvDn                                             CfprApManagedObjectDn,
    cfprApFabricDceSrvRn                                             SnmpAdminString,
    cfprApFabricDceSrvId                                             CfprApNetworkSwitchId,
    cfprApFabricDceSrvLocale                                         CfprApFabricInternalLocale,
    cfprApFabricDceSrvName                                           SnmpAdminString,
    cfprApFabricDceSrvTransport                                      CfprApFabricInternalDceSrvTransport,
    cfprApFabricDceSrvType                                           CfprApFabricInternalDceSrvType
}

cfprApFabricDceSrvInstanceId OBJECT-TYPE
    SYNTAX       CfprApManagedObjectId
    MAX-ACCESS   not-accessible
    STATUS       current
    DESCRIPTION
        "Instance identifier of the managed object."
    ::= { cfprApFabricDceSrvEntry 1 }

cfprApFabricDceSrvDn OBJECT-TYPE
    SYNTAX       CfprApManagedObjectDn
    MAX-ACCESS   read-only
    STATUS       current
    DESCRIPTION
        "Cisco Firepower fabric:DceSrv:dn managed object property"
    ::= { cfprApFabricDceSrvEntry 2 }

cfprApFabricDceSrvRn OBJECT-TYPE
    SYNTAX       SnmpAdminString
    MAX-ACCESS   read-only
    STATUS       current
    DESCRIPTION
        "Cisco Firepower fabric:DceSrv:rn managed object property"
    ::= { cfprApFabricDceSrvEntry 3 }

cfprApFabricDceSrvId OBJECT-TYPE
    SYNTAX       CfprApNetworkSwitchId
    MAX-ACCESS   read-only
    STATUS       current
    DESCRIPTION
        "Cisco Firepower fabric:DceSrv:id managed object property"
    ::= { cfprApFabricDceSrvEntry 4 }

cfprApFabricDceSrvLocale OBJECT-TYPE
    SYNTAX       CfprApFabricInternalLocale
    MAX-ACCESS   read-only
    STATUS       current
    DESCRIPTION
        "Cisco Firepower fabric:DceSrv:locale managed object property"
    ::= { cfprApFabricDceSrvEntry 5 }

cfprApFabricDceSrvName OBJECT-TYPE
    SYNTAX       SnmpAdminString
    MAX-ACCESS   read-only
    STATUS       current
    DESCRIPTION
        "Cisco Firepower fabric:DceSrv:name managed object property"
    ::= { cfprApFabricDceSrvEntry 6 }

cfprApFabricDceSrvTransport OBJECT-TYPE
    SYNTAX       CfprApFabricInternalDceSrvTransport
    MAX-ACCESS   read-only
    STATUS       current
    DESCRIPTION
        "Cisco Firepower fabric:DceSrv:transport managed object property"
    ::= { cfprApFabricDceSrvEntry 7 }

cfprApFabricDceSrvType OBJECT-TYPE
    SYNTAX       CfprApFabricInternalDceSrvType
    MAX-ACCESS   read-only
    STATUS       current
    DESCRIPTION
        "Cisco Firepower fabric:DceSrv:type managed object property"
    ::= { cfprApFabricDceSrvEntry 8 }

cfprApFabricDceSwSrvTable OBJECT-TYPE
    SYNTAX           SEQUENCE OF CfprApFabricDceSwSrvEntry
    MAX-ACCESS       not-accessible
    STATUS           current
    DESCRIPTION
        "Cisco Firepower fabric:DceSwSrv managed object table"
    ::= { cfprApFabricObjects 11 }

cfprApFabricDceSwSrvEntry OBJECT-TYPE
    SYNTAX           CfprApFabricDceSwSrvEntry
    MAX-ACCESS       not-accessible
    STATUS           current
    DESCRIPTION
        "Entry for the cfprApFabricDceSwSrvTable table."
    INDEX { cfprApFabricDceSwSrvInstanceId }
    ::= { cfprApFabricDceSwSrvTable 1 }

CfprApFabricDceSwSrvEntry ::= SEQUENCE {
    cfprApFabricDceSwSrvInstanceId                                   CfprApManagedObjectId,
    cfprApFabricDceSwSrvDn                                           CfprApManagedObjectDn,
    cfprApFabricDceSwSrvRn                                           SnmpAdminString,
    cfprApFabricDceSwSrvId                                           CfprApNetworkSwitchId,
    cfprApFabricDceSwSrvLocale                                       CfprApFabricInternalLocale,
    cfprApFabricDceSwSrvName                                         SnmpAdminString,
    cfprApFabricDceSwSrvTransport                                    CfprApFabricInternalDceSrvTransport,
    cfprApFabricDceSwSrvType                                         CfprApFabricInternalDceSrvType
}

cfprApFabricDceSwSrvInstanceId OBJECT-TYPE
    SYNTAX       CfprApManagedObjectId
    MAX-ACCESS   not-accessible
    STATUS       current
    DESCRIPTION
        "Instance identifier of the managed object."
    ::= { cfprApFabricDceSwSrvEntry 1 }

cfprApFabricDceSwSrvDn OBJECT-TYPE
    SYNTAX       CfprApManagedObjectDn
    MAX-ACCESS   read-only
    STATUS       current
    DESCRIPTION
        "Cisco Firepower fabric:DceSwSrv:dn managed object property"
    ::= { cfprApFabricDceSwSrvEntry 2 }

cfprApFabricDceSwSrvRn OBJECT-TYPE
    SYNTAX       SnmpAdminString
    MAX-ACCESS   read-only
    STATUS       current
    DESCRIPTION
        "Cisco Firepower fabric:DceSwSrv:rn managed object property"
    ::= { cfprApFabricDceSwSrvEntry 3 }

cfprApFabricDceSwSrvId OBJECT-TYPE
    SYNTAX       CfprApNetworkSwitchId
    MAX-ACCESS   read-only
    STATUS       current
    DESCRIPTION
        "Cisco Firepower fabric:DceSwSrv:id managed object property"
    ::= { cfprApFabricDceSwSrvEntry 4 }

cfprApFabricDceSwSrvLocale OBJECT-TYPE
    SYNTAX       CfprApFabricInternalLocale
    MAX-ACCESS   read-only
    STATUS       current
    DESCRIPTION
        "Cisco Firepower fabric:DceSwSrv:locale managed object property"
    ::= { cfprApFabricDceSwSrvEntry 5 }

cfprApFabricDceSwSrvName OBJECT-TYPE
    SYNTAX       SnmpAdminString
    MAX-ACCESS   read-only
    STATUS       current
    DESCRIPTION
        "Cisco Firepower fabric:DceSwSrv:name managed object property"
    ::= { cfprApFabricDceSwSrvEntry 6 }

cfprApFabricDceSwSrvTransport OBJECT-TYPE
    SYNTAX       CfprApFabricInternalDceSrvTransport
    MAX-ACCESS   read-only
    STATUS       current
    DESCRIPTION
        "Cisco Firepower fabric:DceSwSrv:transport managed
        object property"
    ::= { cfprApFabricDceSwSrvEntry 7 }

cfprApFabricDceSwSrvType OBJECT-TYPE
    SYNTAX       CfprApFabricInternalDceSrvType
    MAX-ACCESS   read-only
    STATUS       current
    DESCRIPTION
        "Cisco Firepower fabric:DceSwSrv:type managed object property"
    ::= { cfprApFabricDceSwSrvEntry 8 }

cfprApFabricDceSwSrvEpTable OBJECT-TYPE
    SYNTAX           SEQUENCE OF CfprApFabricDceSwSrvEpEntry
    MAX-ACCESS       not-accessible
    STATUS           current
    DESCRIPTION
        "Cisco Firepower fabric:DceSwSrvEp managed object table"
    ::= { cfprApFabricObjects 12 }

cfprApFabricDceSwSrvEpEntry OBJECT-TYPE
    SYNTAX           CfprApFabricDceSwSrvEpEntry
    MAX-ACCESS       not-accessible
    STATUS           current
    DESCRIPTION
        "Entry for the cfprApFabricDceSwSrvEpTable table."
    INDEX { cfprApFabricDceSwSrvEpInstanceId }
    ::= { cfprApFabricDceSwSrvEpTable 1 }

CfprApFabricDceSwSrvEpEntry ::= SEQUENCE {
    cfprApFabricDceSwSrvEpInstanceId                                 CfprApManagedObjectId,
    cfprApFabricDceSwSrvEpDn                                         CfprApManagedObjectDn,
    cfprApFabricDceSwSrvEpRn                                         SnmpAdminString,
    cfprApFabricDceSwSrvEpAdminState                                 CfprApFabricInternalEpAdminState,
    cfprApFabricDceSwSrvEpAggrPortId                                 Gauge32,
    cfprApFabricDceSwSrvEpChassisId                                  Gauge32,
    cfprApFabricDceSwSrvEpEpDn                                       SnmpAdminString,
    cfprApFabricDceSwSrvEpFltAggr                                    Unsigned64,
    cfprApFabricDceSwSrvEpIfRole                                     CfprApFabricSwSrvEpIfRole,
    cfprApFabricDceSwSrvEpIfType                                     CfprApFabricPIoEpIfType,
    cfprApFabricDceSwSrvEpLicGP                                      Unsigned64,
    cfprApFabricDceSwSrvEpLicState                                   CfprApLicenseState,
    cfprApFabricDceSwSrvEpLocale                                     CfprApFabricInternalEpLocale,
    cfprApFabricDceSwSrvEpName                                       SnmpAdminString,
    cfprApFabricDceSwSrvEpOperState                                  CfprApFabricPIoEpOperState,
    cfprApFabricDceSwSrvEpOperStateReason                            SnmpAdminString,
    cfprApFabricDceSwSrvEpPeerAggrPortId                             Gauge32,
    cfprApFabricDceSwSrvEpPeerChassisId                              Gauge32,
    cfprApFabricDceSwSrvEpPeerDn                                     SnmpAdminString,
    cfprApFabricDceSwSrvEpPeerPortId                                 Gauge32,
    cfprApFabricDceSwSrvEpPeerSlotId                                 Gauge32,
    cfprApFabricDceSwSrvEpPortId                                     CfprApFabricDceSwSrvEpPortId,
    cfprApFabricDceSwSrvEpSlotId                                     CfprApFabricDceSwSrvEpSlotId,
    cfprApFabricDceSwSrvEpSwitchId                                   CfprApNetworkSwitchId,
    cfprApFabricDceSwSrvEpTransport                                  CfprApFabricADceSwSrvEpTransport,
    cfprApFabricDceSwSrvEpType                                       CfprApFabricSwSrvEpType,
    cfprApFabricDceSwSrvEpUsrLbl                                     SnmpAdminString
}

cfprApFabricDceSwSrvEpInstanceId OBJECT-TYPE
    SYNTAX       CfprApManagedObjectId
    MAX-ACCESS   not-accessible
    STATUS       current
    DESCRIPTION
        "Instance identifier of the managed object."
    ::= { cfprApFabricDceSwSrvEpEntry 1 }

cfprApFabricDceSwSrvEpDn OBJECT-TYPE
    SYNTAX       CfprApManagedObjectDn
    MAX-ACCESS   read-only
    STATUS       current
    DESCRIPTION
        "Cisco Firepower fabric:DceSwSrvEp:dn managed object property"
    ::= { cfprApFabricDceSwSrvEpEntry 2 }

cfprApFabricDceSwSrvEpRn OBJECT-TYPE
    SYNTAX       SnmpAdminString
    MAX-ACCESS   read-only
    STATUS       current
    DESCRIPTION
        "Cisco Firepower fabric:DceSwSrvEp:rn managed object property"
    ::= { cfprApFabricDceSwSrvEpEntry 3 }

cfprApFabricDceSwSrvEpAdminState OBJECT-TYPE
    SYNTAX       CfprApFabricInternalEpAdminState
    MAX-ACCESS   read-only
    STATUS       current
    DESCRIPTION
        "Cisco Firepower fabric:DceSwSrvEp:adminState managed
        object property"
    ::= { cfprApFabricDceSwSrvEpEntry 4 }

cfprApFabricDceSwSrvEpAggrPortId OBJECT-TYPE
    SYNTAX       Gauge32
    MAX-ACCESS   read-only
    STATUS       current
    DESCRIPTION
        "Cisco Firepower fabric:DceSwSrvEp:aggrPortId managed
        object property"
    ::= { cfprApFabricDceSwSrvEpEntry 5 }

cfprApFabricDceSwSrvEpChassisId OBJECT-TYPE
    SYNTAX       Gauge32
    MAX-ACCESS   read-only
    STATUS       current
    DESCRIPTION
        "Cisco Firepower fabric:DceSwSrvEp:chassisId managed
        object property"
    ::= { cfprApFabricDceSwSrvEpEntry 6 }

cfprApFabricDceSwSrvEpEpDn OBJECT-TYPE
    SYNTAX       SnmpAdminString
    MAX-ACCESS   read-only
    STATUS       current
    DESCRIPTION
        "Cisco Firepower fabric:DceSwSrvEp:epDn managed object property"
    ::= { cfprApFabricDceSwSrvEpEntry 7 }

cfprApFabricDceSwSrvEpFltAggr OBJECT-TYPE
    SYNTAX       Unsigned64
    MAX-ACCESS   read-only
    STATUS       current
    DESCRIPTION
        "Cisco Firepower fabric:DceSwSrvEp:fltAggr managed
        object property"
    ::= { cfprApFabricDceSwSrvEpEntry 8 }

cfprApFabricDceSwSrvEpIfRole OBJECT-TYPE
    SYNTAX       CfprApFabricSwSrvEpIfRole
    MAX-ACCESS   read-only
    STATUS       current
    DESCRIPTION
        "Cisco Firepower fabric:DceSwSrvEp:ifRole managed object property"
    ::= { cfprApFabricDceSwSrvEpEntry 9 }

cfprApFabricDceSwSrvEpIfType OBJECT-TYPE
    SYNTAX       CfprApFabricPIoEpIfType
    MAX-ACCESS   read-only
    STATUS       current
    DESCRIPTION
        "Cisco Firepower fabric:DceSwSrvEp:ifType managed object property"
    ::= { cfprApFabricDceSwSrvEpEntry 10 }

cfprApFabricDceSwSrvEpLicGP OBJECT-TYPE
    SYNTAX       Unsigned64
    MAX-ACCESS   read-only
    STATUS       current
    DESCRIPTION
        "Cisco Firepower fabric:DceSwSrvEp:licGP managed object property"
    ::= { cfprApFabricDceSwSrvEpEntry 11 }

cfprApFabricDceSwSrvEpLicState OBJECT-TYPE
    SYNTAX       CfprApLicenseState
    MAX-ACCESS   read-only
    STATUS       current
    DESCRIPTION
        "Cisco Firepower fabric:DceSwSrvEp:licState managed
        object property"
    ::= { cfprApFabricDceSwSrvEpEntry 12 }

cfprApFabricDceSwSrvEpLocale OBJECT-TYPE
    SYNTAX       CfprApFabricInternalEpLocale
    MAX-ACCESS   read-only
    STATUS       current
    DESCRIPTION
        "Cisco Firepower fabric:DceSwSrvEp:locale managed object property"
    ::= { cfprApFabricDceSwSrvEpEntry 13 }

cfprApFabricDceSwSrvEpName OBJECT-TYPE
    SYNTAX       SnmpAdminString
    MAX-ACCESS   read-only
    STATUS       current
    DESCRIPTION
        "Cisco Firepower fabric:DceSwSrvEp:name managed object property"
    ::= { cfprApFabricDceSwSrvEpEntry 14 }

cfprApFabricDceSwSrvEpOperState OBJECT-TYPE
    SYNTAX       CfprApFabricPIoEpOperState
    MAX-ACCESS   read-only
    STATUS       current
    DESCRIPTION
        "Cisco Firepower fabric:DceSwSrvEp:operState managed
        object property"
    ::= { cfprApFabricDceSwSrvEpEntry 15 }

cfprApFabricDceSwSrvEpOperStateReason OBJECT-TYPE
    SYNTAX       SnmpAdminString
    MAX-ACCESS   read-only
    STATUS       current
    DESCRIPTION
        "Cisco Firepower fabric:DceSwSrvEp:operStateReason
        managed object property"
    ::= { cfprApFabricDceSwSrvEpEntry 16 }

cfprApFabricDceSwSrvEpPeerAggrPortId OBJECT-TYPE
    SYNTAX       Gauge32
    MAX-ACCESS   read-only
    STATUS       current
    DESCRIPTION
        "Cisco Firepower fabric:DceSwSrvEp:peerAggrPortId
        managed object property"
    ::= { cfprApFabricDceSwSrvEpEntry 17 }

cfprApFabricDceSwSrvEpPeerChassisId OBJECT-TYPE
    SYNTAX       Gauge32
    MAX-ACCESS   read-only
    STATUS       current
    DESCRIPTION
        "Cisco Firepower fabric:DceSwSrvEp:peerChassisId
        managed object property"
    ::= { cfprApFabricDceSwSrvEpEntry 18 }

cfprApFabricDceSwSrvEpPeerDn OBJECT-TYPE
    SYNTAX       SnmpAdminString
    MAX-ACCESS   read-only
    STATUS       current
    DESCRIPTION
        "Cisco Firepower fabric:DceSwSrvEp:peerDn managed object property"
    ::= { cfprApFabricDceSwSrvEpEntry 19 }

cfprApFabricDceSwSrvEpPeerPortId OBJECT-TYPE
    SYNTAX       Gauge32
    MAX-ACCESS   read-only
    STATUS       current
    DESCRIPTION
        "Cisco Firepower fabric:DceSwSrvEp:peerPortId managed
        object property"
    ::= { cfprApFabricDceSwSrvEpEntry 20 }

cfprApFabricDceSwSrvEpPeerSlotId OBJECT-TYPE
    SYNTAX       Gauge32
    MAX-ACCESS   read-only
    STATUS       current
    DESCRIPTION
        "Cisco Firepower fabric:DceSwSrvEp:peerSlotId managed
        object property"
    ::= { cfprApFabricDceSwSrvEpEntry 21 }

cfprApFabricDceSwSrvEpPortId OBJECT-TYPE
    SYNTAX       CfprApFabricDceSwSrvEpPortId
    MAX-ACCESS   read-only
    STATUS       current
    DESCRIPTION
        "Cisco Firepower fabric:DceSwSrvEp:portId managed object property"
    ::= { cfprApFabricDceSwSrvEpEntry 22 }

cfprApFabricDceSwSrvEpSlotId OBJECT-TYPE
    SYNTAX       CfprApFabricDceSwSrvEpSlotId
    MAX-ACCESS   read-only
    STATUS       current
    DESCRIPTION
        "Cisco Firepower fabric:DceSwSrvEp:slotId managed object property"
    ::= { cfprApFabricDceSwSrvEpEntry 23 }

cfprApFabricDceSwSrvEpSwitchId OBJECT-TYPE
    SYNTAX       CfprApNetworkSwitchId
    MAX-ACCESS   read-only
    STATUS       current
    DESCRIPTION
        "Cisco Firepower fabric:DceSwSrvEp:switchId managed
        object property"
    ::= { cfprApFabricDceSwSrvEpEntry 24 }

cfprApFabricDceSwSrvEpTransport OBJECT-TYPE
    SYNTAX       CfprApFabricADceSwSrvEpTransport
    MAX-ACCESS   read-only
    STATUS       current
    DESCRIPTION
        "Cisco Firepower fabric:DceSwSrvEp:transport managed
        object property"
    ::= { cfprApFabricDceSwSrvEpEntry 25 }

cfprApFabricDceSwSrvEpType OBJECT-TYPE
    SYNTAX       CfprApFabricSwSrvEpType
    MAX-ACCESS   read-only
    STATUS       current
    DESCRIPTION
        "Cisco Firepower fabric:DceSwSrvEp:type managed object property"
    ::= { cfprApFabricDceSwSrvEpEntry 26 }

cfprApFabricDceSwSrvEpUsrLbl OBJECT-TYPE
    SYNTAX       SnmpAdminString
    MAX-ACCESS   read-only
    STATUS       current
    DESCRIPTION
        "Cisco Firepower fabric:DceSwSrvEp:usrLbl managed object property"
    ::= { cfprApFabricDceSwSrvEpEntry 27 }

cfprApFabricDceSwSrvPcTable OBJECT-TYPE
    SYNTAX           SEQUENCE OF CfprApFabricDceSwSrvPcEntry
    MAX-ACCESS       not-accessible
    STATUS           current
    DESCRIPTION
        "Cisco Firepower fabric:DceSwSrvPc managed object table"
    ::= { cfprApFabricObjects 13 }

cfprApFabricDceSwSrvPcEntry OBJECT-TYPE
    SYNTAX           CfprApFabricDceSwSrvPcEntry
    MAX-ACCESS       not-accessible
    STATUS           current
    DESCRIPTION
        "Entry for the cfprApFabricDceSwSrvPcTable table."
    INDEX { cfprApFabricDceSwSrvPcInstanceId }
    ::= { cfprApFabricDceSwSrvPcTable 1 }

CfprApFabricDceSwSrvPcEntry ::= SEQUENCE {
    cfprApFabricDceSwSrvPcInstanceId                                 CfprApManagedObjectId,
    cfprApFabricDceSwSrvPcDn                                         CfprApManagedObjectDn,
    cfprApFabricDceSwSrvPcRn                                         SnmpAdminString,
    cfprApFabricDceSwSrvPcAdminState                                 CfprApFabricDceSwSrvPcAdminState,
    cfprApFabricDceSwSrvPcChassisId                                  Gauge32,
    cfprApFabricDceSwSrvPcDescr                                      SnmpAdminString,
    cfprApFabricDceSwSrvPcEpDn                                       SnmpAdminString,
    cfprApFabricDceSwSrvPcFltAggr                                    Unsigned64,
    cfprApFabricDceSwSrvPcIfRole                                     CfprApFabricSwSrvPcIfRole,
    cfprApFabricDceSwSrvPcIfType                                     CfprApFabricCIoEpIfType,
    cfprApFabricDceSwSrvPcLocale                                     CfprApFabricInternalPcLocale,
    cfprApFabricDceSwSrvPcName                                       SnmpAdminString,
    cfprApFabricDceSwSrvPcOperSpeed                                  CfprApPortEthSpeed,
    cfprApFabricDceSwSrvPcOperState                                  CfprApNetworkPortOperState,
    cfprApFabricDceSwSrvPcPeerDn                                     SnmpAdminString,
    cfprApFabricDceSwSrvPcPortId                                     CfprApFabricDceSwSrvPcPortId,
    cfprApFabricDceSwSrvPcStateQual                                  SnmpAdminString,
    cfprApFabricDceSwSrvPcSwitchId                                   CfprApNetworkSwitchId,
    cfprApFabricDceSwSrvPcTransport                                  CfprApFabricDceSwSrvPcTransport,
    cfprApFabricDceSwSrvPcType                                       CfprApFabricSwSrvPcType
}

cfprApFabricDceSwSrvPcInstanceId OBJECT-TYPE
    SYNTAX       CfprApManagedObjectId
    MAX-ACCESS   not-accessible
    STATUS       current
    DESCRIPTION
        "Instance identifier of the managed object."
    ::= { cfprApFabricDceSwSrvPcEntry 1 }

cfprApFabricDceSwSrvPcDn OBJECT-TYPE
    SYNTAX       CfprApManagedObjectDn
    MAX-ACCESS   read-only
    STATUS       current
    DESCRIPTION
        "Cisco Firepower fabric:DceSwSrvPc:dn managed object property"
    ::= { cfprApFabricDceSwSrvPcEntry 2 }

cfprApFabricDceSwSrvPcRn OBJECT-TYPE
    SYNTAX       SnmpAdminString
    MAX-ACCESS   read-only
    STATUS       current
    DESCRIPTION
        "Cisco Firepower fabric:DceSwSrvPc:rn managed object property"
    ::= { cfprApFabricDceSwSrvPcEntry 3 }

cfprApFabricDceSwSrvPcAdminState OBJECT-TYPE
    SYNTAX       CfprApFabricDceSwSrvPcAdminState
    MAX-ACCESS   read-only
    STATUS       current
    DESCRIPTION
        "Cisco Firepower fabric:DceSwSrvPc:adminState managed
        object property"
    ::= { cfprApFabricDceSwSrvPcEntry 4 }

cfprApFabricDceSwSrvPcChassisId OBJECT-TYPE
    SYNTAX       Gauge32
    MAX-ACCESS   read-only
    STATUS       current
    DESCRIPTION
        "Cisco Firepower fabric:DceSwSrvPc:chassisId managed
        object property"
    ::= { cfprApFabricDceSwSrvPcEntry 5 }

cfprApFabricDceSwSrvPcDescr OBJECT-TYPE
    SYNTAX       SnmpAdminString
    MAX-ACCESS   read-only
    STATUS       current
    DESCRIPTION
        "Cisco Firepower fabric:DceSwSrvPc:descr managed object property"
    ::= { cfprApFabricDceSwSrvPcEntry 6 }

cfprApFabricDceSwSrvPcEpDn OBJECT-TYPE
    SYNTAX       SnmpAdminString
    MAX-ACCESS   read-only
    STATUS       current
    DESCRIPTION
        "Cisco Firepower fabric:DceSwSrvPc:epDn managed object property"
    ::= { cfprApFabricDceSwSrvPcEntry 7 }

cfprApFabricDceSwSrvPcFltAggr OBJECT-TYPE
    SYNTAX       Unsigned64
    MAX-ACCESS   read-only
    STATUS       current
    DESCRIPTION
        "Cisco Firepower fabric:DceSwSrvPc:fltAggr managed
        object property"
    ::= { cfprApFabricDceSwSrvPcEntry 8 }

cfprApFabricDceSwSrvPcIfRole OBJECT-TYPE
    SYNTAX       CfprApFabricSwSrvPcIfRole
    MAX-ACCESS   read-only
    STATUS       current
    DESCRIPTION
        "Cisco Firepower fabric:DceSwSrvPc:ifRole managed object property"
    ::= { cfprApFabricDceSwSrvPcEntry 9 }

cfprApFabricDceSwSrvPcIfType OBJECT-TYPE
    SYNTAX       CfprApFabricCIoEpIfType
    MAX-ACCESS   read-only
    STATUS       current
    DESCRIPTION
        "Cisco Firepower fabric:DceSwSrvPc:ifType managed object property"
    ::= { cfprApFabricDceSwSrvPcEntry 10 }

cfprApFabricDceSwSrvPcLocale OBJECT-TYPE
    SYNTAX       CfprApFabricInternalPcLocale
    MAX-ACCESS   read-only
    STATUS       current
    DESCRIPTION
        "Cisco Firepower fabric:DceSwSrvPc:locale managed object property"
    ::= { cfprApFabricDceSwSrvPcEntry 11 }

cfprApFabricDceSwSrvPcName OBJECT-TYPE
    SYNTAX       SnmpAdminString
    MAX-ACCESS   read-only
    STATUS       current
    DESCRIPTION
        "Cisco Firepower fabric:DceSwSrvPc:name managed object property"
    ::= { cfprApFabricDceSwSrvPcEntry 12 }

cfprApFabricDceSwSrvPcOperSpeed OBJECT-TYPE
    SYNTAX       CfprApPortEthSpeed
    MAX-ACCESS   read-only
    STATUS       current
    DESCRIPTION
        "Cisco Firepower fabric:DceSwSrvPc:operSpeed managed
        object property"
    ::= { cfprApFabricDceSwSrvPcEntry 13 }

cfprApFabricDceSwSrvPcOperState OBJECT-TYPE
    SYNTAX       CfprApNetworkPortOperState
    MAX-ACCESS   read-only
    STATUS       current
    DESCRIPTION
        "Cisco Firepower fabric:DceSwSrvPc:operState managed
        object property"
    ::= { cfprApFabricDceSwSrvPcEntry 14 }

cfprApFabricDceSwSrvPcPeerDn OBJECT-TYPE
    SYNTAX       SnmpAdminString
    MAX-ACCESS   read-only
    STATUS       current
    DESCRIPTION
        "Cisco Firepower fabric:DceSwSrvPc:peerDn managed object property"
    ::= { cfprApFabricDceSwSrvPcEntry 15 }

cfprApFabricDceSwSrvPcPortId OBJECT-TYPE
    SYNTAX       CfprApFabricDceSwSrvPcPortId
    MAX-ACCESS   read-only
    STATUS       current
    DESCRIPTION
        "Cisco Firepower fabric:DceSwSrvPc:portId managed object property"
    ::= { cfprApFabricDceSwSrvPcEntry 16 }

cfprApFabricDceSwSrvPcStateQual OBJECT-TYPE
    SYNTAX       SnmpAdminString
    MAX-ACCESS   read-only
    STATUS       current
    DESCRIPTION
        "Cisco Firepower fabric:DceSwSrvPc:stateQual managed
        object property"
    ::= { cfprApFabricDceSwSrvPcEntry 17 }

cfprApFabricDceSwSrvPcSwitchId OBJECT-TYPE
    SYNTAX       CfprApNetworkSwitchId
    MAX-ACCESS   read-only
    STATUS       current
    DESCRIPTION
        "Cisco Firepower fabric:DceSwSrvPc:switchId managed
        object property"
    ::= { cfprApFabricDceSwSrvPcEntry 18 }

cfprApFabricDceSwSrvPcTransport OBJECT-TYPE
    SYNTAX       CfprApFabricDceSwSrvPcTransport
    MAX-ACCESS   read-only
    STATUS       current
    DESCRIPTION
        "Cisco Firepower fabric:DceSwSrvPc:transport managed
        object property"
    ::= { cfprApFabricDceSwSrvPcEntry 19 }

cfprApFabricDceSwSrvPcType OBJECT-TYPE
    SYNTAX       CfprApFabricSwSrvPcType
    MAX-ACCESS   read-only
    STATUS       current
    DESCRIPTION
        "Cisco Firepower fabric:DceSwSrvPc:type managed object property"
    ::= { cfprApFabricDceSwSrvPcEntry 20 }

cfprApFabricDceSwSrvPcEpTable OBJECT-TYPE
    SYNTAX           SEQUENCE OF CfprApFabricDceSwSrvPcEpEntry
    MAX-ACCESS       not-accessible
    STATUS           current
    DESCRIPTION
        "Cisco Firepower fabric:DceSwSrvPcEp managed object table"
    ::= { cfprApFabricObjects 14 }

cfprApFabricDceSwSrvPcEpEntry OBJECT-TYPE
    SYNTAX           CfprApFabricDceSwSrvPcEpEntry
    MAX-ACCESS       not-accessible
    STATUS           current
    DESCRIPTION
        "Entry for the cfprApFabricDceSwSrvPcEpTable table."
    INDEX { cfprApFabricDceSwSrvPcEpInstanceId }
    ::= { cfprApFabricDceSwSrvPcEpTable 1 }

CfprApFabricDceSwSrvPcEpEntry ::= SEQUENCE {
    cfprApFabricDceSwSrvPcEpInstanceId                               CfprApManagedObjectId,
    cfprApFabricDceSwSrvPcEpDnData                                   CfprApManagedObjectDn,
    cfprApFabricDceSwSrvPcEpRn                                       SnmpAdminString,
    cfprApFabricDceSwSrvPcEpAdminState                               CfprApFabricInternalEpAdminState,
    cfprApFabricDceSwSrvPcEpAggrPortId                               Gauge32,
    cfprApFabricDceSwSrvPcEpChassisId                                Gauge32,
    cfprApFabricDceSwSrvPcEpEpDn                                     SnmpAdminString,
    cfprApFabricDceSwSrvPcEpFltAggr                                  Unsigned64,
    cfprApFabricDceSwSrvPcEpIfRole                                   CfprApFabricSwSrvEpIfRole,
    cfprApFabricDceSwSrvPcEpIfType                                   CfprApFabricPIoEpIfType,
    cfprApFabricDceSwSrvPcEpLicGP                                    Unsigned64,
    cfprApFabricDceSwSrvPcEpLicState                                 CfprApLicenseState,
    cfprApFabricDceSwSrvPcEpLocale                                   CfprApFabricInternalEpLocale,
    cfprApFabricDceSwSrvPcEpMembership                               CfprApFabricMembershipStatus,
    cfprApFabricDceSwSrvPcEpName                                     SnmpAdminString,
    cfprApFabricDceSwSrvPcEpOperState                                CfprApFabricPIoEpOperState,
    cfprApFabricDceSwSrvPcEpOperStateReason                          SnmpAdminString,
    cfprApFabricDceSwSrvPcEpPeerAggrPortId                           Gauge32,
    cfprApFabricDceSwSrvPcEpPeerChassisId                            Gauge32,
    cfprApFabricDceSwSrvPcEpPeerDn                                   SnmpAdminString,
    cfprApFabricDceSwSrvPcEpPeerPortId                               Gauge32,
    cfprApFabricDceSwSrvPcEpPeerSlotId                               Gauge32,
    cfprApFabricDceSwSrvPcEpPortId                                   CfprApFabricDceSwSrvPcEpPortId,
    cfprApFabricDceSwSrvPcEpSlotId                                   CfprApFabricDceSwSrvPcEpSlotId,
    cfprApFabricDceSwSrvPcEpSwitchId                                 CfprApNetworkSwitchId,
    cfprApFabricDceSwSrvPcEpTransport                                CfprApFabricADceSwSrvEpTransport,
    cfprApFabricDceSwSrvPcEpType                                     CfprApFabricSwSrvEpType,
    cfprApFabricDceSwSrvPcEpUsrLbl                                   SnmpAdminString
}

cfprApFabricDceSwSrvPcEpInstanceId OBJECT-TYPE
    SYNTAX       CfprApManagedObjectId
    MAX-ACCESS   not-accessible
    STATUS       current
    DESCRIPTION
        "Instance identifier of the managed object."
    ::= { cfprApFabricDceSwSrvPcEpEntry 1 }

cfprApFabricDceSwSrvPcEpDnData OBJECT-TYPE
    SYNTAX       CfprApManagedObjectDn
    MAX-ACCESS   read-only
    STATUS       current
    DESCRIPTION
        "Cisco Firepower fabric:DceSwSrvPcEp:dn managed object property"
    ::= { cfprApFabricDceSwSrvPcEpEntry 2 }

cfprApFabricDceSwSrvPcEpRn OBJECT-TYPE
    SYNTAX       SnmpAdminString
    MAX-ACCESS   read-only
    STATUS       current
    DESCRIPTION
        "Cisco Firepower fabric:DceSwSrvPcEp:rn managed object property"
    ::= { cfprApFabricDceSwSrvPcEpEntry 3 }

cfprApFabricDceSwSrvPcEpAdminState OBJECT-TYPE
    SYNTAX       CfprApFabricInternalEpAdminState
    MAX-ACCESS   read-only
    STATUS       current
    DESCRIPTION
        "Cisco Firepower fabric:DceSwSrvPcEp:adminState
        managed object property"
    ::= { cfprApFabricDceSwSrvPcEpEntry 4 }

cfprApFabricDceSwSrvPcEpAggrPortId OBJECT-TYPE
    SYNTAX       Gauge32
    MAX-ACCESS   read-only
    STATUS       current
    DESCRIPTION
        "Cisco Firepower fabric:DceSwSrvPcEp:aggrPortId
        managed object property"
    ::= { cfprApFabricDceSwSrvPcEpEntry 5 }

cfprApFabricDceSwSrvPcEpChassisId OBJECT-TYPE
    SYNTAX       Gauge32
    MAX-ACCESS   read-only
    STATUS       current
    DESCRIPTION
        "Cisco Firepower fabric:DceSwSrvPcEp:chassisId
        managed object property"
    ::= { cfprApFabricDceSwSrvPcEpEntry 6 }

cfprApFabricDceSwSrvPcEpEpDn OBJECT-TYPE
    SYNTAX       SnmpAdminString
    MAX-ACCESS   read-only
    STATUS       current
    DESCRIPTION
        "Cisco Firepower fabric:DceSwSrvPcEp:epDn managed object property"
    ::= { cfprApFabricDceSwSrvPcEpEntry 7 }

cfprApFabricDceSwSrvPcEpFltAggr OBJECT-TYPE
    SYNTAX       Unsigned64
    MAX-ACCESS   read-only
    STATUS       current
    DESCRIPTION
        "Cisco Firepower fabric:DceSwSrvPcEp:fltAggr managed
        object property"
    ::= { cfprApFabricDceSwSrvPcEpEntry 8 }

cfprApFabricDceSwSrvPcEpIfRole OBJECT-TYPE
    SYNTAX       CfprApFabricSwSrvEpIfRole
    MAX-ACCESS   read-only
    STATUS       current
    DESCRIPTION
        "Cisco Firepower fabric:DceSwSrvPcEp:ifRole managed
        object property"
    ::= { cfprApFabricDceSwSrvPcEpEntry 9 }

cfprApFabricDceSwSrvPcEpIfType OBJECT-TYPE
    SYNTAX       CfprApFabricPIoEpIfType
    MAX-ACCESS   read-only
    STATUS       current
    DESCRIPTION
        "Cisco Firepower fabric:DceSwSrvPcEp:ifType managed
        object property"
    ::= { cfprApFabricDceSwSrvPcEpEntry 10 }

cfprApFabricDceSwSrvPcEpLicGP OBJECT-TYPE
    SYNTAX       Unsigned64
    MAX-ACCESS   read-only
    STATUS       current
    DESCRIPTION
        "Cisco Firepower fabric:DceSwSrvPcEp:licGP managed
        object property"
    ::= { cfprApFabricDceSwSrvPcEpEntry 11 }

cfprApFabricDceSwSrvPcEpLicState OBJECT-TYPE
    SYNTAX       CfprApLicenseState
    MAX-ACCESS   read-only
    STATUS       current
    DESCRIPTION
        "Cisco Firepower fabric:DceSwSrvPcEp:licState managed
        object property"
    ::= { cfprApFabricDceSwSrvPcEpEntry 12 }

cfprApFabricDceSwSrvPcEpLocale OBJECT-TYPE
    SYNTAX       CfprApFabricInternalEpLocale
    MAX-ACCESS   read-only
    STATUS       current
    DESCRIPTION
        "Cisco Firepower fabric:DceSwSrvPcEp:locale managed
        object property"
    ::= { cfprApFabricDceSwSrvPcEpEntry 13 }

cfprApFabricDceSwSrvPcEpMembership OBJECT-TYPE
    SYNTAX       CfprApFabricMembershipStatus
    MAX-ACCESS   read-only
    STATUS       current
    DESCRIPTION
        "Cisco Firepower fabric:DceSwSrvPcEp:membership
        managed object property"
    ::= { cfprApFabricDceSwSrvPcEpEntry 14 }

cfprApFabricDceSwSrvPcEpName OBJECT-TYPE
    SYNTAX       SnmpAdminString
    MAX-ACCESS   read-only
    STATUS       current
    DESCRIPTION
        "Cisco Firepower fabric:DceSwSrvPcEp:name managed object property"
    ::= { cfprApFabricDceSwSrvPcEpEntry 15 }

cfprApFabricDceSwSrvPcEpOperState OBJECT-TYPE
    SYNTAX       CfprApFabricPIoEpOperState
    MAX-ACCESS   read-only
    STATUS       current
    DESCRIPTION
        "Cisco Firepower fabric:DceSwSrvPcEp:operState
        managed object property"
    ::= { cfprApFabricDceSwSrvPcEpEntry 16 }

cfprApFabricDceSwSrvPcEpOperStateReason OBJECT-TYPE
    SYNTAX       SnmpAdminString
    MAX-ACCESS   read-only
    STATUS       current
    DESCRIPTION
        "Cisco Firepower fabric:DceSwSrvPcEp:operStateReason
        managed object property"
    ::= { cfprApFabricDceSwSrvPcEpEntry 17 }

cfprApFabricDceSwSrvPcEpPeerAggrPortId OBJECT-TYPE
    SYNTAX       Gauge32
    MAX-ACCESS   read-only
    STATUS       current
    DESCRIPTION
        "Cisco Firepower fabric:DceSwSrvPcEp:peerAggrPortId
        managed object property"
    ::= { cfprApFabricDceSwSrvPcEpEntry 18 }

cfprApFabricDceSwSrvPcEpPeerChassisId OBJECT-TYPE
    SYNTAX       Gauge32
    MAX-ACCESS   read-only
    STATUS       current
    DESCRIPTION
        "Cisco Firepower fabric:DceSwSrvPcEp:peerChassisId
        managed object property"
    ::= { cfprApFabricDceSwSrvPcEpEntry 19 }

cfprApFabricDceSwSrvPcEpPeerDn OBJECT-TYPE
    SYNTAX       SnmpAdminString
    MAX-ACCESS   read-only
    STATUS       current
    DESCRIPTION
        "Cisco Firepower fabric:DceSwSrvPcEp:peerDn managed
        object property"
    ::= { cfprApFabricDceSwSrvPcEpEntry 20 }

cfprApFabricDceSwSrvPcEpPeerPortId OBJECT-TYPE
    SYNTAX       Gauge32
    MAX-ACCESS   read-only
    STATUS       current
    DESCRIPTION
        "Cisco Firepower fabric:DceSwSrvPcEp:peerPortId
        managed object property"
    ::= { cfprApFabricDceSwSrvPcEpEntry 21 }

cfprApFabricDceSwSrvPcEpPeerSlotId OBJECT-TYPE
    SYNTAX       Gauge32
    MAX-ACCESS   read-only
    STATUS       current
    DESCRIPTION
        "Cisco Firepower fabric:DceSwSrvPcEp:peerSlotId
        managed object property"
    ::= { cfprApFabricDceSwSrvPcEpEntry 22 }

cfprApFabricDceSwSrvPcEpPortId OBJECT-TYPE
    SYNTAX       CfprApFabricDceSwSrvPcEpPortId
    MAX-ACCESS   read-only
    STATUS       current
    DESCRIPTION
        "Cisco Firepower fabric:DceSwSrvPcEp:portId managed
        object property"
    ::= { cfprApFabricDceSwSrvPcEpEntry 23 }

cfprApFabricDceSwSrvPcEpSlotId OBJECT-TYPE
    SYNTAX       CfprApFabricDceSwSrvPcEpSlotId
    MAX-ACCESS   read-only
    STATUS       current
    DESCRIPTION
        "Cisco Firepower fabric:DceSwSrvPcEp:slotId managed
        object property"
    ::= { cfprApFabricDceSwSrvPcEpEntry 24 }

cfprApFabricDceSwSrvPcEpSwitchId OBJECT-TYPE
    SYNTAX       CfprApNetworkSwitchId
    MAX-ACCESS   read-only
    STATUS       current
    DESCRIPTION
        "Cisco Firepower fabric:DceSwSrvPcEp:switchId managed
        object property"
    ::= { cfprApFabricDceSwSrvPcEpEntry 25 }

cfprApFabricDceSwSrvPcEpTransport OBJECT-TYPE
    SYNTAX       CfprApFabricADceSwSrvEpTransport
    MAX-ACCESS   read-only
    STATUS       current
    DESCRIPTION
        "Cisco Firepower fabric:DceSwSrvPcEp:transport
        managed object property"
    ::= { cfprApFabricDceSwSrvPcEpEntry 26 }

cfprApFabricDceSwSrvPcEpType OBJECT-TYPE
    SYNTAX       CfprApFabricSwSrvEpType
    MAX-ACCESS   read-only
    STATUS       current
    DESCRIPTION
        "Cisco Firepower fabric:DceSwSrvPcEp:type managed object property"
    ::= { cfprApFabricDceSwSrvPcEpEntry 27 }

cfprApFabricDceSwSrvPcEpUsrLbl OBJECT-TYPE
    SYNTAX       SnmpAdminString
    MAX-ACCESS   read-only
    STATUS       current
    DESCRIPTION
        "Cisco Firepower fabric:DceSwSrvPcEp:usrLbl managed
        object property"
    ::= { cfprApFabricDceSwSrvPcEpEntry 28 }

cfprApFabricEpTable OBJECT-TYPE
    SYNTAX           SEQUENCE OF CfprApFabricEpEntry
    MAX-ACCESS       not-accessible
    STATUS           current
    DESCRIPTION
        "Cisco Firepower fabric:Ep managed object table"
    ::= { cfprApFabricObjects 15 }

cfprApFabricEpEntry OBJECT-TYPE
    SYNTAX           CfprApFabricEpEntry
    MAX-ACCESS       not-accessible
    STATUS           current
    DESCRIPTION
        "Entry for the cfprApFabricEpTable table."
    INDEX { cfprApFabricEpInstanceId }
    ::= { cfprApFabricEpTable 1 }

CfprApFabricEpEntry ::= SEQUENCE {
    cfprApFabricEpInstanceId                                         CfprApManagedObjectId,
    cfprApFabricEpDn                                                 CfprApManagedObjectDn,
    cfprApFabricEpRn                                                 SnmpAdminString
}

cfprApFabricEpInstanceId OBJECT-TYPE
    SYNTAX       CfprApManagedObjectId
    MAX-ACCESS   not-accessible
    STATUS       current
    DESCRIPTION
        "Instance identifier of the managed object."
    ::= { cfprApFabricEpEntry 1 }

cfprApFabricEpDn OBJECT-TYPE
    SYNTAX       CfprApManagedObjectDn
    MAX-ACCESS   read-only
    STATUS       current
    DESCRIPTION
        "Cisco Firepower fabric:Ep:dn managed object property"
    ::= { cfprApFabricEpEntry 2 }

cfprApFabricEpRn OBJECT-TYPE
    SYNTAX       SnmpAdminString
    MAX-ACCESS   read-only
    STATUS       current
    DESCRIPTION
        "Cisco Firepower fabric:Ep:rn managed object property"
    ::= { cfprApFabricEpEntry 3 }

cfprApFabricEpMgrTable OBJECT-TYPE
    SYNTAX           SEQUENCE OF CfprApFabricEpMgrEntry
    MAX-ACCESS       not-accessible
    STATUS           current
    DESCRIPTION
        "Cisco Firepower fabric:EpMgr managed object table"
    ::= { cfprApFabricObjects 16 }

cfprApFabricEpMgrEntry OBJECT-TYPE
    SYNTAX           CfprApFabricEpMgrEntry
    MAX-ACCESS       not-accessible
    STATUS           current
    DESCRIPTION
        "Entry for the cfprApFabricEpMgrTable table."
    INDEX { cfprApFabricEpMgrInstanceId }
    ::= { cfprApFabricEpMgrTable 1 }

CfprApFabricEpMgrEntry ::= SEQUENCE {
    cfprApFabricEpMgrInstanceId                                      CfprApManagedObjectId,
    cfprApFabricEpMgrDn                                              CfprApManagedObjectDn,
    cfprApFabricEpMgrRn                                              SnmpAdminString,
    cfprApFabricEpMgrConfMode                                        CfprApFabricConfMode,
    cfprApFabricEpMgrConfQual                                        SnmpAdminString,
    cfprApFabricEpMgrConfState                                       CfprApFabricConfState,
    cfprApFabricEpMgrFltAggr                                         Unsigned64,
    cfprApFabricEpMgrFsmDescr                                        SnmpAdminString,
    cfprApFabricEpMgrFsmFlags                                        SnmpAdminString,
    cfprApFabricEpMgrFsmPrev                                         SnmpAdminString,
    cfprApFabricEpMgrFsmProgr                                        Gauge32,
    cfprApFabricEpMgrFsmRmtInvErrCode                                Gauge32,
    cfprApFabricEpMgrFsmRmtInvErrDescr                               SnmpAdminString,
    cfprApFabricEpMgrFsmRmtInvRslt                                   CfprApConditionRemoteInvRslt,
    cfprApFabricEpMgrFsmStageDescr                                   SnmpAdminString,
    cfprApFabricEpMgrFsmStamp                                        DateAndTime,
    cfprApFabricEpMgrFsmStatus                                       SnmpAdminString,
    cfprApFabricEpMgrFsmTry                                          Gauge32,
    cfprApFabricEpMgrId                                              CfprApNetworkSwitchId
}

cfprApFabricEpMgrInstanceId OBJECT-TYPE
    SYNTAX       CfprApManagedObjectId
    MAX-ACCESS   not-accessible
    STATUS       current
    DESCRIPTION
        "Instance identifier of the managed object."
    ::= { cfprApFabricEpMgrEntry 1 }

cfprApFabricEpMgrDn OBJECT-TYPE
    SYNTAX       CfprApManagedObjectDn
    MAX-ACCESS   read-only
    STATUS       current
    DESCRIPTION
        "Cisco Firepower fabric:EpMgr:dn managed object property"
    ::= { cfprApFabricEpMgrEntry 2 }

cfprApFabricEpMgrRn OBJECT-TYPE
    SYNTAX       SnmpAdminString
    MAX-ACCESS   read-only
    STATUS       current
    DESCRIPTION
        "Cisco Firepower fabric:EpMgr:rn managed object property"
    ::= { cfprApFabricEpMgrEntry 3 }

cfprApFabricEpMgrConfMode OBJECT-TYPE
    SYNTAX       CfprApFabricConfMode
    MAX-ACCESS   read-only
    STATUS       current
    DESCRIPTION
        "Cisco Firepower fabric:EpMgr:confMode managed object property"
    ::= { cfprApFabricEpMgrEntry 4 }

cfprApFabricEpMgrConfQual OBJECT-TYPE
    SYNTAX       SnmpAdminString
    MAX-ACCESS   read-only
    STATUS       current
    DESCRIPTION
        "Cisco Firepower fabric:EpMgr:confQual managed object property"
    ::= { cfprApFabricEpMgrEntry 5 }

cfprApFabricEpMgrConfState OBJECT-TYPE
    SYNTAX       CfprApFabricConfState
    MAX-ACCESS   read-only
    STATUS       current
    DESCRIPTION
        "Cisco Firepower fabric:EpMgr:confState managed object property"
    ::= { cfprApFabricEpMgrEntry 6 }

cfprApFabricEpMgrFltAggr OBJECT-TYPE
    SYNTAX       Unsigned64
    MAX-ACCESS   read-only
    STATUS       current
    DESCRIPTION
        "Cisco Firepower fabric:EpMgr:fltAggr managed object property"
    ::= { cfprApFabricEpMgrEntry 7 }

cfprApFabricEpMgrFsmDescr OBJECT-TYPE
    SYNTAX       SnmpAdminString
    MAX-ACCESS   read-only
    STATUS       current
    DESCRIPTION
        "Cisco Firepower fabric:EpMgr:fsmDescr managed object property"
    ::= { cfprApFabricEpMgrEntry 8 }

cfprApFabricEpMgrFsmFlags OBJECT-TYPE
    SYNTAX       SnmpAdminString
    MAX-ACCESS   read-only
    STATUS       current
    DESCRIPTION
        "Cisco Firepower fabric:EpMgr:fsmFlags managed object property"
    ::= { cfprApFabricEpMgrEntry 9 }

cfprApFabricEpMgrFsmPrev OBJECT-TYPE
    SYNTAX       SnmpAdminString
    MAX-ACCESS   read-only
    STATUS       current
    DESCRIPTION
        "Cisco Firepower fabric:EpMgr:fsmPrev managed object property"
    ::= { cfprApFabricEpMgrEntry 10 }

cfprApFabricEpMgrFsmProgr OBJECT-TYPE
    SYNTAX       Gauge32
    MAX-ACCESS   read-only
    STATUS       current
    DESCRIPTION
        "Cisco Firepower fabric:EpMgr:fsmProgr managed object property"
    ::= { cfprApFabricEpMgrEntry 11 }

cfprApFabricEpMgrFsmRmtInvErrCode OBJECT-TYPE
    SYNTAX       Gauge32
    MAX-ACCESS   read-only
    STATUS       current
    DESCRIPTION
        "Cisco Firepower fabric:EpMgr:fsmRmtInvErrCode
        managed object property"
    ::= { cfprApFabricEpMgrEntry 12 }

cfprApFabricEpMgrFsmRmtInvErrDescr OBJECT-TYPE
    SYNTAX       SnmpAdminString
    MAX-ACCESS   read-only
    STATUS       current
    DESCRIPTION
        "Cisco Firepower fabric:EpMgr:fsmRmtInvErrDescr
        managed object property"
    ::= { cfprApFabricEpMgrEntry 13 }

cfprApFabricEpMgrFsmRmtInvRslt OBJECT-TYPE
    SYNTAX       CfprApConditionRemoteInvRslt
    MAX-ACCESS   read-only
    STATUS       current
    DESCRIPTION
        "Cisco Firepower fabric:EpMgr:fsmRmtInvRslt managed
        object property"
    ::= { cfprApFabricEpMgrEntry 14 }

cfprApFabricEpMgrFsmStageDescr OBJECT-TYPE
    SYNTAX       SnmpAdminString
    MAX-ACCESS   read-only
    STATUS       current
    DESCRIPTION
        "Cisco Firepower fabric:EpMgr:fsmStageDescr managed
        object property"
    ::= { cfprApFabricEpMgrEntry 15 }

cfprApFabricEpMgrFsmStamp OBJECT-TYPE
    SYNTAX       DateAndTime
    MAX-ACCESS   read-only
    STATUS       current
    DESCRIPTION
        "Cisco Firepower fabric:EpMgr:fsmStamp managed object property"
    ::= { cfprApFabricEpMgrEntry 16 }

cfprApFabricEpMgrFsmStatus OBJECT-TYPE
    SYNTAX       SnmpAdminString
    MAX-ACCESS   read-only
    STATUS       current
    DESCRIPTION
        "Cisco Firepower fabric:EpMgr:fsmStatus managed object property"
    ::= { cfprApFabricEpMgrEntry 17 }

cfprApFabricEpMgrFsmTry OBJECT-TYPE
    SYNTAX       Gauge32
    MAX-ACCESS   read-only
    STATUS       current
    DESCRIPTION
        "Cisco Firepower fabric:EpMgr:fsmTry managed object property"
    ::= { cfprApFabricEpMgrEntry 18 }

cfprApFabricEpMgrId OBJECT-TYPE
    SYNTAX       CfprApNetworkSwitchId
    MAX-ACCESS   read-only
    STATUS       current
    DESCRIPTION
        "Cisco Firepower fabric:EpMgr:id managed object property"
    ::= { cfprApFabricEpMgrEntry 19 }

cfprApFabricEpMgrFsmTable OBJECT-TYPE
    SYNTAX           SEQUENCE OF CfprApFabricEpMgrFsmEntry
    MAX-ACCESS       not-accessible
    STATUS           current
    DESCRIPTION
        "Cisco Firepower fabric:EpMgrFsm managed object table"
    ::= { cfprApFabricObjects 17 }

cfprApFabricEpMgrFsmEntry OBJECT-TYPE
    SYNTAX           CfprApFabricEpMgrFsmEntry
    MAX-ACCESS       not-accessible
    STATUS           current
    DESCRIPTION
        "Entry for the cfprApFabricEpMgrFsmTable table."
    INDEX { cfprApFabricEpMgrFsmInstanceId }
    ::= { cfprApFabricEpMgrFsmTable 1 }

CfprApFabricEpMgrFsmEntry ::= SEQUENCE {
    cfprApFabricEpMgrFsmInstanceId                                   CfprApManagedObjectId,
    cfprApFabricEpMgrFsmDn                                           CfprApManagedObjectDn,
    cfprApFabricEpMgrFsmRn                                           SnmpAdminString,
    cfprApFabricEpMgrFsmCompletionTime                               DateAndTime,
    cfprApFabricEpMgrFsmCurrentFsm                                   CfprApFabricEpMgrFsmCurrentFsm,
    cfprApFabricEpMgrFsmDescrData                                    SnmpAdminString,
    cfprApFabricEpMgrFsmFsmStatus                                    CfprApFsmFsmStageStatus,
    cfprApFabricEpMgrFsmProgress                                     Gauge32,
    cfprApFabricEpMgrFsmRmtErrCode                                   Gauge32,
    cfprApFabricEpMgrFsmRmtErrDescr                                  SnmpAdminString,
    cfprApFabricEpMgrFsmRmtRslt                                      CfprApConditionRemoteInvRslt
}

cfprApFabricEpMgrFsmInstanceId OBJECT-TYPE
    SYNTAX       CfprApManagedObjectId
    MAX-ACCESS   not-accessible
    STATUS       current
    DESCRIPTION
        "Instance identifier of the managed object."
    ::= { cfprApFabricEpMgrFsmEntry 1 }

cfprApFabricEpMgrFsmDn OBJECT-TYPE
    SYNTAX       CfprApManagedObjectDn
    MAX-ACCESS   read-only
    STATUS       current
    DESCRIPTION
        "Cisco Firepower fabric:EpMgrFsm:dn managed object property"
    ::= { cfprApFabricEpMgrFsmEntry 2 }

cfprApFabricEpMgrFsmRn OBJECT-TYPE
    SYNTAX       SnmpAdminString
    MAX-ACCESS   read-only
    STATUS       current
    DESCRIPTION
        "Cisco Firepower fabric:EpMgrFsm:rn managed object property"
    ::= { cfprApFabricEpMgrFsmEntry 3 }

cfprApFabricEpMgrFsmCompletionTime OBJECT-TYPE
    SYNTAX       DateAndTime
    MAX-ACCESS   read-only
    STATUS       current
    DESCRIPTION
        "Cisco Firepower fabric:EpMgrFsm:completionTime
        managed object property"
    ::= { cfprApFabricEpMgrFsmEntry 4 }

cfprApFabricEpMgrFsmCurrentFsm OBJECT-TYPE
    SYNTAX       CfprApFabricEpMgrFsmCurrentFsm
    MAX-ACCESS   read-only
    STATUS       current
    DESCRIPTION
        "Cisco Firepower fabric:EpMgrFsm:currentFsm managed
        object property"
    ::= { cfprApFabricEpMgrFsmEntry 5 }

cfprApFabricEpMgrFsmDescrData OBJECT-TYPE
    SYNTAX       SnmpAdminString
    MAX-ACCESS   read-only
    STATUS       current
    DESCRIPTION
        "Cisco Firepower fabric:EpMgrFsm:descr managed object property"
    ::= { cfprApFabricEpMgrFsmEntry 6 }

cfprApFabricEpMgrFsmFsmStatus OBJECT-TYPE
    SYNTAX       CfprApFsmFsmStageStatus
    MAX-ACCESS   read-only
    STATUS       current
    DESCRIPTION
        "Cisco Firepower fabric:EpMgrFsm:fsmStatus managed
        object property"
    ::= { cfprApFabricEpMgrFsmEntry 7 }

cfprApFabricEpMgrFsmProgress OBJECT-TYPE
    SYNTAX       Gauge32
    MAX-ACCESS   read-only
    STATUS       current
    DESCRIPTION
        "Cisco Firepower fabric:EpMgrFsm:progress managed object property"
    ::= { cfprApFabricEpMgrFsmEntry 8 }

cfprApFabricEpMgrFsmRmtErrCode OBJECT-TYPE
    SYNTAX       Gauge32
    MAX-ACCESS   read-only
    STATUS       current
    DESCRIPTION
        "Cisco Firepower fabric:EpMgrFsm:rmtErrCode managed
        object property"
    ::= { cfprApFabricEpMgrFsmEntry 9 }

cfprApFabricEpMgrFsmRmtErrDescr OBJECT-TYPE
    SYNTAX       SnmpAdminString
    MAX-ACCESS   read-only
    STATUS       current
    DESCRIPTION
        "Cisco Firepower fabric:EpMgrFsm:rmtErrDescr managed
        object property"
    ::= { cfprApFabricEpMgrFsmEntry 10 }

cfprApFabricEpMgrFsmRmtRslt OBJECT-TYPE
    SYNTAX       CfprApConditionRemoteInvRslt
    MAX-ACCESS   read-only
    STATUS       current
    DESCRIPTION
        "Cisco Firepower fabric:EpMgrFsm:rmtRslt managed object property"
    ::= { cfprApFabricEpMgrFsmEntry 11 }

cfprApFabricEpMgrFsmStageTable OBJECT-TYPE
    SYNTAX           SEQUENCE OF CfprApFabricEpMgrFsmStageEntry
    MAX-ACCESS       not-accessible
    STATUS           current
    DESCRIPTION
        "Cisco Firepower fabric:EpMgrFsmStage managed object table"
    ::= { cfprApFabricObjects 18 }

cfprApFabricEpMgrFsmStageEntry OBJECT-TYPE
    SYNTAX           CfprApFabricEpMgrFsmStageEntry
    MAX-ACCESS       not-accessible
    STATUS           current
    DESCRIPTION
        "Entry for the cfprApFabricEpMgrFsmStageTable table."
    INDEX { cfprApFabricEpMgrFsmStageInstanceId }
    ::= { cfprApFabricEpMgrFsmStageTable 1 }

CfprApFabricEpMgrFsmStageEntry ::= SEQUENCE {
    cfprApFabricEpMgrFsmStageInstanceId                              CfprApManagedObjectId,
    cfprApFabricEpMgrFsmStageDn                                      CfprApManagedObjectDn,
    cfprApFabricEpMgrFsmStageRn                                      SnmpAdminString,
    cfprApFabricEpMgrFsmStageDescrData                               SnmpAdminString,
    cfprApFabricEpMgrFsmStageLastUpdateTime                          DateAndTime,
    cfprApFabricEpMgrFsmStageName                                    CfprApFabricEpMgrFsmStageName,
    cfprApFabricEpMgrFsmStageOrder                                   Gauge32,
    cfprApFabricEpMgrFsmStageRetry                                   Gauge32,
    cfprApFabricEpMgrFsmStageStageStatus                             CfprApFsmFsmStageStatus
}

cfprApFabricEpMgrFsmStageInstanceId OBJECT-TYPE
    SYNTAX       CfprApManagedObjectId
    MAX-ACCESS   not-accessible
    STATUS       current
    DESCRIPTION
        "Instance identifier of the managed object."
    ::= { cfprApFabricEpMgrFsmStageEntry 1 }

cfprApFabricEpMgrFsmStageDn OBJECT-TYPE
    SYNTAX       CfprApManagedObjectDn
    MAX-ACCESS   read-only
    STATUS       current
    DESCRIPTION
        "Cisco Firepower fabric:EpMgrFsmStage:dn managed object property"
    ::= { cfprApFabricEpMgrFsmStageEntry 2 }

cfprApFabricEpMgrFsmStageRn OBJECT-TYPE
    SYNTAX       SnmpAdminString
    MAX-ACCESS   read-only
    STATUS       current
    DESCRIPTION
        "Cisco Firepower fabric:EpMgrFsmStage:rn managed object property"
    ::= { cfprApFabricEpMgrFsmStageEntry 3 }

cfprApFabricEpMgrFsmStageDescrData OBJECT-TYPE
    SYNTAX       SnmpAdminString
    MAX-ACCESS   read-only
    STATUS       current
    DESCRIPTION
        "Cisco Firepower fabric:EpMgrFsmStage:descr managed
        object property"
    ::= { cfprApFabricEpMgrFsmStageEntry 4 }

cfprApFabricEpMgrFsmStageLastUpdateTime OBJECT-TYPE
    SYNTAX       DateAndTime
    MAX-ACCESS   read-only
    STATUS       current
    DESCRIPTION
        "Cisco Firepower fabric:EpMgrFsmStage:lastUpdateTime
        managed object property"
    ::= { cfprApFabricEpMgrFsmStageEntry 5 }

cfprApFabricEpMgrFsmStageName OBJECT-TYPE
    SYNTAX       CfprApFabricEpMgrFsmStageName
    MAX-ACCESS   read-only
    STATUS       current
    DESCRIPTION
        "Cisco Firepower fabric:EpMgrFsmStage:name managed
        object property"
    ::= { cfprApFabricEpMgrFsmStageEntry 6 }

cfprApFabricEpMgrFsmStageOrder OBJECT-TYPE
    SYNTAX       Gauge32
    MAX-ACCESS   read-only
    STATUS       current
    DESCRIPTION
        "Cisco Firepower fabric:EpMgrFsmStage:order managed
        object property"
    ::= { cfprApFabricEpMgrFsmStageEntry 7 }

cfprApFabricEpMgrFsmStageRetry OBJECT-TYPE
    SYNTAX       Gauge32
    MAX-ACCESS   read-only
    STATUS       current
    DESCRIPTION
        "Cisco Firepower fabric:EpMgrFsmStage:retry managed
        object property"
    ::= { cfprApFabricEpMgrFsmStageEntry 8 }

cfprApFabricEpMgrFsmStageStageStatus OBJECT-TYPE
    SYNTAX       CfprApFsmFsmStageStatus
    MAX-ACCESS   read-only
    STATUS       current
    DESCRIPTION
        "Cisco Firepower fabric:EpMgrFsmStage:stageStatus
        managed object property"
    ::= { cfprApFabricEpMgrFsmStageEntry 9 }

cfprApFabricEpMgrFsmTaskTable OBJECT-TYPE
    SYNTAX           SEQUENCE OF CfprApFabricEpMgrFsmTaskEntry
    MAX-ACCESS       not-accessible
    STATUS           current
    DESCRIPTION
        "Cisco Firepower fabric:EpMgrFsmTask managed object table"
    ::= { cfprApFabricObjects 19 }

cfprApFabricEpMgrFsmTaskEntry OBJECT-TYPE
    SYNTAX           CfprApFabricEpMgrFsmTaskEntry
    MAX-ACCESS       not-accessible
    STATUS           current
    DESCRIPTION
        "Entry for the cfprApFabricEpMgrFsmTaskTable table."
    INDEX { cfprApFabricEpMgrFsmTaskInstanceId }
    ::= { cfprApFabricEpMgrFsmTaskTable 1 }

CfprApFabricEpMgrFsmTaskEntry ::= SEQUENCE {
    cfprApFabricEpMgrFsmTaskInstanceId                               CfprApManagedObjectId,
    cfprApFabricEpMgrFsmTaskDn                                       CfprApManagedObjectDn,
    cfprApFabricEpMgrFsmTaskRn                                       SnmpAdminString,
    cfprApFabricEpMgrFsmTaskCompletion                               CfprApFsmCompletion,
    cfprApFabricEpMgrFsmTaskFlags                                    CfprApFabricEpMgrFsmTaskFlags,
    cfprApFabricEpMgrFsmTaskItem                                     CfprApFabricEpMgrFsmTaskItem,
    cfprApFabricEpMgrFsmTaskSeqId                                    Gauge32
}

cfprApFabricEpMgrFsmTaskInstanceId OBJECT-TYPE
    SYNTAX       CfprApManagedObjectId
    MAX-ACCESS   not-accessible
    STATUS       current
    DESCRIPTION
        "Instance identifier of the managed object."
    ::= { cfprApFabricEpMgrFsmTaskEntry 1 }

cfprApFabricEpMgrFsmTaskDn OBJECT-TYPE
    SYNTAX       CfprApManagedObjectDn
    MAX-ACCESS   read-only
    STATUS       current
    DESCRIPTION
        "Cisco Firepower fabric:EpMgrFsmTask:dn managed object property"
    ::= { cfprApFabricEpMgrFsmTaskEntry 2 }

cfprApFabricEpMgrFsmTaskRn OBJECT-TYPE
    SYNTAX       SnmpAdminString
    MAX-ACCESS   read-only
    STATUS       current
    DESCRIPTION
        "Cisco Firepower fabric:EpMgrFsmTask:rn managed object property"
    ::= { cfprApFabricEpMgrFsmTaskEntry 3 }

cfprApFabricEpMgrFsmTaskCompletion OBJECT-TYPE
    SYNTAX       CfprApFsmCompletion
    MAX-ACCESS   read-only
    STATUS       current
    DESCRIPTION
        "Cisco Firepower fabric:EpMgrFsmTask:completion
        managed object property"
    ::= { cfprApFabricEpMgrFsmTaskEntry 4 }

cfprApFabricEpMgrFsmTaskFlags OBJECT-TYPE
    SYNTAX       CfprApFabricEpMgrFsmTaskFlags
    MAX-ACCESS   read-only
    STATUS       current
    DESCRIPTION
        "Cisco Firepower fabric:EpMgrFsmTask:flags managed
        object property"
    ::= { cfprApFabricEpMgrFsmTaskEntry 5 }

cfprApFabricEpMgrFsmTaskItem OBJECT-TYPE
    SYNTAX       CfprApFabricEpMgrFsmTaskItem
    MAX-ACCESS   read-only
    STATUS       current
    DESCRIPTION
        "Cisco Firepower fabric:EpMgrFsmTask:item managed object property"
    ::= { cfprApFabricEpMgrFsmTaskEntry 6 }

cfprApFabricEpMgrFsmTaskSeqId OBJECT-TYPE
    SYNTAX       Gauge32
    MAX-ACCESS   read-only
    STATUS       current
    DESCRIPTION
        "Cisco Firepower fabric:EpMgrFsmTask:seqId managed
        object property"
    ::= { cfprApFabricEpMgrFsmTaskEntry 7 }

cfprApFabricEthEstcTable OBJECT-TYPE
    SYNTAX           SEQUENCE OF CfprApFabricEthEstcEntry
    MAX-ACCESS       not-accessible
    STATUS           current
    DESCRIPTION
        "Cisco Firepower fabric:EthEstc managed object table"
    ::= { cfprApFabricObjects 20 }

cfprApFabricEthEstcEntry OBJECT-TYPE
    SYNTAX           CfprApFabricEthEstcEntry
    MAX-ACCESS       not-accessible
    STATUS           current
    DESCRIPTION
        "Entry for the cfprApFabricEthEstcTable table."
    INDEX { cfprApFabricEthEstcInstanceId }
    ::= { cfprApFabricEthEstcTable 1 }

CfprApFabricEthEstcEntry ::= SEQUENCE {
    cfprApFabricEthEstcInstanceId                                    CfprApManagedObjectId,
    cfprApFabricEthEstcDn                                            CfprApManagedObjectDn,
    cfprApFabricEthEstcRn                                            SnmpAdminString,
    cfprApFabricEthEstcId                                            CfprApNetworkSwitchId,
    cfprApFabricEthEstcLocale                                        CfprApFabricExternalLocale,
    cfprApFabricEthEstcName                                          SnmpAdminString,
    cfprApFabricEthEstcTransport                                     CfprApFabricEthEstcTransport,
    cfprApFabricEthEstcType                                          CfprApFabricEthEstcType
}

cfprApFabricEthEstcInstanceId OBJECT-TYPE
    SYNTAX       CfprApManagedObjectId
    MAX-ACCESS   not-accessible
    STATUS       current
    DESCRIPTION
        "Instance identifier of the managed object."
    ::= { cfprApFabricEthEstcEntry 1 }

cfprApFabricEthEstcDn OBJECT-TYPE
    SYNTAX       CfprApManagedObjectDn
    MAX-ACCESS   read-only
    STATUS       current
    DESCRIPTION
        "Cisco Firepower fabric:EthEstc:dn managed object property"
    ::= { cfprApFabricEthEstcEntry 2 }

cfprApFabricEthEstcRn OBJECT-TYPE
    SYNTAX       SnmpAdminString
    MAX-ACCESS   read-only
    STATUS       current
    DESCRIPTION
        "Cisco Firepower fabric:EthEstc:rn managed object property"
    ::= { cfprApFabricEthEstcEntry 3 }

cfprApFabricEthEstcId OBJECT-TYPE
    SYNTAX       CfprApNetworkSwitchId
    MAX-ACCESS   read-only
    STATUS       current
    DESCRIPTION
        "Cisco Firepower fabric:EthEstc:id managed object property"
    ::= { cfprApFabricEthEstcEntry 4 }

cfprApFabricEthEstcLocale OBJECT-TYPE
    SYNTAX       CfprApFabricExternalLocale
    MAX-ACCESS   read-only
    STATUS       current
    DESCRIPTION
        "Cisco Firepower fabric:EthEstc:locale managed object property"
    ::= { cfprApFabricEthEstcEntry 5 }

cfprApFabricEthEstcName OBJECT-TYPE
    SYNTAX       SnmpAdminString
    MAX-ACCESS   read-only
    STATUS       current
    DESCRIPTION
        "Cisco Firepower fabric:EthEstc:name managed object property"
    ::= { cfprApFabricEthEstcEntry 6 }

cfprApFabricEthEstcTransport OBJECT-TYPE
    SYNTAX       CfprApFabricEthEstcTransport
    MAX-ACCESS   read-only
    STATUS       current
    DESCRIPTION
        "Cisco Firepower fabric:EthEstc:transport managed object property"
    ::= { cfprApFabricEthEstcEntry 7 }

cfprApFabricEthEstcType OBJECT-TYPE
    SYNTAX       CfprApFabricEthEstcType
    MAX-ACCESS   read-only
    STATUS       current
    DESCRIPTION
        "Cisco Firepower fabric:EthEstc:type managed object property"
    ::= { cfprApFabricEthEstcEntry 8 }

cfprApFabricEthEstcCloudTable OBJECT-TYPE
    SYNTAX           SEQUENCE OF CfprApFabricEthEstcCloudEntry
    MAX-ACCESS       not-accessible
    STATUS           current
    DESCRIPTION
        "Cisco Firepower fabric:EthEstcCloud managed object table"
    ::= { cfprApFabricObjects 21 }

cfprApFabricEthEstcCloudEntry OBJECT-TYPE
    SYNTAX           CfprApFabricEthEstcCloudEntry
    MAX-ACCESS       not-accessible
    STATUS           current
    DESCRIPTION
        "Entry for the cfprApFabricEthEstcCloudTable table."
    INDEX { cfprApFabricEthEstcCloudInstanceId }
    ::= { cfprApFabricEthEstcCloudTable 1 }

CfprApFabricEthEstcCloudEntry ::= SEQUENCE {
    cfprApFabricEthEstcCloudInstanceId                               CfprApManagedObjectId,
    cfprApFabricEthEstcCloudDn                                       CfprApManagedObjectDn,
    cfprApFabricEthEstcCloudRn                                       SnmpAdminString
}

cfprApFabricEthEstcCloudInstanceId OBJECT-TYPE
    SYNTAX       CfprApManagedObjectId
    MAX-ACCESS   not-accessible
    STATUS       current
    DESCRIPTION
        "Instance identifier of the managed object."
    ::= { cfprApFabricEthEstcCloudEntry 1 }

cfprApFabricEthEstcCloudDn OBJECT-TYPE
    SYNTAX       CfprApManagedObjectDn
    MAX-ACCESS   read-only
    STATUS       current
    DESCRIPTION
        "Cisco Firepower fabric:EthEstcCloud:dn managed object property"
    ::= { cfprApFabricEthEstcCloudEntry 2 }

cfprApFabricEthEstcCloudRn OBJECT-TYPE
    SYNTAX       SnmpAdminString
    MAX-ACCESS   read-only
    STATUS       current
    DESCRIPTION
        "Cisco Firepower fabric:EthEstcCloud:rn managed object property"
    ::= { cfprApFabricEthEstcCloudEntry 3 }

cfprApFabricEthEstcEpTable OBJECT-TYPE
    SYNTAX           SEQUENCE OF CfprApFabricEthEstcEpEntry
    MAX-ACCESS       not-accessible
    STATUS           current
    DESCRIPTION
        "Cisco Firepower fabric:EthEstcEp managed object table"
    ::= { cfprApFabricObjects 22 }

cfprApFabricEthEstcEpEntry OBJECT-TYPE
    SYNTAX           CfprApFabricEthEstcEpEntry
    MAX-ACCESS       not-accessible
    STATUS           current
    DESCRIPTION
        "Entry for the cfprApFabricEthEstcEpTable table."
    INDEX { cfprApFabricEthEstcEpInstanceId }
    ::= { cfprApFabricEthEstcEpTable 1 }

CfprApFabricEthEstcEpEntry ::= SEQUENCE {
    cfprApFabricEthEstcEpInstanceId                                  CfprApManagedObjectId,
    cfprApFabricEthEstcEpDn                                          CfprApManagedObjectDn,
    cfprApFabricEthEstcEpRn                                          SnmpAdminString,
    cfprApFabricEthEstcEpAdminSpeed                                  CfprApPortEthSpeed,
    cfprApFabricEthEstcEpAdminState                                  CfprApFabricExternalEpAdminState,
    cfprApFabricEthEstcEpAggrPortId                                  Gauge32,
    cfprApFabricEthEstcEpChassisId                                   Gauge32,
    cfprApFabricEthEstcEpConfigState                                 CfprApFabricConfigState,
    cfprApFabricEthEstcEpEpDn                                        SnmpAdminString,
    cfprApFabricEthEstcEpFlowCtrlPolicy                              SnmpAdminString,
    cfprApFabricEthEstcEpFltAggr                                     Unsigned64,
    cfprApFabricEthEstcEpIfRole                                      CfprApFabricAEthEstcEpIfRole,
    cfprApFabricEthEstcEpIfType                                      CfprApFabricPIoEpIfType,
    cfprApFabricEthEstcEpLicGP                                       Unsigned64,
    cfprApFabricEthEstcEpLicState                                    CfprApLicenseState,
    cfprApFabricEthEstcEpLocale                                      CfprApFabricExternalEpLocale,
    cfprApFabricEthEstcEpName                                        SnmpAdminString,
    cfprApFabricEthEstcEpNwCtrlPolicyName                            SnmpAdminString,
    cfprApFabricEthEstcEpOperNwCtrlPolicyName                        SnmpAdminString,
    cfprApFabricEthEstcEpOperPortMode                                CfprApFabricEthEstcOperPortMode,
    cfprApFabricEthEstcEpOperState                                   CfprApFabricPIoEpOperState,
    cfprApFabricEthEstcEpOperStateReason                             SnmpAdminString,
    cfprApFabricEthEstcEpPeerAggrPortId                              Gauge32,
    cfprApFabricEthEstcEpPeerChassisId                               Gauge32,
    cfprApFabricEthEstcEpPeerDn                                      SnmpAdminString,
    cfprApFabricEthEstcEpPeerPortId                                  Gauge32,
    cfprApFabricEthEstcEpPeerSlotId                                  Gauge32,
    cfprApFabricEthEstcEpPinGroupName                                SnmpAdminString,
    cfprApFabricEthEstcEpPortId                                      CfprApFabricEthEstcEpPortId,
    cfprApFabricEthEstcEpPortMode                                    CfprApFabricEthEstcPortMode,
    cfprApFabricEthEstcEpPrio                                        CfprApFabricEthEstcEpPrio,
    cfprApFabricEthEstcEpSlotId                                      CfprApFabricEthEstcEpSlotId,
    cfprApFabricEthEstcEpSwitchId                                    CfprApNetworkSwitchId,
    cfprApFabricEthEstcEpTransport                                   CfprApFabricEthEstcEpTransport,
    cfprApFabricEthEstcEpType                                        CfprApFabricEthEstcEpType,
    cfprApFabricEthEstcEpUsrLbl                                      SnmpAdminString,
    cfprApFabricEthEstcEpWarnings                                    CfprApFabricWarnings
}

cfprApFabricEthEstcEpInstanceId OBJECT-TYPE
    SYNTAX       CfprApManagedObjectId
    MAX-ACCESS   not-accessible
    STATUS       current
    DESCRIPTION
        "Instance identifier of the managed object."
    ::= { cfprApFabricEthEstcEpEntry 1 }

cfprApFabricEthEstcEpDn OBJECT-TYPE
    SYNTAX       CfprApManagedObjectDn
    MAX-ACCESS   read-only
    STATUS       current
    DESCRIPTION
        "Cisco Firepower fabric:EthEstcEp:dn managed object property"
    ::= { cfprApFabricEthEstcEpEntry 2 }

cfprApFabricEthEstcEpRn OBJECT-TYPE
    SYNTAX       SnmpAdminString
    MAX-ACCESS   read-only
    STATUS       current
    DESCRIPTION
        "Cisco Firepower fabric:EthEstcEp:rn managed object property"
    ::= { cfprApFabricEthEstcEpEntry 3 }

cfprApFabricEthEstcEpAdminSpeed OBJECT-TYPE
    SYNTAX       CfprApPortEthSpeed
    MAX-ACCESS   read-only
    STATUS       current
    DESCRIPTION
        "Cisco Firepower fabric:EthEstcEp:adminSpeed managed
        object property"
    ::= { cfprApFabricEthEstcEpEntry 4 }

cfprApFabricEthEstcEpAdminState OBJECT-TYPE
    SYNTAX       CfprApFabricExternalEpAdminState
    MAX-ACCESS   read-only
    STATUS       current
    DESCRIPTION
        "Cisco Firepower fabric:EthEstcEp:adminState managed
        object property"
    ::= { cfprApFabricEthEstcEpEntry 5 }

cfprApFabricEthEstcEpAggrPortId OBJECT-TYPE
    SYNTAX       Gauge32
    MAX-ACCESS   read-only
    STATUS       current
    DESCRIPTION
        "Cisco Firepower fabric:EthEstcEp:aggrPortId managed
        object property"
    ::= { cfprApFabricEthEstcEpEntry 6 }

cfprApFabricEthEstcEpChassisId OBJECT-TYPE
    SYNTAX       Gauge32
    MAX-ACCESS   read-only
    STATUS       current
    DESCRIPTION
        "Cisco Firepower fabric:EthEstcEp:chassisId managed
        object property"
    ::= { cfprApFabricEthEstcEpEntry 7 }

cfprApFabricEthEstcEpConfigState OBJECT-TYPE
    SYNTAX       CfprApFabricConfigState
    MAX-ACCESS   read-only
    STATUS       current
    DESCRIPTION
        "Cisco Firepower fabric:EthEstcEp:configState managed
        object property"
    ::= { cfprApFabricEthEstcEpEntry 8 }

cfprApFabricEthEstcEpEpDn OBJECT-TYPE
    SYNTAX       SnmpAdminString
    MAX-ACCESS   read-only
    STATUS       current
    DESCRIPTION
        "Cisco Firepower fabric:EthEstcEp:epDn managed object property"
    ::= { cfprApFabricEthEstcEpEntry 9 }

cfprApFabricEthEstcEpFlowCtrlPolicy OBJECT-TYPE
    SYNTAX       SnmpAdminString
    MAX-ACCESS   read-only
    STATUS       current
    DESCRIPTION
        "Cisco Firepower fabric:EthEstcEp:flowCtrlPolicy
        managed object property"
    ::= { cfprApFabricEthEstcEpEntry 10 }

cfprApFabricEthEstcEpFltAggr OBJECT-TYPE
    SYNTAX       Unsigned64
    MAX-ACCESS   read-only
    STATUS       current
    DESCRIPTION
        "Cisco Firepower fabric:EthEstcEp:fltAggr managed object property"
    ::= { cfprApFabricEthEstcEpEntry 11 }

cfprApFabricEthEstcEpIfRole OBJECT-TYPE
    SYNTAX       CfprApFabricAEthEstcEpIfRole
    MAX-ACCESS   read-only
    STATUS       current
    DESCRIPTION
        "Cisco Firepower fabric:EthEstcEp:ifRole managed object property"
    ::= { cfprApFabricEthEstcEpEntry 12 }

cfprApFabricEthEstcEpIfType OBJECT-TYPE
    SYNTAX       CfprApFabricPIoEpIfType
    MAX-ACCESS   read-only
    STATUS       current
    DESCRIPTION
        "Cisco Firepower fabric:EthEstcEp:ifType managed object property"
    ::= { cfprApFabricEthEstcEpEntry 13 }

cfprApFabricEthEstcEpLicGP OBJECT-TYPE
    SYNTAX       Unsigned64
    MAX-ACCESS   read-only
    STATUS       current
    DESCRIPTION
        "Cisco Firepower fabric:EthEstcEp:licGP managed object property"
    ::= { cfprApFabricEthEstcEpEntry 14 }

cfprApFabricEthEstcEpLicState OBJECT-TYPE
    SYNTAX       CfprApLicenseState
    MAX-ACCESS   read-only
    STATUS       current
    DESCRIPTION
        "Cisco Firepower fabric:EthEstcEp:licState managed
        object property"
    ::= { cfprApFabricEthEstcEpEntry 15 }

cfprApFabricEthEstcEpLocale OBJECT-TYPE
    SYNTAX       CfprApFabricExternalEpLocale
    MAX-ACCESS   read-only
    STATUS       current
    DESCRIPTION
        "Cisco Firepower fabric:EthEstcEp:locale managed object property"
    ::= { cfprApFabricEthEstcEpEntry 16 }

cfprApFabricEthEstcEpName OBJECT-TYPE
    SYNTAX       SnmpAdminString
    MAX-ACCESS   read-only
    STATUS       current
    DESCRIPTION
        "Cisco Firepower fabric:EthEstcEp:name managed object property"
    ::= { cfprApFabricEthEstcEpEntry 17 }

cfprApFabricEthEstcEpNwCtrlPolicyName OBJECT-TYPE
    SYNTAX       SnmpAdminString
    MAX-ACCESS   read-only
    STATUS       current
    DESCRIPTION
        "Cisco Firepower fabric:EthEstcEp:nwCtrlPolicyName
        managed object property"
    ::= { cfprApFabricEthEstcEpEntry 18 }

cfprApFabricEthEstcEpOperNwCtrlPolicyName OBJECT-TYPE
    SYNTAX       SnmpAdminString
    MAX-ACCESS   read-only
    STATUS       current
    DESCRIPTION
        "Cisco Firepower fabric:EthEstcEp:operNwCtrlPolicyName
        managed object property"
    ::= { cfprApFabricEthEstcEpEntry 19 }

cfprApFabricEthEstcEpOperPortMode OBJECT-TYPE
    SYNTAX       CfprApFabricEthEstcOperPortMode
    MAX-ACCESS   read-only
    STATUS       current
    DESCRIPTION
        "Cisco Firepower fabric:EthEstcEp:operPortMode
        managed object property"
    ::= { cfprApFabricEthEstcEpEntry 20 }

cfprApFabricEthEstcEpOperState OBJECT-TYPE
    SYNTAX       CfprApFabricPIoEpOperState
    MAX-ACCESS   read-only
    STATUS       current
    DESCRIPTION
        "Cisco Firepower fabric:EthEstcEp:operState managed
        object property"
    ::= { cfprApFabricEthEstcEpEntry 21 }

cfprApFabricEthEstcEpOperStateReason OBJECT-TYPE
    SYNTAX       SnmpAdminString
    MAX-ACCESS   read-only
    STATUS       current
    DESCRIPTION
        "Cisco Firepower fabric:EthEstcEp:operStateReason
        managed object property"
    ::= { cfprApFabricEthEstcEpEntry 22 }

cfprApFabricEthEstcEpPeerAggrPortId OBJECT-TYPE
    SYNTAX       Gauge32
    MAX-ACCESS   read-only
    STATUS       current
    DESCRIPTION
        "Cisco Firepower fabric:EthEstcEp:peerAggrPortId
        managed object property"
    ::= { cfprApFabricEthEstcEpEntry 23 }

cfprApFabricEthEstcEpPeerChassisId OBJECT-TYPE
    SYNTAX       Gauge32
    MAX-ACCESS   read-only
    STATUS       current
    DESCRIPTION
        "Cisco Firepower fabric:EthEstcEp:peerChassisId
        managed object property"
    ::= { cfprApFabricEthEstcEpEntry 24 }

cfprApFabricEthEstcEpPeerDn OBJECT-TYPE
    SYNTAX       SnmpAdminString
    MAX-ACCESS   read-only
    STATUS       current
    DESCRIPTION
        "Cisco Firepower fabric:EthEstcEp:peerDn managed object property"
    ::= { cfprApFabricEthEstcEpEntry 25 }

cfprApFabricEthEstcEpPeerPortId OBJECT-TYPE
    SYNTAX       Gauge32
    MAX-ACCESS   read-only
    STATUS       current
    DESCRIPTION
        "Cisco Firepower fabric:EthEstcEp:peerPortId managed
        object property"
    ::= { cfprApFabricEthEstcEpEntry 26 }

cfprApFabricEthEstcEpPeerSlotId OBJECT-TYPE
    SYNTAX       Gauge32
    MAX-ACCESS   read-only
    STATUS       current
    DESCRIPTION
        "Cisco Firepower fabric:EthEstcEp:peerSlotId managed
        object property"
    ::= { cfprApFabricEthEstcEpEntry 27 }

cfprApFabricEthEstcEpPinGroupName OBJECT-TYPE
    SYNTAX       SnmpAdminString
    MAX-ACCESS   read-only
    STATUS       current
    DESCRIPTION
        "Cisco Firepower fabric:EthEstcEp:pinGroupName
        managed object property"
    ::= { cfprApFabricEthEstcEpEntry 28 }

cfprApFabricEthEstcEpPortId OBJECT-TYPE
    SYNTAX       CfprApFabricEthEstcEpPortId
    MAX-ACCESS   read-only
    STATUS       current
    DESCRIPTION
        "Cisco Firepower fabric:EthEstcEp:portId managed object property"
    ::= { cfprApFabricEthEstcEpEntry 29 }

cfprApFabricEthEstcEpPortMode OBJECT-TYPE
    SYNTAX       CfprApFabricEthEstcPortMode
    MAX-ACCESS   read-only
    STATUS       current
    DESCRIPTION
        "Cisco Firepower fabric:EthEstcEp:portMode managed
        object property"
    ::= { cfprApFabricEthEstcEpEntry 30 }

cfprApFabricEthEstcEpPrio OBJECT-TYPE
    SYNTAX       CfprApFabricEthEstcEpPrio
    MAX-ACCESS   read-only
    STATUS       current
    DESCRIPTION
        "Cisco Firepower fabric:EthEstcEp:prio managed object property"
    ::= { cfprApFabricEthEstcEpEntry 31 }

cfprApFabricEthEstcEpSlotId OBJECT-TYPE
    SYNTAX       CfprApFabricEthEstcEpSlotId
    MAX-ACCESS   read-only
    STATUS       current
    DESCRIPTION
        "Cisco Firepower fabric:EthEstcEp:slotId managed object property"
    ::= { cfprApFabricEthEstcEpEntry 32 }

cfprApFabricEthEstcEpSwitchId OBJECT-TYPE
    SYNTAX       CfprApNetworkSwitchId
    MAX-ACCESS   read-only
    STATUS       current
    DESCRIPTION
        "Cisco Firepower fabric:EthEstcEp:switchId managed
        object property"
    ::= { cfprApFabricEthEstcEpEntry 33 }

cfprApFabricEthEstcEpTransport OBJECT-TYPE
    SYNTAX       CfprApFabricEthEstcEpTransport
    MAX-ACCESS   read-only
    STATUS       current
    DESCRIPTION
        "Cisco Firepower fabric:EthEstcEp:transport managed
        object property"
    ::= { cfprApFabricEthEstcEpEntry 34 }

cfprApFabricEthEstcEpType OBJECT-TYPE
    SYNTAX       CfprApFabricEthEstcEpType
    MAX-ACCESS   read-only
    STATUS       current
    DESCRIPTION
        "Cisco Firepower fabric:EthEstcEp:type managed object property"
    ::= { cfprApFabricEthEstcEpEntry 35 }

cfprApFabricEthEstcEpUsrLbl OBJECT-TYPE
    SYNTAX       SnmpAdminString
    MAX-ACCESS   read-only
    STATUS       current
    DESCRIPTION
        "Cisco Firepower fabric:EthEstcEp:usrLbl managed object property"
    ::= { cfprApFabricEthEstcEpEntry 36 }

cfprApFabricEthEstcEpWarnings OBJECT-TYPE
    SYNTAX       CfprApFabricWarnings
    MAX-ACCESS   read-only
    STATUS       current
    DESCRIPTION
        "Cisco Firepower fabric:EthEstcEp:warnings managed
        object property"
    ::= { cfprApFabricEthEstcEpEntry 37 }

cfprApFabricEthEstcPcTable OBJECT-TYPE
    SYNTAX           SEQUENCE OF CfprApFabricEthEstcPcEntry
    MAX-ACCESS       not-accessible
    STATUS           current
    DESCRIPTION
        "Cisco Firepower fabric:EthEstcPc managed object table"
    ::= { cfprApFabricObjects 23 }

cfprApFabricEthEstcPcEntry OBJECT-TYPE
    SYNTAX           CfprApFabricEthEstcPcEntry
    MAX-ACCESS       not-accessible
    STATUS           current
    DESCRIPTION
        "Entry for the cfprApFabricEthEstcPcTable table."
    INDEX { cfprApFabricEthEstcPcInstanceId }
    ::= { cfprApFabricEthEstcPcTable 1 }

CfprApFabricEthEstcPcEntry ::= SEQUENCE {
    cfprApFabricEthEstcPcInstanceId                                  CfprApManagedObjectId,
    cfprApFabricEthEstcPcDn                                          CfprApManagedObjectDn,
    cfprApFabricEthEstcPcRn                                          SnmpAdminString,
    cfprApFabricEthEstcPcAdminSpeed                                  CfprApPortEthAdminSpeed,
    cfprApFabricEthEstcPcAdminState                                  CfprApFabricCIoEpAdminState,
    cfprApFabricEthEstcPcDescr                                       SnmpAdminString,
    cfprApFabricEthEstcPcEpDn                                        SnmpAdminString,
    cfprApFabricEthEstcPcFlowCtrlPolicy                              SnmpAdminString,
    cfprApFabricEthEstcPcFltAggr                                     Unsigned64,
    cfprApFabricEthEstcPcIfRole                                      CfprApFabricEstcPcIfRole,
    cfprApFabricEthEstcPcIfType                                      CfprApFabricCIoEpIfType,
    cfprApFabricEthEstcPcLacpPolicyName                              SnmpAdminString,
    cfprApFabricEthEstcPcLocale                                      CfprApFabricExternalPcLocale,
    cfprApFabricEthEstcPcName                                        SnmpAdminString,
    cfprApFabricEthEstcPcNwCtrlPolicyName                            SnmpAdminString,
    cfprApFabricEthEstcPcOperLacpPolicyName                          SnmpAdminString,
    cfprApFabricEthEstcPcOperNwCtrlPolicyName                        SnmpAdminString,
    cfprApFabricEthEstcPcOperSpeed                                   CfprApPortEthSpeed,
    cfprApFabricEthEstcPcOperState                                   CfprApNetworkPortOperState,
    cfprApFabricEthEstcPcPeerDn                                      SnmpAdminString,
    cfprApFabricEthEstcPcPinGroupName                                SnmpAdminString,
    cfprApFabricEthEstcPcPortId                                      Gauge32,
    cfprApFabricEthEstcPcPortMode                                    CfprApFabricEthEstcPortMode,
    cfprApFabricEthEstcPcPrio                                        CfprApQosPriority,
    cfprApFabricEthEstcPcProtocol                                    CfprApFabricEthPcProtocol,
    cfprApFabricEthEstcPcStateQual                                   SnmpAdminString,
    cfprApFabricEthEstcPcSwitchId                                    CfprApNetworkSwitchId,
    cfprApFabricEthEstcPcTransport                                   CfprApFabricEthEstcPcTransport,
    cfprApFabricEthEstcPcType                                        CfprApFabricEstcPcType,
    cfprApFabricEthEstcPcWarnings                                    CfprApFabricWarnings
}

cfprApFabricEthEstcPcInstanceId OBJECT-TYPE
    SYNTAX       CfprApManagedObjectId
    MAX-ACCESS   not-accessible
    STATUS       current
    DESCRIPTION
        "Instance identifier of the managed object."
    ::= { cfprApFabricEthEstcPcEntry 1 }

cfprApFabricEthEstcPcDn OBJECT-TYPE
    SYNTAX       CfprApManagedObjectDn
    MAX-ACCESS   read-only
    STATUS       current
    DESCRIPTION
        "Cisco Firepower fabric:EthEstcPc:dn managed object property"
    ::= { cfprApFabricEthEstcPcEntry 2 }

cfprApFabricEthEstcPcRn OBJECT-TYPE
    SYNTAX       SnmpAdminString
    MAX-ACCESS   read-only
    STATUS       current
    DESCRIPTION
        "Cisco Firepower fabric:EthEstcPc:rn managed object property"
    ::= { cfprApFabricEthEstcPcEntry 3 }

cfprApFabricEthEstcPcAdminSpeed OBJECT-TYPE
    SYNTAX       CfprApPortEthAdminSpeed
    MAX-ACCESS   read-only
    STATUS       current
    DESCRIPTION
        "Cisco Firepower fabric:EthEstcPc:adminSpeed managed
        object property"
    ::= { cfprApFabricEthEstcPcEntry 4 }

cfprApFabricEthEstcPcAdminState OBJECT-TYPE
    SYNTAX       CfprApFabricCIoEpAdminState
    MAX-ACCESS   read-only
    STATUS       current
    DESCRIPTION
        "Cisco Firepower fabric:EthEstcPc:adminState managed
        object property"
    ::= { cfprApFabricEthEstcPcEntry 5 }

cfprApFabricEthEstcPcDescr OBJECT-TYPE
    SYNTAX       SnmpAdminString
    MAX-ACCESS   read-only
    STATUS       current
    DESCRIPTION
        "Cisco Firepower fabric:EthEstcPc:descr managed object property"
    ::= { cfprApFabricEthEstcPcEntry 6 }

cfprApFabricEthEstcPcEpDn OBJECT-TYPE
    SYNTAX       SnmpAdminString
    MAX-ACCESS   read-only
    STATUS       current
    DESCRIPTION
        "Cisco Firepower fabric:EthEstcPc:epDn managed object property"
    ::= { cfprApFabricEthEstcPcEntry 7 }

cfprApFabricEthEstcPcFlowCtrlPolicy OBJECT-TYPE
    SYNTAX       SnmpAdminString
    MAX-ACCESS   read-only
    STATUS       current
    DESCRIPTION
        "Cisco Firepower fabric:EthEstcPc:flowCtrlPolicy
        managed object property"
    ::= { cfprApFabricEthEstcPcEntry 8 }

cfprApFabricEthEstcPcFltAggr OBJECT-TYPE
    SYNTAX       Unsigned64
    MAX-ACCESS   read-only
    STATUS       current
    DESCRIPTION
        "Cisco Firepower fabric:EthEstcPc:fltAggr managed object property"
    ::= { cfprApFabricEthEstcPcEntry 9 }

cfprApFabricEthEstcPcIfRole OBJECT-TYPE
    SYNTAX       CfprApFabricEstcPcIfRole
    MAX-ACCESS   read-only
    STATUS       current
    DESCRIPTION
        "Cisco Firepower fabric:EthEstcPc:ifRole managed object property"
    ::= { cfprApFabricEthEstcPcEntry 10 }

cfprApFabricEthEstcPcIfType OBJECT-TYPE
    SYNTAX       CfprApFabricCIoEpIfType
    MAX-ACCESS   read-only
    STATUS       current
    DESCRIPTION
        "Cisco Firepower fabric:EthEstcPc:ifType managed object property"
    ::= { cfprApFabricEthEstcPcEntry 11 }

cfprApFabricEthEstcPcLacpPolicyName OBJECT-TYPE
    SYNTAX       SnmpAdminString
    MAX-ACCESS   read-only
    STATUS       current
    DESCRIPTION
        "Cisco Firepower fabric:EthEstcPc:lacpPolicyName
        managed object property"
    ::= { cfprApFabricEthEstcPcEntry 12 }

cfprApFabricEthEstcPcLocale OBJECT-TYPE
    SYNTAX       CfprApFabricExternalPcLocale
    MAX-ACCESS   read-only
    STATUS       current
    DESCRIPTION
        "Cisco Firepower fabric:EthEstcPc:locale managed object property"
    ::= { cfprApFabricEthEstcPcEntry 13 }

cfprApFabricEthEstcPcName OBJECT-TYPE
    SYNTAX       SnmpAdminString
    MAX-ACCESS   read-only
    STATUS       current
    DESCRIPTION
        "Cisco Firepower fabric:EthEstcPc:name managed object property"
    ::= { cfprApFabricEthEstcPcEntry 14 }

cfprApFabricEthEstcPcNwCtrlPolicyName OBJECT-TYPE
    SYNTAX       SnmpAdminString
    MAX-ACCESS   read-only
    STATUS       current
    DESCRIPTION
        "Cisco Firepower fabric:EthEstcPc:nwCtrlPolicyName
        managed object property"
    ::= { cfprApFabricEthEstcPcEntry 15 }

cfprApFabricEthEstcPcOperLacpPolicyName OBJECT-TYPE
    SYNTAX       SnmpAdminString
    MAX-ACCESS   read-only
    STATUS       current
    DESCRIPTION
        "Cisco Firepower fabric:EthEstcPc:operLacpPolicyName
        managed object property"
    ::= { cfprApFabricEthEstcPcEntry 16 }

cfprApFabricEthEstcPcOperNwCtrlPolicyName OBJECT-TYPE
    SYNTAX       SnmpAdminString
    MAX-ACCESS   read-only
    STATUS       current
    DESCRIPTION
        "Cisco Firepower fabric:EthEstcPc:operNwCtrlPolicyName
        managed object property"
    ::= { cfprApFabricEthEstcPcEntry 17 }

cfprApFabricEthEstcPcOperSpeed OBJECT-TYPE
    SYNTAX       CfprApPortEthSpeed
    MAX-ACCESS   read-only
    STATUS       current
    DESCRIPTION
        "Cisco Firepower fabric:EthEstcPc:operSpeed managed
        object property"
    ::= { cfprApFabricEthEstcPcEntry 18 }

cfprApFabricEthEstcPcOperState OBJECT-TYPE
    SYNTAX       CfprApNetworkPortOperState
    MAX-ACCESS   read-only
    STATUS       current
    DESCRIPTION
        "Cisco Firepower fabric:EthEstcPc:operState managed
        object property"
    ::= { cfprApFabricEthEstcPcEntry 19 }

cfprApFabricEthEstcPcPeerDn OBJECT-TYPE
    SYNTAX       SnmpAdminString
    MAX-ACCESS   read-only
    STATUS       current
    DESCRIPTION
        "Cisco Firepower fabric:EthEstcPc:peerDn managed object property"
    ::= { cfprApFabricEthEstcPcEntry 20 }

cfprApFabricEthEstcPcPinGroupName OBJECT-TYPE
    SYNTAX       SnmpAdminString
    MAX-ACCESS   read-only
    STATUS       current
    DESCRIPTION
        "Cisco Firepower fabric:EthEstcPc:pinGroupName
        managed object property"
    ::= { cfprApFabricEthEstcPcEntry 21 }

cfprApFabricEthEstcPcPortId OBJECT-TYPE
    SYNTAX       Gauge32
    MAX-ACCESS   read-only
    STATUS       current
    DESCRIPTION
        "Cisco Firepower fabric:EthEstcPc:portId managed object property"
    ::= { cfprApFabricEthEstcPcEntry 22 }

cfprApFabricEthEstcPcPortMode OBJECT-TYPE
    SYNTAX       CfprApFabricEthEstcPortMode
    MAX-ACCESS   read-only
    STATUS       current
    DESCRIPTION
        "Cisco Firepower fabric:EthEstcPc:portMode managed
        object property"
    ::= { cfprApFabricEthEstcPcEntry 23 }

cfprApFabricEthEstcPcPrio OBJECT-TYPE
    SYNTAX       CfprApQosPriority
    MAX-ACCESS   read-only
    STATUS       current
    DESCRIPTION
        "Cisco Firepower fabric:EthEstcPc:prio managed object property"
    ::= { cfprApFabricEthEstcPcEntry 24 }

cfprApFabricEthEstcPcProtocol OBJECT-TYPE
    SYNTAX       CfprApFabricEthPcProtocol
    MAX-ACCESS   read-only
    STATUS       current
    DESCRIPTION
        "Cisco Firepower fabric:EthEstcPc:protocol managed
        object property"
    ::= { cfprApFabricEthEstcPcEntry 25 }

cfprApFabricEthEstcPcStateQual OBJECT-TYPE
    SYNTAX       SnmpAdminString
    MAX-ACCESS   read-only
    STATUS       current
    DESCRIPTION
        "Cisco Firepower fabric:EthEstcPc:stateQual managed
        object property"
    ::= { cfprApFabricEthEstcPcEntry 26 }

cfprApFabricEthEstcPcSwitchId OBJECT-TYPE
    SYNTAX       CfprApNetworkSwitchId
    MAX-ACCESS   read-only
    STATUS       current
    DESCRIPTION
        "Cisco Firepower fabric:EthEstcPc:switchId managed
        object property"
    ::= { cfprApFabricEthEstcPcEntry 27 }

cfprApFabricEthEstcPcTransport OBJECT-TYPE
    SYNTAX       CfprApFabricEthEstcPcTransport
    MAX-ACCESS   read-only
    STATUS       current
    DESCRIPTION
        "Cisco Firepower fabric:EthEstcPc:transport managed
        object property"
    ::= { cfprApFabricEthEstcPcEntry 28 }

cfprApFabricEthEstcPcType OBJECT-TYPE
    SYNTAX       CfprApFabricEstcPcType
    MAX-ACCESS   read-only
    STATUS       current
    DESCRIPTION
        "Cisco Firepower fabric:EthEstcPc:type managed object property"
    ::= { cfprApFabricEthEstcPcEntry 29 }

cfprApFabricEthEstcPcWarnings OBJECT-TYPE
    SYNTAX       CfprApFabricWarnings
    MAX-ACCESS   read-only
    STATUS       current
    DESCRIPTION
        "Cisco Firepower fabric:EthEstcPc:warnings managed
        object property"
    ::= { cfprApFabricEthEstcPcEntry 30 }

cfprApFabricEthEstcPcEpTable OBJECT-TYPE
    SYNTAX           SEQUENCE OF CfprApFabricEthEstcPcEpEntry
    MAX-ACCESS       not-accessible
    STATUS           current
    DESCRIPTION
        "Cisco Firepower fabric:EthEstcPcEp managed object table"
    ::= { cfprApFabricObjects 24 }

cfprApFabricEthEstcPcEpEntry OBJECT-TYPE
    SYNTAX           CfprApFabricEthEstcPcEpEntry
    MAX-ACCESS       not-accessible
    STATUS           current
    DESCRIPTION
        "Entry for the cfprApFabricEthEstcPcEpTable table."
    INDEX { cfprApFabricEthEstcPcEpInstanceId }
    ::= { cfprApFabricEthEstcPcEpTable 1 }

CfprApFabricEthEstcPcEpEntry ::= SEQUENCE {
    cfprApFabricEthEstcPcEpInstanceId                                CfprApManagedObjectId,
    cfprApFabricEthEstcPcEpDnData                                    CfprApManagedObjectDn,
    cfprApFabricEthEstcPcEpRn                                        SnmpAdminString,
    cfprApFabricEthEstcPcEpAdminSpeed                                CfprApPortSpeed,
    cfprApFabricEthEstcPcEpAdminState                                CfprApFabricExternalEpAdminState,
    cfprApFabricEthEstcPcEpAggrPortId                                Gauge32,
    cfprApFabricEthEstcPcEpChassisId                                 Gauge32,
    cfprApFabricEthEstcPcEpConfigState                               CfprApFabricConfigState,
    cfprApFabricEthEstcPcEpEpDn                                      SnmpAdminString,
    cfprApFabricEthEstcPcEpFltAggr                                   Unsigned64,
    cfprApFabricEthEstcPcEpIfRole                                    CfprApFabricAEthEstcEpIfRole,
    cfprApFabricEthEstcPcEpIfType                                    CfprApFabricPIoEpIfType,
    cfprApFabricEthEstcPcEpLicGP                                     Unsigned64,
    cfprApFabricEthEstcPcEpLicState                                  CfprApLicenseState,
    cfprApFabricEthEstcPcEpLocale                                    CfprApFabricExternalEpLocale,
    cfprApFabricEthEstcPcEpMembership                                CfprApFabricMembershipStatus,
    cfprApFabricEthEstcPcEpName                                      SnmpAdminString,
    cfprApFabricEthEstcPcEpOperState                                 CfprApFabricPIoEpOperState,
    cfprApFabricEthEstcPcEpOperStateReason                           SnmpAdminString,
    cfprApFabricEthEstcPcEpPeerAggrPortId                            Gauge32,
    cfprApFabricEthEstcPcEpPeerChassisId                             Gauge32,
    cfprApFabricEthEstcPcEpPeerDn                                    SnmpAdminString,
    cfprApFabricEthEstcPcEpPeerPortId                                Gauge32,
    cfprApFabricEthEstcPcEpPeerSlotId                                Gauge32,
    cfprApFabricEthEstcPcEpPortId                                    CfprApFabricEthEstcPcEpPortId,
    cfprApFabricEthEstcPcEpSlotId                                    CfprApFabricEthEstcPcEpSlotId,
    cfprApFabricEthEstcPcEpSwitchId                                  CfprApNetworkSwitchId,
    cfprApFabricEthEstcPcEpTransport                                 CfprApFabricAEthEstcEpTransport,
    cfprApFabricEthEstcPcEpType                                      CfprApFabricAEthEstcEpType,
    cfprApFabricEthEstcPcEpUsrLbl                                    SnmpAdminString,
    cfprApFabricEthEstcPcEpWarnings                                  CfprApFabricWarnings
}

cfprApFabricEthEstcPcEpInstanceId OBJECT-TYPE
    SYNTAX       CfprApManagedObjectId
    MAX-ACCESS   not-accessible
    STATUS       current
    DESCRIPTION
        "Instance identifier of the managed object."
    ::= { cfprApFabricEthEstcPcEpEntry 1 }

cfprApFabricEthEstcPcEpDnData OBJECT-TYPE
    SYNTAX       CfprApManagedObjectDn
    MAX-ACCESS   read-only
    STATUS       current
    DESCRIPTION
        "Cisco Firepower fabric:EthEstcPcEp:dn managed object property"
    ::= { cfprApFabricEthEstcPcEpEntry 2 }

cfprApFabricEthEstcPcEpRn OBJECT-TYPE
    SYNTAX       SnmpAdminString
    MAX-ACCESS   read-only
    STATUS       current
    DESCRIPTION
        "Cisco Firepower fabric:EthEstcPcEp:rn managed object property"
    ::= { cfprApFabricEthEstcPcEpEntry 3 }

cfprApFabricEthEstcPcEpAdminSpeed OBJECT-TYPE
    SYNTAX       CfprApPortSpeed
    MAX-ACCESS   read-only
    STATUS       current
    DESCRIPTION
        "Cisco Firepower fabric:EthEstcPcEp:adminSpeed
        managed object property"
    ::= { cfprApFabricEthEstcPcEpEntry 4 }

cfprApFabricEthEstcPcEpAdminState OBJECT-TYPE
    SYNTAX       CfprApFabricExternalEpAdminState
    MAX-ACCESS   read-only
    STATUS       current
    DESCRIPTION
        "Cisco Firepower fabric:EthEstcPcEp:adminState
        managed object property"
    ::= { cfprApFabricEthEstcPcEpEntry 5 }

cfprApFabricEthEstcPcEpAggrPortId OBJECT-TYPE
    SYNTAX       Gauge32
    MAX-ACCESS   read-only
    STATUS       current
    DESCRIPTION
        "Cisco Firepower fabric:EthEstcPcEp:aggrPortId
        managed object property"
    ::= { cfprApFabricEthEstcPcEpEntry 6 }

cfprApFabricEthEstcPcEpChassisId OBJECT-TYPE
    SYNTAX       Gauge32
    MAX-ACCESS   read-only
    STATUS       current
    DESCRIPTION
        "Cisco Firepower fabric:EthEstcPcEp:chassisId managed
        object property"
    ::= { cfprApFabricEthEstcPcEpEntry 7 }

cfprApFabricEthEstcPcEpConfigState OBJECT-TYPE
    SYNTAX       CfprApFabricConfigState
    MAX-ACCESS   read-only
    STATUS       current
    DESCRIPTION
        "Cisco Firepower fabric:EthEstcPcEp:configState
        managed object property"
    ::= { cfprApFabricEthEstcPcEpEntry 8 }

cfprApFabricEthEstcPcEpEpDn OBJECT-TYPE
    SYNTAX       SnmpAdminString
    MAX-ACCESS   read-only
    STATUS       current
    DESCRIPTION
        "Cisco Firepower fabric:EthEstcPcEp:epDn managed object property"
    ::= { cfprApFabricEthEstcPcEpEntry 9 }

cfprApFabricEthEstcPcEpFltAggr OBJECT-TYPE
    SYNTAX       Unsigned64
    MAX-ACCESS   read-only
    STATUS       current
    DESCRIPTION
        "Cisco Firepower fabric:EthEstcPcEp:fltAggr managed
        object property"
    ::= { cfprApFabricEthEstcPcEpEntry 10 }

cfprApFabricEthEstcPcEpIfRole OBJECT-TYPE
    SYNTAX       CfprApFabricAEthEstcEpIfRole
    MAX-ACCESS   read-only
    STATUS       current
    DESCRIPTION
        "Cisco Firepower fabric:EthEstcPcEp:ifRole managed
        object property"
    ::= { cfprApFabricEthEstcPcEpEntry 11 }

cfprApFabricEthEstcPcEpIfType OBJECT-TYPE
    SYNTAX       CfprApFabricPIoEpIfType
    MAX-ACCESS   read-only
    STATUS       current
    DESCRIPTION
        "Cisco Firepower fabric:EthEstcPcEp:ifType managed
        object property"
    ::= { cfprApFabricEthEstcPcEpEntry 12 }

cfprApFabricEthEstcPcEpLicGP OBJECT-TYPE
    SYNTAX       Unsigned64
    MAX-ACCESS   read-only
    STATUS       current
    DESCRIPTION
        "Cisco Firepower fabric:EthEstcPcEp:licGP managed object property"
    ::= { cfprApFabricEthEstcPcEpEntry 13 }

cfprApFabricEthEstcPcEpLicState OBJECT-TYPE
    SYNTAX       CfprApLicenseState
    MAX-ACCESS   read-only
    STATUS       current
    DESCRIPTION
        "Cisco Firepower fabric:EthEstcPcEp:licState managed
        object property"
    ::= { cfprApFabricEthEstcPcEpEntry 14 }

cfprApFabricEthEstcPcEpLocale OBJECT-TYPE
    SYNTAX       CfprApFabricExternalEpLocale
    MAX-ACCESS   read-only
    STATUS       current
    DESCRIPTION
        "Cisco Firepower fabric:EthEstcPcEp:locale managed
        object property"
    ::= { cfprApFabricEthEstcPcEpEntry 15 }

cfprApFabricEthEstcPcEpMembership OBJECT-TYPE
    SYNTAX       CfprApFabricMembershipStatus
    MAX-ACCESS   read-only
    STATUS       current
    DESCRIPTION
        "Cisco Firepower fabric:EthEstcPcEp:membership
        managed object property"
    ::= { cfprApFabricEthEstcPcEpEntry 16 }

cfprApFabricEthEstcPcEpName OBJECT-TYPE
    SYNTAX       SnmpAdminString
    MAX-ACCESS   read-only
    STATUS       current
    DESCRIPTION
        "Cisco Firepower fabric:EthEstcPcEp:name managed object property"
    ::= { cfprApFabricEthEstcPcEpEntry 17 }

cfprApFabricEthEstcPcEpOperState OBJECT-TYPE
    SYNTAX       CfprApFabricPIoEpOperState
    MAX-ACCESS   read-only
    STATUS       current
    DESCRIPTION
        "Cisco Firepower fabric:EthEstcPcEp:operState managed
        object property"
    ::= { cfprApFabricEthEstcPcEpEntry 18 }

cfprApFabricEthEstcPcEpOperStateReason OBJECT-TYPE
    SYNTAX       SnmpAdminString
    MAX-ACCESS   read-only
    STATUS       current
    DESCRIPTION
        "Cisco Firepower fabric:EthEstcPcEp:operStateReason
        managed object property"
    ::= { cfprApFabricEthEstcPcEpEntry 19 }

cfprApFabricEthEstcPcEpPeerAggrPortId OBJECT-TYPE
    SYNTAX       Gauge32
    MAX-ACCESS   read-only
    STATUS       current
    DESCRIPTION
        "Cisco Firepower fabric:EthEstcPcEp:peerAggrPortId
        managed object property"
    ::= { cfprApFabricEthEstcPcEpEntry 20 }

cfprApFabricEthEstcPcEpPeerChassisId OBJECT-TYPE
    SYNTAX       Gauge32
    MAX-ACCESS   read-only
    STATUS       current
    DESCRIPTION
        "Cisco Firepower fabric:EthEstcPcEp:peerChassisId
        managed object property"
    ::= { cfprApFabricEthEstcPcEpEntry 21 }

cfprApFabricEthEstcPcEpPeerDn OBJECT-TYPE
    SYNTAX       SnmpAdminString
    MAX-ACCESS   read-only
    STATUS       current
    DESCRIPTION
        "Cisco Firepower fabric:EthEstcPcEp:peerDn managed
        object property"
    ::= { cfprApFabricEthEstcPcEpEntry 22 }

cfprApFabricEthEstcPcEpPeerPortId OBJECT-TYPE
    SYNTAX       Gauge32
    MAX-ACCESS   read-only
    STATUS       current
    DESCRIPTION
        "Cisco Firepower fabric:EthEstcPcEp:peerPortId
        managed object property"
    ::= { cfprApFabricEthEstcPcEpEntry 23 }

cfprApFabricEthEstcPcEpPeerSlotId OBJECT-TYPE
    SYNTAX       Gauge32
    MAX-ACCESS   read-only
    STATUS       current
    DESCRIPTION
        "Cisco Firepower fabric:EthEstcPcEp:peerSlotId
        managed object property"
    ::= { cfprApFabricEthEstcPcEpEntry 24 }

cfprApFabricEthEstcPcEpPortId OBJECT-TYPE
    SYNTAX       CfprApFabricEthEstcPcEpPortId
    MAX-ACCESS   read-only
    STATUS       current
    DESCRIPTION
        "Cisco Firepower fabric:EthEstcPcEp:portId managed
        object property"
    ::= { cfprApFabricEthEstcPcEpEntry 25 }

cfprApFabricEthEstcPcEpSlotId OBJECT-TYPE
    SYNTAX       CfprApFabricEthEstcPcEpSlotId
    MAX-ACCESS   read-only
    STATUS       current
    DESCRIPTION
        "Cisco Firepower fabric:EthEstcPcEp:slotId managed
        object property"
    ::= { cfprApFabricEthEstcPcEpEntry 26 }

cfprApFabricEthEstcPcEpSwitchId OBJECT-TYPE
    SYNTAX       CfprApNetworkSwitchId
    MAX-ACCESS   read-only
    STATUS       current
    DESCRIPTION
        "Cisco Firepower fabric:EthEstcPcEp:switchId managed
        object property"
    ::= { cfprApFabricEthEstcPcEpEntry 27 }

cfprApFabricEthEstcPcEpTransport OBJECT-TYPE
    SYNTAX       CfprApFabricAEthEstcEpTransport
    MAX-ACCESS   read-only
    STATUS       current
    DESCRIPTION
        "Cisco Firepower fabric:EthEstcPcEp:transport managed
        object property"
    ::= { cfprApFabricEthEstcPcEpEntry 28 }

cfprApFabricEthEstcPcEpType OBJECT-TYPE
    SYNTAX       CfprApFabricAEthEstcEpType
    MAX-ACCESS   read-only
    STATUS       current
    DESCRIPTION
        "Cisco Firepower fabric:EthEstcPcEp:type managed object property"
    ::= { cfprApFabricEthEstcPcEpEntry 29 }

cfprApFabricEthEstcPcEpUsrLbl OBJECT-TYPE
    SYNTAX       SnmpAdminString
    MAX-ACCESS   read-only
    STATUS       current
    DESCRIPTION
        "Cisco Firepower fabric:EthEstcPcEp:usrLbl managed
        object property"
    ::= { cfprApFabricEthEstcPcEpEntry 30 }

cfprApFabricEthEstcPcEpWarnings OBJECT-TYPE
    SYNTAX       CfprApFabricWarnings
    MAX-ACCESS   read-only
    STATUS       current
    DESCRIPTION
        "Cisco Firepower fabric:EthEstcPcEp:warnings managed
        object property"
    ::= { cfprApFabricEthEstcPcEpEntry 31 }

cfprApFabricEthLanTable OBJECT-TYPE
    SYNTAX           SEQUENCE OF CfprApFabricEthLanEntry
    MAX-ACCESS       not-accessible
    STATUS           current
    DESCRIPTION
        "Cisco Firepower fabric:EthLan managed object table"
    ::= { cfprApFabricObjects 26 }

cfprApFabricEthLanEntry OBJECT-TYPE
    SYNTAX           CfprApFabricEthLanEntry
    MAX-ACCESS       not-accessible
    STATUS           current
    DESCRIPTION
        "Entry for the cfprApFabricEthLanTable table."
    INDEX { cfprApFabricEthLanInstanceId }
    ::= { cfprApFabricEthLanTable 1 }

CfprApFabricEthLanEntry ::= SEQUENCE {
    cfprApFabricEthLanInstanceId                                     CfprApManagedObjectId,
    cfprApFabricEthLanDn                                             CfprApManagedObjectDn,
    cfprApFabricEthLanRn                                             SnmpAdminString,
    cfprApFabricEthLanId                                             CfprApNetworkSwitchId,
    cfprApFabricEthLanLocale                                         CfprApFabricExternalLocale,
    cfprApFabricEthLanName                                           SnmpAdminString,
    cfprApFabricEthLanTransport                                      CfprApFabricEthLanTransport,
    cfprApFabricEthLanType                                           CfprApFabricLanType
}

cfprApFabricEthLanInstanceId OBJECT-TYPE
    SYNTAX       CfprApManagedObjectId
    MAX-ACCESS   not-accessible
    STATUS       current
    DESCRIPTION
        "Instance identifier of the managed object."
    ::= { cfprApFabricEthLanEntry 1 }

cfprApFabricEthLanDn OBJECT-TYPE
    SYNTAX       CfprApManagedObjectDn
    MAX-ACCESS   read-only
    STATUS       current
    DESCRIPTION
        "Cisco Firepower fabric:EthLan:dn managed object property"
    ::= { cfprApFabricEthLanEntry 2 }

cfprApFabricEthLanRn OBJECT-TYPE
    SYNTAX       SnmpAdminString
    MAX-ACCESS   read-only
    STATUS       current
    DESCRIPTION
        "Cisco Firepower fabric:EthLan:rn managed object property"
    ::= { cfprApFabricEthLanEntry 3 }

cfprApFabricEthLanId OBJECT-TYPE
    SYNTAX       CfprApNetworkSwitchId
    MAX-ACCESS   read-only
    STATUS       current
    DESCRIPTION
        "Cisco Firepower fabric:EthLan:id managed object property"
    ::= { cfprApFabricEthLanEntry 4 }

cfprApFabricEthLanLocale OBJECT-TYPE
    SYNTAX       CfprApFabricExternalLocale
    MAX-ACCESS   read-only
    STATUS       current
    DESCRIPTION
        "Cisco Firepower fabric:EthLan:locale managed object property"
    ::= { cfprApFabricEthLanEntry 5 }

cfprApFabricEthLanName OBJECT-TYPE
    SYNTAX       SnmpAdminString
    MAX-ACCESS   read-only
    STATUS       current
    DESCRIPTION
        "Cisco Firepower fabric:EthLan:name managed object property"
    ::= { cfprApFabricEthLanEntry 6 }

cfprApFabricEthLanTransport OBJECT-TYPE
    SYNTAX       CfprApFabricEthLanTransport
    MAX-ACCESS   read-only
    STATUS       current
    DESCRIPTION
        "Cisco Firepower fabric:EthLan:transport managed object property"
    ::= { cfprApFabricEthLanEntry 7 }

cfprApFabricEthLanType OBJECT-TYPE
    SYNTAX       CfprApFabricLanType
    MAX-ACCESS   read-only
    STATUS       current
    DESCRIPTION
        "Cisco Firepower fabric:EthLan:type managed object property"
    ::= { cfprApFabricEthLanEntry 8 }

cfprApFabricEthLanEpTable OBJECT-TYPE
    SYNTAX           SEQUENCE OF CfprApFabricEthLanEpEntry
    MAX-ACCESS       not-accessible
    STATUS           current
    DESCRIPTION
        "Cisco Firepower fabric:EthLanEp managed object table"
    ::= { cfprApFabricObjects 27 }

cfprApFabricEthLanEpEntry OBJECT-TYPE
    SYNTAX           CfprApFabricEthLanEpEntry
    MAX-ACCESS       not-accessible
    STATUS           current
    DESCRIPTION
        "Entry for the cfprApFabricEthLanEpTable table."
    INDEX { cfprApFabricEthLanEpInstanceId }
    ::= { cfprApFabricEthLanEpTable 1 }

CfprApFabricEthLanEpEntry ::= SEQUENCE {
    cfprApFabricEthLanEpInstanceId                                   CfprApManagedObjectId,
    cfprApFabricEthLanEpDn                                           CfprApManagedObjectDn,
    cfprApFabricEthLanEpRn                                           SnmpAdminString,
    cfprApFabricEthLanEpAdminDuplex                                  CfprApPortDuplex,
    cfprApFabricEthLanEpAdminSpeed                                   CfprApPortEthSpeed,
    cfprApFabricEthLanEpAdminState                                   CfprApFabricEthLanEpAdminState,
    cfprApFabricEthLanEpAggrPortId                                   Gauge32,
    cfprApFabricEthLanEpAutoNeg                                      TruthValue,
    cfprApFabricEthLanEpChassisId                                    Gauge32,
    cfprApFabricEthLanEpDtagVlan                                     Gauge32,
    cfprApFabricEthLanEpEpDn                                         SnmpAdminString,
    cfprApFabricEthLanEpEthLinkProfileName                           SnmpAdminString,
    cfprApFabricEthLanEpFlowCtrlPolicy                               SnmpAdminString,
    cfprApFabricEthLanEpFltAggr                                      Unsigned64,
    cfprApFabricEthLanEpHashAlg                                      CfprApNhTpHashType,
    cfprApFabricEthLanEpIfRole                                       CfprApFabricLanEpIfRole,
    cfprApFabricEthLanEpIfType                                       CfprApFabricPIoEpIfType,
    cfprApFabricEthLanEpLicGP                                        Unsigned64,
    cfprApFabricEthLanEpLicState                                     CfprApLicenseState,
    cfprApFabricEthLanEpLocale                                       CfprApFabricExternalEpLocale,
    cfprApFabricEthLanEpName                                         SnmpAdminString,
    cfprApFabricEthLanEpOperEthLinkProfileName                       SnmpAdminString,
    cfprApFabricEthLanEpOperState                                    CfprApFabricPIoEpOperState,
    cfprApFabricEthLanEpOperStateReason                              SnmpAdminString,
    cfprApFabricEthLanEpOverlappingVlans                             SnmpAdminString,
    cfprApFabricEthLanEpPeerAggrPortId                               Gauge32,
    cfprApFabricEthLanEpPeerChassisId                                Gauge32,
    cfprApFabricEthLanEpPeerDn                                       SnmpAdminString,
    cfprApFabricEthLanEpPeerPortId                                   Gauge32,
    cfprApFabricEthLanEpPeerSlotId                                   Gauge32,
    cfprApFabricEthLanEpPortId                                       Gauge32,
    cfprApFabricEthLanEpQosPrio                                      CfprApFabricQosPrio,
    cfprApFabricEthLanEpSlotId                                       Gauge32,
    cfprApFabricEthLanEpSpeedCap                                     CfprApFabricEthLanEpSpeedCap,
    cfprApFabricEthLanEpSsaPortType                                  CfprApFabricSSAPortType,
    cfprApFabricEthLanEpSsaVlanId                                    Gauge32,
    cfprApFabricEthLanEpSwitchId                                     CfprApNetworkSwitchId,
    cfprApFabricEthLanEpTransport                                    CfprApFabricAEthLanEpTransport,
    cfprApFabricEthLanEpType                                         CfprApFabricLanEpType,
    cfprApFabricEthLanEpUdldOperState                                CfprApFabricUdldOperState,
    cfprApFabricEthLanEpUsrLbl                                       SnmpAdminString,
    cfprApFabricEthLanEpVlanStatus                                   CfprApFabricEthLanEpVlanStatus,
    cfprApFabricEthLanEpWarnings                                     CfprApFabricWarnings
}

cfprApFabricEthLanEpInstanceId OBJECT-TYPE
    SYNTAX       CfprApManagedObjectId
    MAX-ACCESS   not-accessible
    STATUS       current
    DESCRIPTION
        "Instance identifier of the managed object."
    ::= { cfprApFabricEthLanEpEntry 1 }

cfprApFabricEthLanEpDn OBJECT-TYPE
    SYNTAX       CfprApManagedObjectDn
    MAX-ACCESS   read-only
    STATUS       current
    DESCRIPTION
        "Cisco Firepower fabric:EthLanEp:dn managed object property"
    ::= { cfprApFabricEthLanEpEntry 2 }

cfprApFabricEthLanEpRn OBJECT-TYPE
    SYNTAX       SnmpAdminString
    MAX-ACCESS   read-only
    STATUS       current
    DESCRIPTION
        "Cisco Firepower fabric:EthLanEp:rn managed object property"
    ::= { cfprApFabricEthLanEpEntry 3 }

cfprApFabricEthLanEpAdminDuplex OBJECT-TYPE
    SYNTAX       CfprApPortDuplex
    MAX-ACCESS   read-only
    STATUS       current
    DESCRIPTION
        "Cisco Firepower fabric:EthLanEp:adminDuplex managed
        object property"
    ::= { cfprApFabricEthLanEpEntry 4 }

cfprApFabricEthLanEpAdminSpeed OBJECT-TYPE
    SYNTAX       CfprApPortEthSpeed
    MAX-ACCESS   read-only
    STATUS       current
    DESCRIPTION
        "Cisco Firepower fabric:EthLanEp:adminSpeed managed
        object property"
    ::= { cfprApFabricEthLanEpEntry 5 }

cfprApFabricEthLanEpAdminState OBJECT-TYPE
    SYNTAX       CfprApFabricEthLanEpAdminState
    MAX-ACCESS   read-only
    STATUS       current
    DESCRIPTION
        "Cisco Firepower fabric:EthLanEp:adminState managed
        object property"
    ::= { cfprApFabricEthLanEpEntry 6 }

cfprApFabricEthLanEpAggrPortId OBJECT-TYPE
    SYNTAX       Gauge32
    MAX-ACCESS   read-only
    STATUS       current
    DESCRIPTION
        "Cisco Firepower fabric:EthLanEp:aggrPortId managed
        object property"
    ::= { cfprApFabricEthLanEpEntry 7 }

cfprApFabricEthLanEpAutoNeg OBJECT-TYPE
    SYNTAX       TruthValue
    MAX-ACCESS   read-only
    STATUS       current
    DESCRIPTION
        "Cisco Firepower fabric:EthLanEp:autoNeg managed object property"
    ::= { cfprApFabricEthLanEpEntry 8 }

cfprApFabricEthLanEpChassisId OBJECT-TYPE
    SYNTAX       Gauge32
    MAX-ACCESS   read-only
    STATUS       current
    DESCRIPTION
        "Cisco Firepower fabric:EthLanEp:chassisId managed
        object property"
    ::= { cfprApFabricEthLanEpEntry 9 }

cfprApFabricEthLanEpDtagVlan OBJECT-TYPE
    SYNTAX       Gauge32
    MAX-ACCESS   read-only
    STATUS       current
    DESCRIPTION
        "Cisco Firepower fabric:EthLanEp:dtagVlan managed object property"
    ::= { cfprApFabricEthLanEpEntry 10 }

cfprApFabricEthLanEpEpDn OBJECT-TYPE
    SYNTAX       SnmpAdminString
    MAX-ACCESS   read-only
    STATUS       current
    DESCRIPTION
        "Cisco Firepower fabric:EthLanEp:epDn managed object property"
    ::= { cfprApFabricEthLanEpEntry 11 }

cfprApFabricEthLanEpEthLinkProfileName OBJECT-TYPE
    SYNTAX       SnmpAdminString
    MAX-ACCESS   read-only
    STATUS       current
    DESCRIPTION
        "Cisco Firepower fabric:EthLanEp:ethLinkProfileName
        managed object property"
    ::= { cfprApFabricEthLanEpEntry 12 }

cfprApFabricEthLanEpFlowCtrlPolicy OBJECT-TYPE
    SYNTAX       SnmpAdminString
    MAX-ACCESS   read-only
    STATUS       current
    DESCRIPTION
        "Cisco Firepower fabric:EthLanEp:flowCtrlPolicy
        managed object property"
    ::= { cfprApFabricEthLanEpEntry 13 }

cfprApFabricEthLanEpFltAggr OBJECT-TYPE
    SYNTAX       Unsigned64
    MAX-ACCESS   read-only
    STATUS       current
    DESCRIPTION
        "Cisco Firepower fabric:EthLanEp:fltAggr managed object property"
    ::= { cfprApFabricEthLanEpEntry 14 }

cfprApFabricEthLanEpHashAlg OBJECT-TYPE
    SYNTAX       CfprApNhTpHashType
    MAX-ACCESS   read-only
    STATUS       current
    DESCRIPTION
        "Cisco Firepower fabric:EthLanEp:hashAlg managed object property"
    ::= { cfprApFabricEthLanEpEntry 15 }

cfprApFabricEthLanEpIfRole OBJECT-TYPE
    SYNTAX       CfprApFabricLanEpIfRole
    MAX-ACCESS   read-only
    STATUS       current
    DESCRIPTION
        "Cisco Firepower fabric:EthLanEp:ifRole managed object property"
    ::= { cfprApFabricEthLanEpEntry 16 }

cfprApFabricEthLanEpIfType OBJECT-TYPE
    SYNTAX       CfprApFabricPIoEpIfType
    MAX-ACCESS   read-only
    STATUS       current
    DESCRIPTION
        "Cisco Firepower fabric:EthLanEp:ifType managed object property"
    ::= { cfprApFabricEthLanEpEntry 17 }

cfprApFabricEthLanEpLicGP OBJECT-TYPE
    SYNTAX       Unsigned64
    MAX-ACCESS   read-only
    STATUS       current
    DESCRIPTION
        "Cisco Firepower fabric:EthLanEp:licGP managed object property"
    ::= { cfprApFabricEthLanEpEntry 18 }

cfprApFabricEthLanEpLicState OBJECT-TYPE
    SYNTAX       CfprApLicenseState
    MAX-ACCESS   read-only
    STATUS       current
    DESCRIPTION
        "Cisco Firepower fabric:EthLanEp:licState managed object property"
    ::= { cfprApFabricEthLanEpEntry 19 }

cfprApFabricEthLanEpLocale OBJECT-TYPE
    SYNTAX       CfprApFabricExternalEpLocale
    MAX-ACCESS   read-only
    STATUS       current
    DESCRIPTION
        "Cisco Firepower fabric:EthLanEp:locale managed object property"
    ::= { cfprApFabricEthLanEpEntry 20 }

cfprApFabricEthLanEpName OBJECT-TYPE
    SYNTAX       SnmpAdminString
    MAX-ACCESS   read-only
    STATUS       current
    DESCRIPTION
        "Cisco Firepower fabric:EthLanEp:name managed object property"
    ::= { cfprApFabricEthLanEpEntry 21 }

cfprApFabricEthLanEpOperEthLinkProfileName OBJECT-TYPE
    SYNTAX       SnmpAdminString
    MAX-ACCESS   read-only
    STATUS       current
    DESCRIPTION
        "Cisco Firepower fabric:EthLanEp:operEthLinkProfileName
        managed object property"
    ::= { cfprApFabricEthLanEpEntry 22 }

cfprApFabricEthLanEpOperState OBJECT-TYPE
    SYNTAX       CfprApFabricPIoEpOperState
    MAX-ACCESS   read-only
    STATUS       current
    DESCRIPTION
        "Cisco Firepower fabric:EthLanEp:operState managed
        object property"
    ::= { cfprApFabricEthLanEpEntry 23 }

cfprApFabricEthLanEpOperStateReason OBJECT-TYPE
    SYNTAX       SnmpAdminString
    MAX-ACCESS   read-only
    STATUS       current
    DESCRIPTION
        "Cisco Firepower fabric:EthLanEp:operStateReason
        managed object property"
    ::= { cfprApFabricEthLanEpEntry 24 }

cfprApFabricEthLanEpOverlappingVlans OBJECT-TYPE
    SYNTAX       SnmpAdminString
    MAX-ACCESS   read-only
    STATUS       current
    DESCRIPTION
        "Cisco Firepower fabric:EthLanEp:overlappingVlans
        managed object property"
    ::= { cfprApFabricEthLanEpEntry 25 }

cfprApFabricEthLanEpPeerAggrPortId OBJECT-TYPE
    SYNTAX       Gauge32
    MAX-ACCESS   read-only
    STATUS       current
    DESCRIPTION
        "Cisco Firepower fabric:EthLanEp:peerAggrPortId
        managed object property"
    ::= { cfprApFabricEthLanEpEntry 26 }

cfprApFabricEthLanEpPeerChassisId OBJECT-TYPE
    SYNTAX       Gauge32
    MAX-ACCESS   read-only
    STATUS       current
    DESCRIPTION
        "Cisco Firepower fabric:EthLanEp:peerChassisId
        managed object property"
    ::= { cfprApFabricEthLanEpEntry 27 }

cfprApFabricEthLanEpPeerDn OBJECT-TYPE
    SYNTAX       SnmpAdminString
    MAX-ACCESS   read-only
    STATUS       current
    DESCRIPTION
        "Cisco Firepower fabric:EthLanEp:peerDn managed object property"
    ::= { cfprApFabricEthLanEpEntry 28 }

cfprApFabricEthLanEpPeerPortId OBJECT-TYPE
    SYNTAX       Gauge32
    MAX-ACCESS   read-only
    STATUS       current
    DESCRIPTION
        "Cisco Firepower fabric:EthLanEp:peerPortId managed
        object property"
    ::= { cfprApFabricEthLanEpEntry 29 }

cfprApFabricEthLanEpPeerSlotId OBJECT-TYPE
    SYNTAX       Gauge32
    MAX-ACCESS   read-only
    STATUS       current
    DESCRIPTION
        "Cisco Firepower fabric:EthLanEp:peerSlotId managed
        object property"
    ::= { cfprApFabricEthLanEpEntry 30 }

cfprApFabricEthLanEpPortId OBJECT-TYPE
    SYNTAX       Gauge32
    MAX-ACCESS   read-only
    STATUS       current
    DESCRIPTION
        "Cisco Firepower fabric:EthLanEp:portId managed object property"
    ::= { cfprApFabricEthLanEpEntry 31 }

cfprApFabricEthLanEpQosPrio OBJECT-TYPE
    SYNTAX       CfprApFabricQosPrio
    MAX-ACCESS   read-only
    STATUS       current
    DESCRIPTION
        "Cisco Firepower fabric:EthLanEp:qosPrio managed object property"
    ::= { cfprApFabricEthLanEpEntry 32 }

cfprApFabricEthLanEpSlotId OBJECT-TYPE
    SYNTAX       Gauge32
    MAX-ACCESS   read-only
    STATUS       current
    DESCRIPTION
        "Cisco Firepower fabric:EthLanEp:slotId managed object property"
    ::= { cfprApFabricEthLanEpEntry 33 }

cfprApFabricEthLanEpSpeedCap OBJECT-TYPE
    SYNTAX       CfprApFabricEthLanEpSpeedCap
    MAX-ACCESS   read-only
    STATUS       current
    DESCRIPTION
        "Cisco Firepower fabric:EthLanEp:speedCap managed object property"
    ::= { cfprApFabricEthLanEpEntry 34 }

cfprApFabricEthLanEpSsaPortType OBJECT-TYPE
    SYNTAX       CfprApFabricSSAPortType
    MAX-ACCESS   read-only
    STATUS       current
    DESCRIPTION
        "Cisco Firepower fabric:EthLanEp:ssaPortType managed
        object property"
    ::= { cfprApFabricEthLanEpEntry 35 }

cfprApFabricEthLanEpSsaVlanId OBJECT-TYPE
    SYNTAX       Gauge32
    MAX-ACCESS   read-only
    STATUS       current
    DESCRIPTION
        "Cisco Firepower fabric:EthLanEp:ssaVlanId managed
        object property"
    ::= { cfprApFabricEthLanEpEntry 36 }

cfprApFabricEthLanEpSwitchId OBJECT-TYPE
    SYNTAX       CfprApNetworkSwitchId
    MAX-ACCESS   read-only
    STATUS       current
    DESCRIPTION
        "Cisco Firepower fabric:EthLanEp:switchId managed object property"
    ::= { cfprApFabricEthLanEpEntry 37 }

cfprApFabricEthLanEpTransport OBJECT-TYPE
    SYNTAX       CfprApFabricAEthLanEpTransport
    MAX-ACCESS   read-only
    STATUS       current
    DESCRIPTION
        "Cisco Firepower fabric:EthLanEp:transport managed
        object property"
    ::= { cfprApFabricEthLanEpEntry 38 }

cfprApFabricEthLanEpType OBJECT-TYPE
    SYNTAX       CfprApFabricLanEpType
    MAX-ACCESS   read-only
    STATUS       current
    DESCRIPTION
        "Cisco Firepower fabric:EthLanEp:type managed object property"
    ::= { cfprApFabricEthLanEpEntry 39 }

cfprApFabricEthLanEpUdldOperState OBJECT-TYPE
    SYNTAX       CfprApFabricUdldOperState
    MAX-ACCESS   read-only
    STATUS       current
    DESCRIPTION
        "Cisco Firepower fabric:EthLanEp:udldOperState
        managed object property"
    ::= { cfprApFabricEthLanEpEntry 40 }

cfprApFabricEthLanEpUsrLbl OBJECT-TYPE
    SYNTAX       SnmpAdminString
    MAX-ACCESS   read-only
    STATUS       current
    DESCRIPTION
        "Cisco Firepower fabric:EthLanEp:usrLbl managed object property"
    ::= { cfprApFabricEthLanEpEntry 41 }

cfprApFabricEthLanEpVlanStatus OBJECT-TYPE
    SYNTAX       CfprApFabricEthLanEpVlanStatus
    MAX-ACCESS   read-only
    STATUS       current
    DESCRIPTION
        "Cisco Firepower fabric:EthLanEp:vlanStatus managed
        object property"
    ::= { cfprApFabricEthLanEpEntry 42 }

cfprApFabricEthLanEpWarnings OBJECT-TYPE
    SYNTAX       CfprApFabricWarnings
    MAX-ACCESS   read-only
    STATUS       current
    DESCRIPTION
        "Cisco Firepower fabric:EthLanEp:warnings managed object property"
    ::= { cfprApFabricEthLanEpEntry 43 }

cfprApFabricEthLanPcTable OBJECT-TYPE
    SYNTAX           SEQUENCE OF CfprApFabricEthLanPcEntry
    MAX-ACCESS       not-accessible
    STATUS           current
    DESCRIPTION
        "Cisco Firepower fabric:EthLanPc managed object table"
    ::= { cfprApFabricObjects 29 }

cfprApFabricEthLanPcEntry OBJECT-TYPE
    SYNTAX           CfprApFabricEthLanPcEntry
    MAX-ACCESS       not-accessible
    STATUS           current
    DESCRIPTION
        "Entry for the cfprApFabricEthLanPcTable table."
    INDEX { cfprApFabricEthLanPcInstanceId }
    ::= { cfprApFabricEthLanPcTable 1 }

CfprApFabricEthLanPcEntry ::= SEQUENCE {
    cfprApFabricEthLanPcInstanceId                                   CfprApManagedObjectId,
    cfprApFabricEthLanPcDn                                           CfprApManagedObjectDn,
    cfprApFabricEthLanPcRn                                           SnmpAdminString,
    cfprApFabricEthLanPcAdminDuplex                                  CfprApPortDuplex,
    cfprApFabricEthLanPcAdminSpeed                                   CfprApPortEthSpeed,
    cfprApFabricEthLanPcAdminState                                   CfprApFabricEthLanPcAdminState,
    cfprApFabricEthLanPcAutoNeg                                      TruthValue,
    cfprApFabricEthLanPcBandwidth                                    Gauge32,
    cfprApFabricEthLanPcCluChassisId                                 Gauge32,
    cfprApFabricEthLanPcClusterName                                  SnmpAdminString,
    cfprApFabricEthLanPcDescr                                        SnmpAdminString,
    cfprApFabricEthLanPcDtagVlan                                     Gauge32,
    cfprApFabricEthLanPcEpDn                                         SnmpAdminString,
    cfprApFabricEthLanPcFlowCtrlPolicy                               SnmpAdminString,
    cfprApFabricEthLanPcFltAggr                                      Unsigned64,
    cfprApFabricEthLanPcHashAlg                                      CfprApNhTpHashType,
    cfprApFabricEthLanPcIfRole                                       CfprApFabricLanPcIfRole,
    cfprApFabricEthLanPcIfType                                       CfprApFabricCIoEpIfType,
    cfprApFabricEthLanPcLacpDetach                                   CfprApFabricEthLanPcLacpDetach,
    cfprApFabricEthLanPcLacpMode                                     CfprApFabricLacpMode,
    cfprApFabricEthLanPcLacpPolicyName                               SnmpAdminString,
    cfprApFabricEthLanPcLocale                                       CfprApFabricExternalPcLocale,
    cfprApFabricEthLanPcName                                         SnmpAdminString,
    cfprApFabricEthLanPcOperLacpPolicyName                           SnmpAdminString,
    cfprApFabricEthLanPcOperSpeed                                    CfprApPortEthSpeed,
    cfprApFabricEthLanPcOperState                                    CfprApNetworkPortOperState,
    cfprApFabricEthLanPcOverlappingVlans                             SnmpAdminString,
    cfprApFabricEthLanPcPeerDn                                       SnmpAdminString,
    cfprApFabricEthLanPcPortId                                       Gauge32,
    cfprApFabricEthLanPcQosPrio                                      CfprApFabricQosPrio,
    cfprApFabricEthLanPcSpannedCluster                               CfprApFabricSpannedCluster,
    cfprApFabricEthLanPcSpeedCap                                     CfprApFabricEthLanPcSpeedCap,
    cfprApFabricEthLanPcSsaPortType                                  CfprApFabricSSAPortType,
    cfprApFabricEthLanPcSsaVlanId                                    Gauge32,
    cfprApFabricEthLanPcStateQual                                    SnmpAdminString,
    cfprApFabricEthLanPcSwitchId                                     CfprApNetworkSwitchId,
    cfprApFabricEthLanPcTransport                                    CfprApFabricEthLanPcTransport,
    cfprApFabricEthLanPcType                                         CfprApFabricLanPcType,
    cfprApFabricEthLanPcVlanStatus                                   CfprApFabricEthLanPcVlanStatus,
    cfprApFabricEthLanPcWarnings                                     CfprApFabricWarnings
}

cfprApFabricEthLanPcInstanceId OBJECT-TYPE
    SYNTAX       CfprApManagedObjectId
    MAX-ACCESS   not-accessible
    STATUS       current
    DESCRIPTION
        "Instance identifier of the managed object."
    ::= { cfprApFabricEthLanPcEntry 1 }

cfprApFabricEthLanPcDn OBJECT-TYPE
    SYNTAX       CfprApManagedObjectDn
    MAX-ACCESS   read-only
    STATUS       current
    DESCRIPTION
        "Cisco Firepower fabric:EthLanPc:dn managed object property"
    ::= { cfprApFabricEthLanPcEntry 2 }

cfprApFabricEthLanPcRn OBJECT-TYPE
    SYNTAX       SnmpAdminString
    MAX-ACCESS   read-only
    STATUS       current
    DESCRIPTION
        "Cisco Firepower fabric:EthLanPc:rn managed object property"
    ::= { cfprApFabricEthLanPcEntry 3 }

cfprApFabricEthLanPcAdminDuplex OBJECT-TYPE
    SYNTAX       CfprApPortDuplex
    MAX-ACCESS   read-only
    STATUS       current
    DESCRIPTION
        "Cisco Firepower fabric:EthLanPc:adminDuplex managed
        object property"
    ::= { cfprApFabricEthLanPcEntry 4 }

cfprApFabricEthLanPcAdminSpeed OBJECT-TYPE
    SYNTAX       CfprApPortEthSpeed
    MAX-ACCESS   read-only
    STATUS       current
    DESCRIPTION
        "Cisco Firepower fabric:EthLanPc:adminSpeed managed
        object property"
    ::= { cfprApFabricEthLanPcEntry 5 }

cfprApFabricEthLanPcAdminState OBJECT-TYPE
    SYNTAX       CfprApFabricEthLanPcAdminState
    MAX-ACCESS   read-only
    STATUS       current
    DESCRIPTION
        "Cisco Firepower fabric:EthLanPc:adminState managed
        object property"
    ::= { cfprApFabricEthLanPcEntry 6 }

cfprApFabricEthLanPcAutoNeg OBJECT-TYPE
    SYNTAX       TruthValue
    MAX-ACCESS   read-only
    STATUS       current
    DESCRIPTION
        "Cisco Firepower fabric:EthLanPc:autoNeg managed object property"
    ::= { cfprApFabricEthLanPcEntry 7 }

cfprApFabricEthLanPcBandwidth OBJECT-TYPE
    SYNTAX       Gauge32
    MAX-ACCESS   read-only
    STATUS       current
    DESCRIPTION
        "Cisco Firepower fabric:EthLanPc:bandwidth managed
        object property"
    ::= { cfprApFabricEthLanPcEntry 8 }

cfprApFabricEthLanPcCluChassisId OBJECT-TYPE
    SYNTAX       Gauge32
    MAX-ACCESS   read-only
    STATUS       current
    DESCRIPTION
        "Cisco Firepower fabric:EthLanPc:cluChassisId managed
        object property"
    ::= { cfprApFabricEthLanPcEntry 9 }

cfprApFabricEthLanPcClusterName OBJECT-TYPE
    SYNTAX       SnmpAdminString
    MAX-ACCESS   read-only
    STATUS       current
    DESCRIPTION
        "Cisco Firepower fabric:EthLanPc:clusterName managed
        object property"
    ::= { cfprApFabricEthLanPcEntry 10 }

cfprApFabricEthLanPcDescr OBJECT-TYPE
    SYNTAX       SnmpAdminString
    MAX-ACCESS   read-only
    STATUS       current
    DESCRIPTION
        "Cisco Firepower fabric:EthLanPc:descr managed object property"
    ::= { cfprApFabricEthLanPcEntry 11 }

cfprApFabricEthLanPcDtagVlan OBJECT-TYPE
    SYNTAX       Gauge32
    MAX-ACCESS   read-only
    STATUS       current
    DESCRIPTION
        "Cisco Firepower fabric:EthLanPc:dtagVlan managed object property"
    ::= { cfprApFabricEthLanPcEntry 12 }

cfprApFabricEthLanPcEpDn OBJECT-TYPE
    SYNTAX       SnmpAdminString
    MAX-ACCESS   read-only
    STATUS       current
    DESCRIPTION
        "Cisco Firepower fabric:EthLanPc:epDn managed object property"
    ::= { cfprApFabricEthLanPcEntry 13 }

cfprApFabricEthLanPcFlowCtrlPolicy OBJECT-TYPE
    SYNTAX       SnmpAdminString
    MAX-ACCESS   read-only
    STATUS       current
    DESCRIPTION
        "Cisco Firepower fabric:EthLanPc:flowCtrlPolicy
        managed object property"
    ::= { cfprApFabricEthLanPcEntry 14 }

cfprApFabricEthLanPcFltAggr OBJECT-TYPE
    SYNTAX       Unsigned64
    MAX-ACCESS   read-only
    STATUS       current
    DESCRIPTION
        "Cisco Firepower fabric:EthLanPc:fltAggr managed object property"
    ::= { cfprApFabricEthLanPcEntry 15 }

cfprApFabricEthLanPcHashAlg OBJECT-TYPE
    SYNTAX       CfprApNhTpHashType
    MAX-ACCESS   read-only
    STATUS       current
    DESCRIPTION
        "Cisco Firepower fabric:EthLanPc:hashAlg managed object property"
    ::= { cfprApFabricEthLanPcEntry 16 }

cfprApFabricEthLanPcIfRole OBJECT-TYPE
    SYNTAX       CfprApFabricLanPcIfRole
    MAX-ACCESS   read-only
    STATUS       current
    DESCRIPTION
        "Cisco Firepower fabric:EthLanPc:ifRole managed object property"
    ::= { cfprApFabricEthLanPcEntry 17 }

cfprApFabricEthLanPcIfType OBJECT-TYPE
    SYNTAX       CfprApFabricCIoEpIfType
    MAX-ACCESS   read-only
    STATUS       current
    DESCRIPTION
        "Cisco Firepower fabric:EthLanPc:ifType managed object property"
    ::= { cfprApFabricEthLanPcEntry 18 }

cfprApFabricEthLanPcLacpDetach OBJECT-TYPE
    SYNTAX       CfprApFabricEthLanPcLacpDetach
    MAX-ACCESS   read-only
    STATUS       current
    DESCRIPTION
        "Cisco Firepower fabric:EthLanPc:lacpDetach managed
        object property"
    ::= { cfprApFabricEthLanPcEntry 19 }

cfprApFabricEthLanPcLacpMode OBJECT-TYPE
    SYNTAX       CfprApFabricLacpMode
    MAX-ACCESS   read-only
    STATUS       current
    DESCRIPTION
        "Cisco Firepower fabric:EthLanPc:lacpMode managed object property"
    ::= { cfprApFabricEthLanPcEntry 20 }

cfprApFabricEthLanPcLacpPolicyName OBJECT-TYPE
    SYNTAX       SnmpAdminString
    MAX-ACCESS   read-only
    STATUS       current
    DESCRIPTION
        "Cisco Firepower fabric:EthLanPc:lacpPolicyName
        managed object property"
    ::= { cfprApFabricEthLanPcEntry 21 }

cfprApFabricEthLanPcLocale OBJECT-TYPE
    SYNTAX       CfprApFabricExternalPcLocale
    MAX-ACCESS   read-only
    STATUS       current
    DESCRIPTION
        "Cisco Firepower fabric:EthLanPc:locale managed object property"
    ::= { cfprApFabricEthLanPcEntry 22 }

cfprApFabricEthLanPcName OBJECT-TYPE
    SYNTAX       SnmpAdminString
    MAX-ACCESS   read-only
    STATUS       current
    DESCRIPTION
        "Cisco Firepower fabric:EthLanPc:name managed object property"
    ::= { cfprApFabricEthLanPcEntry 23 }

cfprApFabricEthLanPcOperLacpPolicyName OBJECT-TYPE
    SYNTAX       SnmpAdminString
    MAX-ACCESS   read-only
    STATUS       current
    DESCRIPTION
        "Cisco Firepower fabric:EthLanPc:operLacpPolicyName
        managed object property"
    ::= { cfprApFabricEthLanPcEntry 24 }

cfprApFabricEthLanPcOperSpeed OBJECT-TYPE
    SYNTAX       CfprApPortEthSpeed
    MAX-ACCESS   read-only
    STATUS       current
    DESCRIPTION
        "Cisco Firepower fabric:EthLanPc:operSpeed managed
        object property"
    ::= { cfprApFabricEthLanPcEntry 25 }

cfprApFabricEthLanPcOperState OBJECT-TYPE
    SYNTAX       CfprApNetworkPortOperState
    MAX-ACCESS   read-only
    STATUS       current
    DESCRIPTION
        "Cisco Firepower fabric:EthLanPc:operState managed
        object property"
    ::= { cfprApFabricEthLanPcEntry 26 }

cfprApFabricEthLanPcOverlappingVlans OBJECT-TYPE
    SYNTAX       SnmpAdminString
    MAX-ACCESS   read-only
    STATUS       current
    DESCRIPTION
        "Cisco Firepower fabric:EthLanPc:overlappingVlans
        managed object property"
    ::= { cfprApFabricEthLanPcEntry 27 }

cfprApFabricEthLanPcPeerDn OBJECT-TYPE
    SYNTAX       SnmpAdminString
    MAX-ACCESS   read-only
    STATUS       current
    DESCRIPTION
        "Cisco Firepower fabric:EthLanPc:peerDn managed object property"
    ::= { cfprApFabricEthLanPcEntry 28 }

cfprApFabricEthLanPcPortId OBJECT-TYPE
    SYNTAX       Gauge32
    MAX-ACCESS   read-only
    STATUS       current
    DESCRIPTION
        "Cisco Firepower fabric:EthLanPc:portId managed object property"
    ::= { cfprApFabricEthLanPcEntry 29 }

cfprApFabricEthLanPcQosPrio OBJECT-TYPE
    SYNTAX       CfprApFabricQosPrio
    MAX-ACCESS   read-only
    STATUS       current
    DESCRIPTION
        "Cisco Firepower fabric:EthLanPc:qosPrio managed object property"
    ::= { cfprApFabricEthLanPcEntry 30 }

cfprApFabricEthLanPcSpannedCluster OBJECT-TYPE
    SYNTAX       CfprApFabricSpannedCluster
    MAX-ACCESS   read-only
    STATUS       current
    DESCRIPTION
        "Cisco Firepower fabric:EthLanPc:spannedCluster
        managed object property"
    ::= { cfprApFabricEthLanPcEntry 31 }

cfprApFabricEthLanPcSpeedCap OBJECT-TYPE
    SYNTAX       CfprApFabricEthLanPcSpeedCap
    MAX-ACCESS   read-only
    STATUS       current
    DESCRIPTION
        "Cisco Firepower fabric:EthLanPc:speedCap managed object property"
    ::= { cfprApFabricEthLanPcEntry 32 }

cfprApFabricEthLanPcSsaPortType OBJECT-TYPE
    SYNTAX       CfprApFabricSSAPortType
    MAX-ACCESS   read-only
    STATUS       current
    DESCRIPTION
        "Cisco Firepower fabric:EthLanPc:ssaPortType managed
        object property"
    ::= { cfprApFabricEthLanPcEntry 33 }

cfprApFabricEthLanPcSsaVlanId OBJECT-TYPE
    SYNTAX       Gauge32
    MAX-ACCESS   read-only
    STATUS       current
    DESCRIPTION
        "Cisco Firepower fabric:EthLanPc:ssaVlanId managed
        object property"
    ::= { cfprApFabricEthLanPcEntry 34 }

cfprApFabricEthLanPcStateQual OBJECT-TYPE
    SYNTAX       SnmpAdminString
    MAX-ACCESS   read-only
    STATUS       current
    DESCRIPTION
        "Cisco Firepower fabric:EthLanPc:stateQual managed
        object property"
    ::= { cfprApFabricEthLanPcEntry 35 }

cfprApFabricEthLanPcSwitchId OBJECT-TYPE
    SYNTAX       CfprApNetworkSwitchId
    MAX-ACCESS   read-only
    STATUS       current
    DESCRIPTION
        "Cisco Firepower fabric:EthLanPc:switchId managed object property"
    ::= { cfprApFabricEthLanPcEntry 36 }

cfprApFabricEthLanPcTransport OBJECT-TYPE
    SYNTAX       CfprApFabricEthLanPcTransport
    MAX-ACCESS   read-only
    STATUS       current
    DESCRIPTION
        "Cisco Firepower fabric:EthLanPc:transport managed
        object property"
    ::= { cfprApFabricEthLanPcEntry 37 }

cfprApFabricEthLanPcType OBJECT-TYPE
    SYNTAX       CfprApFabricLanPcType
    MAX-ACCESS   read-only
    STATUS       current
    DESCRIPTION
        "Cisco Firepower fabric:EthLanPc:type managed object property"
    ::= { cfprApFabricEthLanPcEntry 38 }

cfprApFabricEthLanPcVlanStatus OBJECT-TYPE
    SYNTAX       CfprApFabricEthLanPcVlanStatus
    MAX-ACCESS   read-only
    STATUS       current
    DESCRIPTION
        "Cisco Firepower fabric:EthLanPc:vlanStatus managed
        object property"
    ::= { cfprApFabricEthLanPcEntry 39 }

cfprApFabricEthLanPcWarnings OBJECT-TYPE
    SYNTAX       CfprApFabricWarnings
    MAX-ACCESS   read-only
    STATUS       current
    DESCRIPTION
        "Cisco Firepower fabric:EthLanPc:warnings managed object property"
    ::= { cfprApFabricEthLanPcEntry 40 }

cfprApFabricEthLanPcEpTable OBJECT-TYPE
    SYNTAX           SEQUENCE OF CfprApFabricEthLanPcEpEntry
    MAX-ACCESS       not-accessible
    STATUS           current
    DESCRIPTION
        "Cisco Firepower fabric:EthLanPcEp managed object table"
    ::= { cfprApFabricObjects 30 }

cfprApFabricEthLanPcEpEntry OBJECT-TYPE
    SYNTAX           CfprApFabricEthLanPcEpEntry
    MAX-ACCESS       not-accessible
    STATUS           current
    DESCRIPTION
        "Entry for the cfprApFabricEthLanPcEpTable table."
    INDEX { cfprApFabricEthLanPcEpInstanceId }
    ::= { cfprApFabricEthLanPcEpTable 1 }

CfprApFabricEthLanPcEpEntry ::= SEQUENCE {
    cfprApFabricEthLanPcEpInstanceId                                 CfprApManagedObjectId,
    cfprApFabricEthLanPcEpDnData                                     CfprApManagedObjectDn,
    cfprApFabricEthLanPcEpRn                                         SnmpAdminString,
    cfprApFabricEthLanPcEpAdminState                                 CfprApFabricExternalEpAdminState,
    cfprApFabricEthLanPcEpAggrPortId                                 Gauge32,
    cfprApFabricEthLanPcEpChassisId                                  Gauge32,
    cfprApFabricEthLanPcEpEpDn                                       SnmpAdminString,
    cfprApFabricEthLanPcEpEthLinkProfileName                         SnmpAdminString,
    cfprApFabricEthLanPcEpFltAggr                                    Unsigned64,
    cfprApFabricEthLanPcEpIfRole                                     CfprApFabricLanEpIfRole,
    cfprApFabricEthLanPcEpIfType                                     CfprApFabricPIoEpIfType,
    cfprApFabricEthLanPcEpLicGP                                      Unsigned64,
    cfprApFabricEthLanPcEpLicState                                   CfprApLicenseState,
    cfprApFabricEthLanPcEpLocale                                     CfprApFabricExternalEpLocale,
    cfprApFabricEthLanPcEpMembership                                 CfprApFabricMembershipStatus,
    cfprApFabricEthLanPcEpName                                       SnmpAdminString,
    cfprApFabricEthLanPcEpOperEthLinkProfileName                     SnmpAdminString,
    cfprApFabricEthLanPcEpOperState                                  CfprApFabricPIoEpOperState,
    cfprApFabricEthLanPcEpOperStateReason                            SnmpAdminString,
    cfprApFabricEthLanPcEpPeerAggrPortId                             Gauge32,
    cfprApFabricEthLanPcEpPeerChassisId                              Gauge32,
    cfprApFabricEthLanPcEpPeerDn                                     SnmpAdminString,
    cfprApFabricEthLanPcEpPeerPortId                                 Gauge32,
    cfprApFabricEthLanPcEpPeerSlotId                                 Gauge32,
    cfprApFabricEthLanPcEpPortId                                     Gauge32,
    cfprApFabricEthLanPcEpSlotId                                     Gauge32,
    cfprApFabricEthLanPcEpSwitchId                                   CfprApNetworkSwitchId,
    cfprApFabricEthLanPcEpTransport                                  CfprApFabricAEthLanEpTransport,
    cfprApFabricEthLanPcEpType                                       CfprApFabricLanEpType,
    cfprApFabricEthLanPcEpUdldOperState                              CfprApFabricUdldOperState,
    cfprApFabricEthLanPcEpWarnings                                   CfprApFabricWarnings
}

cfprApFabricEthLanPcEpInstanceId OBJECT-TYPE
    SYNTAX       CfprApManagedObjectId
    MAX-ACCESS   not-accessible
    STATUS       current
    DESCRIPTION
        "Instance identifier of the managed object."
    ::= { cfprApFabricEthLanPcEpEntry 1 }

cfprApFabricEthLanPcEpDnData OBJECT-TYPE
    SYNTAX       CfprApManagedObjectDn
    MAX-ACCESS   read-only
    STATUS       current
    DESCRIPTION
        "Cisco Firepower fabric:EthLanPcEp:dn managed object property"
    ::= { cfprApFabricEthLanPcEpEntry 2 }

cfprApFabricEthLanPcEpRn OBJECT-TYPE
    SYNTAX       SnmpAdminString
    MAX-ACCESS   read-only
    STATUS       current
    DESCRIPTION
        "Cisco Firepower fabric:EthLanPcEp:rn managed object property"
    ::= { cfprApFabricEthLanPcEpEntry 3 }

cfprApFabricEthLanPcEpAdminState OBJECT-TYPE
    SYNTAX       CfprApFabricExternalEpAdminState
    MAX-ACCESS   read-only
    STATUS       current
    DESCRIPTION
        "Cisco Firepower fabric:EthLanPcEp:adminState managed
        object property"
    ::= { cfprApFabricEthLanPcEpEntry 4 }

cfprApFabricEthLanPcEpAggrPortId OBJECT-TYPE
    SYNTAX       Gauge32
    MAX-ACCESS   read-only
    STATUS       current
    DESCRIPTION
        "Cisco Firepower fabric:EthLanPcEp:aggrPortId managed
        object property"
    ::= { cfprApFabricEthLanPcEpEntry 5 }

cfprApFabricEthLanPcEpChassisId OBJECT-TYPE
    SYNTAX       Gauge32
    MAX-ACCESS   read-only
    STATUS       current
    DESCRIPTION
        "Cisco Firepower fabric:EthLanPcEp:chassisId managed
        object property"
    ::= { cfprApFabricEthLanPcEpEntry 6 }

cfprApFabricEthLanPcEpEpDn OBJECT-TYPE
    SYNTAX       SnmpAdminString
    MAX-ACCESS   read-only
    STATUS       current
    DESCRIPTION
        "Cisco Firepower fabric:EthLanPcEp:epDn managed object property"
    ::= { cfprApFabricEthLanPcEpEntry 7 }

cfprApFabricEthLanPcEpEthLinkProfileName OBJECT-TYPE
    SYNTAX       SnmpAdminString
    MAX-ACCESS   read-only
    STATUS       current
    DESCRIPTION
        "Cisco Firepower fabric:EthLanPcEp:ethLinkProfileName
        managed object property"
    ::= { cfprApFabricEthLanPcEpEntry 8 }

cfprApFabricEthLanPcEpFltAggr OBJECT-TYPE
    SYNTAX       Unsigned64
    MAX-ACCESS   read-only
    STATUS       current
    DESCRIPTION
        "Cisco Firepower fabric:EthLanPcEp:fltAggr managed
        object property"
    ::= { cfprApFabricEthLanPcEpEntry 9 }

cfprApFabricEthLanPcEpIfRole OBJECT-TYPE
    SYNTAX       CfprApFabricLanEpIfRole
    MAX-ACCESS   read-only
    STATUS       current
    DESCRIPTION
        "Cisco Firepower fabric:EthLanPcEp:ifRole managed object property"
    ::= { cfprApFabricEthLanPcEpEntry 10 }

cfprApFabricEthLanPcEpIfType OBJECT-TYPE
    SYNTAX       CfprApFabricPIoEpIfType
    MAX-ACCESS   read-only
    STATUS       current
    DESCRIPTION
        "Cisco Firepower fabric:EthLanPcEp:ifType managed object property"
    ::= { cfprApFabricEthLanPcEpEntry 11 }

cfprApFabricEthLanPcEpLicGP OBJECT-TYPE
    SYNTAX       Unsigned64
    MAX-ACCESS   read-only
    STATUS       current
    DESCRIPTION
        "Cisco Firepower fabric:EthLanPcEp:licGP managed object property"
    ::= { cfprApFabricEthLanPcEpEntry 12 }

cfprApFabricEthLanPcEpLicState OBJECT-TYPE
    SYNTAX       CfprApLicenseState
    MAX-ACCESS   read-only
    STATUS       current
    DESCRIPTION
        "Cisco Firepower fabric:EthLanPcEp:licState managed
        object property"
    ::= { cfprApFabricEthLanPcEpEntry 13 }

cfprApFabricEthLanPcEpLocale OBJECT-TYPE
    SYNTAX       CfprApFabricExternalEpLocale
    MAX-ACCESS   read-only
    STATUS       current
    DESCRIPTION
        "Cisco Firepower fabric:EthLanPcEp:locale managed object property"
    ::= { cfprApFabricEthLanPcEpEntry 14 }

cfprApFabricEthLanPcEpMembership OBJECT-TYPE
    SYNTAX       CfprApFabricMembershipStatus
    MAX-ACCESS   read-only
    STATUS       current
    DESCRIPTION
        "Cisco Firepower fabric:EthLanPcEp:membership managed
        object property"
    ::= { cfprApFabricEthLanPcEpEntry 15 }

cfprApFabricEthLanPcEpName OBJECT-TYPE
    SYNTAX       SnmpAdminString
    MAX-ACCESS   read-only
    STATUS       current
    DESCRIPTION
        "Cisco Firepower fabric:EthLanPcEp:name managed object property"
    ::= { cfprApFabricEthLanPcEpEntry 16 }

cfprApFabricEthLanPcEpOperEthLinkProfileName OBJECT-TYPE
    SYNTAX       SnmpAdminString
    MAX-ACCESS   read-only
    STATUS       current
    DESCRIPTION
        "Cisco Firepower fabric:EthLanPcEp:operEthLinkProfileName
        managed object property"
    ::= { cfprApFabricEthLanPcEpEntry 17 }

cfprApFabricEthLanPcEpOperState OBJECT-TYPE
    SYNTAX       CfprApFabricPIoEpOperState
    MAX-ACCESS   read-only
    STATUS       current
    DESCRIPTION
        "Cisco Firepower fabric:EthLanPcEp:operState managed
        object property"
    ::= { cfprApFabricEthLanPcEpEntry 18 }

cfprApFabricEthLanPcEpOperStateReason OBJECT-TYPE
    SYNTAX       SnmpAdminString
    MAX-ACCESS   read-only
    STATUS       current
    DESCRIPTION
        "Cisco Firepower fabric:EthLanPcEp:operStateReason
        managed object property"
    ::= { cfprApFabricEthLanPcEpEntry 19 }

cfprApFabricEthLanPcEpPeerAggrPortId OBJECT-TYPE
    SYNTAX       Gauge32
    MAX-ACCESS   read-only
    STATUS       current
    DESCRIPTION
        "Cisco Firepower fabric:EthLanPcEp:peerAggrPortId
        managed object property"
    ::= { cfprApFabricEthLanPcEpEntry 20 }

cfprApFabricEthLanPcEpPeerChassisId OBJECT-TYPE
    SYNTAX       Gauge32
    MAX-ACCESS   read-only
    STATUS       current
    DESCRIPTION
        "Cisco Firepower fabric:EthLanPcEp:peerChassisId
        managed object property"
    ::= { cfprApFabricEthLanPcEpEntry 21 }

cfprApFabricEthLanPcEpPeerDn OBJECT-TYPE
    SYNTAX       SnmpAdminString
    MAX-ACCESS   read-only
    STATUS       current
    DESCRIPTION
        "Cisco Firepower fabric:EthLanPcEp:peerDn managed object property"
    ::= { cfprApFabricEthLanPcEpEntry 22 }

cfprApFabricEthLanPcEpPeerPortId OBJECT-TYPE
    SYNTAX       Gauge32
    MAX-ACCESS   read-only
    STATUS       current
    DESCRIPTION
        "Cisco Firepower fabric:EthLanPcEp:peerPortId managed
        object property"
    ::= { cfprApFabricEthLanPcEpEntry 23 }

cfprApFabricEthLanPcEpPeerSlotId OBJECT-TYPE
    SYNTAX       Gauge32
    MAX-ACCESS   read-only
    STATUS       current
    DESCRIPTION
        "Cisco Firepower fabric:EthLanPcEp:peerSlotId managed
        object property"
    ::= { cfprApFabricEthLanPcEpEntry 24 }

cfprApFabricEthLanPcEpPortId OBJECT-TYPE
    SYNTAX       Gauge32
    MAX-ACCESS   read-only
    STATUS       current
    DESCRIPTION
        "Cisco Firepower fabric:EthLanPcEp:portId managed object property"
    ::= { cfprApFabricEthLanPcEpEntry 25 }

cfprApFabricEthLanPcEpSlotId OBJECT-TYPE
    SYNTAX       Gauge32
    MAX-ACCESS   read-only
    STATUS       current
    DESCRIPTION
        "Cisco Firepower fabric:EthLanPcEp:slotId managed object property"
    ::= { cfprApFabricEthLanPcEpEntry 26 }

cfprApFabricEthLanPcEpSwitchId OBJECT-TYPE
    SYNTAX       CfprApNetworkSwitchId
    MAX-ACCESS   read-only
    STATUS       current
    DESCRIPTION
        "Cisco Firepower fabric:EthLanPcEp:switchId managed
        object property"
    ::= { cfprApFabricEthLanPcEpEntry 27 }

cfprApFabricEthLanPcEpTransport OBJECT-TYPE
    SYNTAX       CfprApFabricAEthLanEpTransport
    MAX-ACCESS   read-only
    STATUS       current
    DESCRIPTION
        "Cisco Firepower fabric:EthLanPcEp:transport managed
        object property"
    ::= { cfprApFabricEthLanPcEpEntry 28 }

cfprApFabricEthLanPcEpType OBJECT-TYPE
    SYNTAX       CfprApFabricLanEpType
    MAX-ACCESS   read-only
    STATUS       current
    DESCRIPTION
        "Cisco Firepower fabric:EthLanPcEp:type managed object property"
    ::= { cfprApFabricEthLanPcEpEntry 29 }

cfprApFabricEthLanPcEpUdldOperState OBJECT-TYPE
    SYNTAX       CfprApFabricUdldOperState
    MAX-ACCESS   read-only
    STATUS       current
    DESCRIPTION
        "Cisco Firepower fabric:EthLanPcEp:udldOperState
        managed object property"
    ::= { cfprApFabricEthLanPcEpEntry 30 }

cfprApFabricEthLanPcEpWarnings OBJECT-TYPE
    SYNTAX       CfprApFabricWarnings
    MAX-ACCESS   read-only
    STATUS       current
    DESCRIPTION
        "Cisco Firepower fabric:EthLanPcEp:warnings managed
        object property"
    ::= { cfprApFabricEthLanPcEpEntry 31 }

cfprApFabricEthLinkProfileTable OBJECT-TYPE
    SYNTAX           SEQUENCE OF CfprApFabricEthLinkProfileEntry
    MAX-ACCESS       not-accessible
    STATUS           current
    DESCRIPTION
        "Cisco Firepower fabric:EthLinkProfile managed object table"
    ::= { cfprApFabricObjects 31 }

cfprApFabricEthLinkProfileEntry OBJECT-TYPE
    SYNTAX           CfprApFabricEthLinkProfileEntry
    MAX-ACCESS       not-accessible
    STATUS           current
    DESCRIPTION
        "Entry for the cfprApFabricEthLinkProfileTable table."
    INDEX { cfprApFabricEthLinkProfileInstanceId }
    ::= { cfprApFabricEthLinkProfileTable 1 }

CfprApFabricEthLinkProfileEntry ::= SEQUENCE {
    cfprApFabricEthLinkProfileInstanceId                             CfprApManagedObjectId,
    cfprApFabricEthLinkProfileDn                                     CfprApManagedObjectDn,
    cfprApFabricEthLinkProfileRn                                     SnmpAdminString,
    cfprApFabricEthLinkProfileCdpLinkPolicyName                      SnmpAdminString,
    cfprApFabricEthLinkProfileDescr                                  SnmpAdminString,
    cfprApFabricEthLinkProfileIntId                                  SnmpAdminString,
    cfprApFabricEthLinkProfileName                                   SnmpAdminString,
    cfprApFabricEthLinkProfileOperCdpLinkPolicyName                  SnmpAdminString,
    cfprApFabricEthLinkProfileOperUdldLinkPolicyName                 SnmpAdminString,
    cfprApFabricEthLinkProfilePolicyLevel                            Gauge32,
    cfprApFabricEthLinkProfilePolicyOwner                            CfprApPolicyPolicyOwner,
    cfprApFabricEthLinkProfileUdldLinkPolicyName                     SnmpAdminString
}

cfprApFabricEthLinkProfileInstanceId OBJECT-TYPE
    SYNTAX       CfprApManagedObjectId
    MAX-ACCESS   not-accessible
    STATUS       current
    DESCRIPTION
        "Instance identifier of the managed object."
    ::= { cfprApFabricEthLinkProfileEntry 1 }

cfprApFabricEthLinkProfileDn OBJECT-TYPE
    SYNTAX       CfprApManagedObjectDn
    MAX-ACCESS   read-only
    STATUS       current
    DESCRIPTION
        "Cisco Firepower fabric:EthLinkProfile:dn managed object property"
    ::= { cfprApFabricEthLinkProfileEntry 2 }

cfprApFabricEthLinkProfileRn OBJECT-TYPE
    SYNTAX       SnmpAdminString
    MAX-ACCESS   read-only
    STATUS       current
    DESCRIPTION
        "Cisco Firepower fabric:EthLinkProfile:rn managed object property"
    ::= { cfprApFabricEthLinkProfileEntry 3 }

cfprApFabricEthLinkProfileCdpLinkPolicyName OBJECT-TYPE
    SYNTAX       SnmpAdminString
    MAX-ACCESS   read-only
    STATUS       current
    DESCRIPTION
        "Cisco Firepower fabric:EthLinkProfile:cdpLinkPolicyName
        managed object property"
    ::= { cfprApFabricEthLinkProfileEntry 4 }

cfprApFabricEthLinkProfileDescr OBJECT-TYPE
    SYNTAX       SnmpAdminString
    MAX-ACCESS   read-only
    STATUS       current
    DESCRIPTION
        "Cisco Firepower fabric:EthLinkProfile:descr managed
        object property"
    ::= { cfprApFabricEthLinkProfileEntry 5 }

cfprApFabricEthLinkProfileIntId OBJECT-TYPE
    SYNTAX       SnmpAdminString
    MAX-ACCESS   read-only
    STATUS       current
    DESCRIPTION
        "Cisco Firepower fabric:EthLinkProfile:intId managed
        object property"
    ::= { cfprApFabricEthLinkProfileEntry 6 }

cfprApFabricEthLinkProfileName OBJECT-TYPE
    SYNTAX       SnmpAdminString
    MAX-ACCESS   read-only
    STATUS       current
    DESCRIPTION
        "Cisco Firepower fabric:EthLinkProfile:name managed
        object property"
    ::= { cfprApFabricEthLinkProfileEntry 7 }

cfprApFabricEthLinkProfileOperCdpLinkPolicyName OBJECT-TYPE
    SYNTAX       SnmpAdminString
    MAX-ACCESS   read-only
    STATUS       current
    DESCRIPTION
        "Cisco Firepower fabric:EthLinkProfile:operCdpLinkPolicyName
        managed object property"
    ::= { cfprApFabricEthLinkProfileEntry 8 }

cfprApFabricEthLinkProfileOperUdldLinkPolicyName OBJECT-TYPE
    SYNTAX       SnmpAdminString
    MAX-ACCESS   read-only
    STATUS       current
    DESCRIPTION
        "Cisco Firepower fabric:EthLinkProfile:operUdldLinkPolicyName
        managed object property"
    ::= { cfprApFabricEthLinkProfileEntry 9 }

cfprApFabricEthLinkProfilePolicyLevel OBJECT-TYPE
    SYNTAX       Gauge32
    MAX-ACCESS   read-only
    STATUS       current
    DESCRIPTION
        "Cisco Firepower fabric:EthLinkProfile:policyLevel
        managed object property"
    ::= { cfprApFabricEthLinkProfileEntry 10 }

cfprApFabricEthLinkProfilePolicyOwner OBJECT-TYPE
    SYNTAX       CfprApPolicyPolicyOwner
    MAX-ACCESS   read-only
    STATUS       current
    DESCRIPTION
        "Cisco Firepower fabric:EthLinkProfile:policyOwner
        managed object property"
    ::= { cfprApFabricEthLinkProfileEntry 11 }

cfprApFabricEthLinkProfileUdldLinkPolicyName OBJECT-TYPE
    SYNTAX       SnmpAdminString
    MAX-ACCESS   read-only
    STATUS       current
    DESCRIPTION
        "Cisco Firepower fabric:EthLinkProfile:udldLinkPolicyName
        managed object property"
    ::= { cfprApFabricEthLinkProfileEntry 12 }

cfprApFabricEthMonTable OBJECT-TYPE
    SYNTAX           SEQUENCE OF CfprApFabricEthMonEntry
    MAX-ACCESS       not-accessible
    STATUS           current
    DESCRIPTION
        "Cisco Firepower fabric:EthMon managed object table"
    ::= { cfprApFabricObjects 32 }

cfprApFabricEthMonEntry OBJECT-TYPE
    SYNTAX           CfprApFabricEthMonEntry
    MAX-ACCESS       not-accessible
    STATUS           current
    DESCRIPTION
        "Entry for the cfprApFabricEthMonTable table."
    INDEX { cfprApFabricEthMonInstanceId }
    ::= { cfprApFabricEthMonTable 1 }

CfprApFabricEthMonEntry ::= SEQUENCE {
    cfprApFabricEthMonInstanceId                                     CfprApManagedObjectId,
    cfprApFabricEthMonDn                                             CfprApManagedObjectDn,
    cfprApFabricEthMonRn                                             SnmpAdminString,
    cfprApFabricEthMonAdminState                                     CfprApFabricMonAdminState,
    cfprApFabricEthMonConfigFailReason                               SnmpAdminString,
    cfprApFabricEthMonId                                             CfprApNetworkSwitchId,
    cfprApFabricEthMonIsConfigSuccess                                TruthValue,
    cfprApFabricEthMonLocale                                         CfprApFabricExternalLocale,
    cfprApFabricEthMonName                                           SnmpAdminString,
    cfprApFabricEthMonOperState                                      CfprApFabricMonOperState,
    cfprApFabricEthMonOperStateReason                                CfprApFabricMonOperStateReason,
    cfprApFabricEthMonPeerDn                                         SnmpAdminString,
    cfprApFabricEthMonSession                                        Gauge32,
    cfprApFabricEthMonTransport                                      CfprApFabricEthMonTransport,
    cfprApFabricEthMonType                                           CfprApFabricEthMonType
}

cfprApFabricEthMonInstanceId OBJECT-TYPE
    SYNTAX       CfprApManagedObjectId
    MAX-ACCESS   not-accessible
    STATUS       current
    DESCRIPTION
        "Instance identifier of the managed object."
    ::= { cfprApFabricEthMonEntry 1 }

cfprApFabricEthMonDn OBJECT-TYPE
    SYNTAX       CfprApManagedObjectDn
    MAX-ACCESS   read-only
    STATUS       current
    DESCRIPTION
        "Cisco Firepower fabric:EthMon:dn managed object property"
    ::= { cfprApFabricEthMonEntry 2 }

cfprApFabricEthMonRn OBJECT-TYPE
    SYNTAX       SnmpAdminString
    MAX-ACCESS   read-only
    STATUS       current
    DESCRIPTION
        "Cisco Firepower fabric:EthMon:rn managed object property"
    ::= { cfprApFabricEthMonEntry 3 }

cfprApFabricEthMonAdminState OBJECT-TYPE
    SYNTAX       CfprApFabricMonAdminState
    MAX-ACCESS   read-only
    STATUS       current
    DESCRIPTION
        "Cisco Firepower fabric:EthMon:adminState managed object property"
    ::= { cfprApFabricEthMonEntry 4 }

cfprApFabricEthMonConfigFailReason OBJECT-TYPE
    SYNTAX       SnmpAdminString
    MAX-ACCESS   read-only
    STATUS       current
    DESCRIPTION
        "Cisco Firepower fabric:EthMon:configFailReason
        managed object property"
    ::= { cfprApFabricEthMonEntry 5 }

cfprApFabricEthMonId OBJECT-TYPE
    SYNTAX       CfprApNetworkSwitchId
    MAX-ACCESS   read-only
    STATUS       current
    DESCRIPTION
        "Cisco Firepower fabric:EthMon:id managed object property"
    ::= { cfprApFabricEthMonEntry 6 }

cfprApFabricEthMonIsConfigSuccess OBJECT-TYPE
    SYNTAX       TruthValue
    MAX-ACCESS   read-only
    STATUS       current
    DESCRIPTION
        "Cisco Firepower fabric:EthMon:isConfigSuccess
        managed object property"
    ::= { cfprApFabricEthMonEntry 7 }

cfprApFabricEthMonLocale OBJECT-TYPE
    SYNTAX       CfprApFabricExternalLocale
    MAX-ACCESS   read-only
    STATUS       current
    DESCRIPTION
        "Cisco Firepower fabric:EthMon:locale managed object property"
    ::= { cfprApFabricEthMonEntry 8 }

cfprApFabricEthMonName OBJECT-TYPE
    SYNTAX       SnmpAdminString
    MAX-ACCESS   read-only
    STATUS       current
    DESCRIPTION
        "Cisco Firepower fabric:EthMon:name managed object property"
    ::= { cfprApFabricEthMonEntry 9 }

cfprApFabricEthMonOperState OBJECT-TYPE
    SYNTAX       CfprApFabricMonOperState
    MAX-ACCESS   read-only
    STATUS       current
    DESCRIPTION
        "Cisco Firepower fabric:EthMon:operState managed object property"
    ::= { cfprApFabricEthMonEntry 10 }

cfprApFabricEthMonOperStateReason OBJECT-TYPE
    SYNTAX       CfprApFabricMonOperStateReason
    MAX-ACCESS   read-only
    STATUS       current
    DESCRIPTION
        "Cisco Firepower fabric:EthMon:operStateReason
        managed object property"
    ::= { cfprApFabricEthMonEntry 11 }

cfprApFabricEthMonPeerDn OBJECT-TYPE
    SYNTAX       SnmpAdminString
    MAX-ACCESS   read-only
    STATUS       current
    DESCRIPTION
        "Cisco Firepower fabric:EthMon:peerDn managed object property"
    ::= { cfprApFabricEthMonEntry 12 }

cfprApFabricEthMonSession OBJECT-TYPE
    SYNTAX       Gauge32
    MAX-ACCESS   read-only
    STATUS       current
    DESCRIPTION
        "Cisco Firepower fabric:EthMon:session managed object property"
    ::= { cfprApFabricEthMonEntry 13 }

cfprApFabricEthMonTransport OBJECT-TYPE
    SYNTAX       CfprApFabricEthMonTransport
    MAX-ACCESS   read-only
    STATUS       current
    DESCRIPTION
        "Cisco Firepower fabric:EthMon:transport managed object property"
    ::= { cfprApFabricEthMonEntry 14 }

cfprApFabricEthMonType OBJECT-TYPE
    SYNTAX       CfprApFabricEthMonType
    MAX-ACCESS   read-only
    STATUS       current
    DESCRIPTION
        "Cisco Firepower fabric:EthMon:type managed object property"
    ::= { cfprApFabricEthMonEntry 15 }

cfprApFabricEthMonDestEpTable OBJECT-TYPE
    SYNTAX           SEQUENCE OF CfprApFabricEthMonDestEpEntry
    MAX-ACCESS       not-accessible
    STATUS           current
    DESCRIPTION
        "Cisco Firepower fabric:EthMonDestEp managed object table"
    ::= { cfprApFabricObjects 33 }

cfprApFabricEthMonDestEpEntry OBJECT-TYPE
    SYNTAX           CfprApFabricEthMonDestEpEntry
    MAX-ACCESS       not-accessible
    STATUS           current
    DESCRIPTION
        "Entry for the cfprApFabricEthMonDestEpTable table."
    INDEX { cfprApFabricEthMonDestEpInstanceId }
    ::= { cfprApFabricEthMonDestEpTable 1 }

CfprApFabricEthMonDestEpEntry ::= SEQUENCE {
    cfprApFabricEthMonDestEpInstanceId                               CfprApManagedObjectId,
    cfprApFabricEthMonDestEpDn                                       CfprApManagedObjectDn,
    cfprApFabricEthMonDestEpRn                                       SnmpAdminString,
    cfprApFabricEthMonDestEpAdminSpeed                               CfprApFabricEthMonDestEpAdminSpeed,
    cfprApFabricEthMonDestEpAdminState                               CfprApFabricExternalEpAdminState,
    cfprApFabricEthMonDestEpAggrPortId                               Gauge32,
    cfprApFabricEthMonDestEpChassisId                                Gauge32,
    cfprApFabricEthMonDestEpEpDn                                     SnmpAdminString,
    cfprApFabricEthMonDestEpFltAggr                                  Unsigned64,
    cfprApFabricEthMonDestEpIfRole                                   CfprApFabricEthMonDestEpIfRole,
    cfprApFabricEthMonDestEpIfType                                   CfprApFabricPIoEpIfType,
    cfprApFabricEthMonDestEpLicGP                                    Unsigned64,
    cfprApFabricEthMonDestEpLicState                                 CfprApLicenseState,
    cfprApFabricEthMonDestEpLocale                                   CfprApFabricExternalEpLocale,
    cfprApFabricEthMonDestEpName                                     SnmpAdminString,
    cfprApFabricEthMonDestEpOperState                                CfprApFabricPIoEpOperState,
    cfprApFabricEthMonDestEpOperStateReason                          SnmpAdminString,
    cfprApFabricEthMonDestEpPeerAggrPortId                           Gauge32,
    cfprApFabricEthMonDestEpPeerChassisId                            Gauge32,
    cfprApFabricEthMonDestEpPeerDn                                   SnmpAdminString,
    cfprApFabricEthMonDestEpPeerPortId                               Gauge32,
    cfprApFabricEthMonDestEpPeerSlotId                               Gauge32,
    cfprApFabricEthMonDestEpPortId                                   CfprApFabricEthMonDestEpPortId,
    cfprApFabricEthMonDestEpSlotId                                   CfprApFabricEthMonDestEpSlotId,
    cfprApFabricEthMonDestEpSwitchId                                 CfprApNetworkSwitchId,
    cfprApFabricEthMonDestEpTransport                                CfprApNetworkTransport,
    cfprApFabricEthMonDestEpType                                     CfprApFabricEthMonDestEpType,
    cfprApFabricEthMonDestEpWarnings                                 CfprApFabricWarnings
}

cfprApFabricEthMonDestEpInstanceId OBJECT-TYPE
    SYNTAX       CfprApManagedObjectId
    MAX-ACCESS   not-accessible
    STATUS       current
    DESCRIPTION
        "Instance identifier of the managed object."
    ::= { cfprApFabricEthMonDestEpEntry 1 }

cfprApFabricEthMonDestEpDn OBJECT-TYPE
    SYNTAX       CfprApManagedObjectDn
    MAX-ACCESS   read-only
    STATUS       current
    DESCRIPTION
        "Cisco Firepower fabric:EthMonDestEp:dn managed object property"
    ::= { cfprApFabricEthMonDestEpEntry 2 }

cfprApFabricEthMonDestEpRn OBJECT-TYPE
    SYNTAX       SnmpAdminString
    MAX-ACCESS   read-only
    STATUS       current
    DESCRIPTION
        "Cisco Firepower fabric:EthMonDestEp:rn managed object property"
    ::= { cfprApFabricEthMonDestEpEntry 3 }

cfprApFabricEthMonDestEpAdminSpeed OBJECT-TYPE
    SYNTAX       CfprApFabricEthMonDestEpAdminSpeed
    MAX-ACCESS   read-only
    STATUS       current
    DESCRIPTION
        "Cisco Firepower fabric:EthMonDestEp:adminSpeed
        managed object property"
    ::= { cfprApFabricEthMonDestEpEntry 4 }

cfprApFabricEthMonDestEpAdminState OBJECT-TYPE
    SYNTAX       CfprApFabricExternalEpAdminState
    MAX-ACCESS   read-only
    STATUS       current
    DESCRIPTION
        "Cisco Firepower fabric:EthMonDestEp:adminState
        managed object property"
    ::= { cfprApFabricEthMonDestEpEntry 5 }

cfprApFabricEthMonDestEpAggrPortId OBJECT-TYPE
    SYNTAX       Gauge32
    MAX-ACCESS   read-only
    STATUS       current
    DESCRIPTION
        "Cisco Firepower fabric:EthMonDestEp:aggrPortId
        managed object property"
    ::= { cfprApFabricEthMonDestEpEntry 6 }

cfprApFabricEthMonDestEpChassisId OBJECT-TYPE
    SYNTAX       Gauge32
    MAX-ACCESS   read-only
    STATUS       current
    DESCRIPTION
        "Cisco Firepower fabric:EthMonDestEp:chassisId
        managed object property"
    ::= { cfprApFabricEthMonDestEpEntry 7 }

cfprApFabricEthMonDestEpEpDn OBJECT-TYPE
    SYNTAX       SnmpAdminString
    MAX-ACCESS   read-only
    STATUS       current
    DESCRIPTION
        "Cisco Firepower fabric:EthMonDestEp:epDn managed object property"
    ::= { cfprApFabricEthMonDestEpEntry 8 }

cfprApFabricEthMonDestEpFltAggr OBJECT-TYPE
    SYNTAX       Unsigned64
    MAX-ACCESS   read-only
    STATUS       current
    DESCRIPTION
        "Cisco Firepower fabric:EthMonDestEp:fltAggr managed
        object property"
    ::= { cfprApFabricEthMonDestEpEntry 9 }

cfprApFabricEthMonDestEpIfRole OBJECT-TYPE
    SYNTAX       CfprApFabricEthMonDestEpIfRole
    MAX-ACCESS   read-only
    STATUS       current
    DESCRIPTION
        "Cisco Firepower fabric:EthMonDestEp:ifRole managed
        object property"
    ::= { cfprApFabricEthMonDestEpEntry 10 }

cfprApFabricEthMonDestEpIfType OBJECT-TYPE
    SYNTAX       CfprApFabricPIoEpIfType
    MAX-ACCESS   read-only
    STATUS       current
    DESCRIPTION
        "Cisco Firepower fabric:EthMonDestEp:ifType managed
        object property"
    ::= { cfprApFabricEthMonDestEpEntry 11 }

cfprApFabricEthMonDestEpLicGP OBJECT-TYPE
    SYNTAX       Unsigned64
    MAX-ACCESS   read-only
    STATUS       current
    DESCRIPTION
        "Cisco Firepower fabric:EthMonDestEp:licGP managed
        object property"
    ::= { cfprApFabricEthMonDestEpEntry 12 }

cfprApFabricEthMonDestEpLicState OBJECT-TYPE
    SYNTAX       CfprApLicenseState
    MAX-ACCESS   read-only
    STATUS       current
    DESCRIPTION
        "Cisco Firepower fabric:EthMonDestEp:licState managed
        object property"
    ::= { cfprApFabricEthMonDestEpEntry 13 }

cfprApFabricEthMonDestEpLocale OBJECT-TYPE
    SYNTAX       CfprApFabricExternalEpLocale
    MAX-ACCESS   read-only
    STATUS       current
    DESCRIPTION
        "Cisco Firepower fabric:EthMonDestEp:locale managed
        object property"
    ::= { cfprApFabricEthMonDestEpEntry 14 }

cfprApFabricEthMonDestEpName OBJECT-TYPE
    SYNTAX       SnmpAdminString
    MAX-ACCESS   read-only
    STATUS       current
    DESCRIPTION
        "Cisco Firepower fabric:EthMonDestEp:name managed object property"
    ::= { cfprApFabricEthMonDestEpEntry 15 }

cfprApFabricEthMonDestEpOperState OBJECT-TYPE
    SYNTAX       CfprApFabricPIoEpOperState
    MAX-ACCESS   read-only
    STATUS       current
    DESCRIPTION
        "Cisco Firepower fabric:EthMonDestEp:operState
        managed object property"
    ::= { cfprApFabricEthMonDestEpEntry 16 }

cfprApFabricEthMonDestEpOperStateReason OBJECT-TYPE
    SYNTAX       SnmpAdminString
    MAX-ACCESS   read-only
    STATUS       current
    DESCRIPTION
        "Cisco Firepower fabric:EthMonDestEp:operStateReason
        managed object property"
    ::= { cfprApFabricEthMonDestEpEntry 17 }

cfprApFabricEthMonDestEpPeerAggrPortId OBJECT-TYPE
    SYNTAX       Gauge32
    MAX-ACCESS   read-only
    STATUS       current
    DESCRIPTION
        "Cisco Firepower fabric:EthMonDestEp:peerAggrPortId
        managed object property"
    ::= { cfprApFabricEthMonDestEpEntry 18 }

cfprApFabricEthMonDestEpPeerChassisId OBJECT-TYPE
    SYNTAX       Gauge32
    MAX-ACCESS   read-only
    STATUS       current
    DESCRIPTION
        "Cisco Firepower fabric:EthMonDestEp:peerChassisId
        managed object property"
    ::= { cfprApFabricEthMonDestEpEntry 19 }

cfprApFabricEthMonDestEpPeerDn OBJECT-TYPE
    SYNTAX       SnmpAdminString
    MAX-ACCESS   read-only
    STATUS       current
    DESCRIPTION
        "Cisco Firepower fabric:EthMonDestEp:peerDn managed
        object property"
    ::= { cfprApFabricEthMonDestEpEntry 20 }

cfprApFabricEthMonDestEpPeerPortId OBJECT-TYPE
    SYNTAX       Gauge32
    MAX-ACCESS   read-only
    STATUS       current
    DESCRIPTION
        "Cisco Firepower fabric:EthMonDestEp:peerPortId
        managed object property"
    ::= { cfprApFabricEthMonDestEpEntry 21 }

cfprApFabricEthMonDestEpPeerSlotId OBJECT-TYPE
    SYNTAX       Gauge32
    MAX-ACCESS   read-only
    STATUS       current
    DESCRIPTION
        "Cisco Firepower fabric:EthMonDestEp:peerSlotId
        managed object property"
    ::= { cfprApFabricEthMonDestEpEntry 22 }

cfprApFabricEthMonDestEpPortId OBJECT-TYPE
    SYNTAX       CfprApFabricEthMonDestEpPortId
    MAX-ACCESS   read-only
    STATUS       current
    DESCRIPTION
        "Cisco Firepower fabric:EthMonDestEp:portId managed
        object property"
    ::= { cfprApFabricEthMonDestEpEntry 23 }

cfprApFabricEthMonDestEpSlotId OBJECT-TYPE
    SYNTAX       CfprApFabricEthMonDestEpSlotId
    MAX-ACCESS   read-only
    STATUS       current
    DESCRIPTION
        "Cisco Firepower fabric:EthMonDestEp:slotId managed
        object property"
    ::= { cfprApFabricEthMonDestEpEntry 24 }

cfprApFabricEthMonDestEpSwitchId OBJECT-TYPE
    SYNTAX       CfprApNetworkSwitchId
    MAX-ACCESS   read-only
    STATUS       current
    DESCRIPTION
        "Cisco Firepower fabric:EthMonDestEp:switchId managed
        object property"
    ::= { cfprApFabricEthMonDestEpEntry 25 }

cfprApFabricEthMonDestEpTransport OBJECT-TYPE
    SYNTAX       CfprApNetworkTransport
    MAX-ACCESS   read-only
    STATUS       current
    DESCRIPTION
        "Cisco Firepower fabric:EthMonDestEp:transport
        managed object property"
    ::= { cfprApFabricEthMonDestEpEntry 26 }

cfprApFabricEthMonDestEpType OBJECT-TYPE
    SYNTAX       CfprApFabricEthMonDestEpType
    MAX-ACCESS   read-only
    STATUS       current
    DESCRIPTION
        "Cisco Firepower fabric:EthMonDestEp:type managed object property"
    ::= { cfprApFabricEthMonDestEpEntry 27 }

cfprApFabricEthMonDestEpWarnings OBJECT-TYPE
    SYNTAX       CfprApFabricWarnings
    MAX-ACCESS   read-only
    STATUS       current
    DESCRIPTION
        "Cisco Firepower fabric:EthMonDestEp:warnings managed
        object property"
    ::= { cfprApFabricEthMonDestEpEntry 28 }

cfprApFabricEthMonFiltEpTable OBJECT-TYPE
    SYNTAX           SEQUENCE OF CfprApFabricEthMonFiltEpEntry
    MAX-ACCESS       not-accessible
    STATUS           current
    DESCRIPTION
        "Cisco Firepower fabric:EthMonFiltEp managed object table"
    ::= { cfprApFabricObjects 34 }

cfprApFabricEthMonFiltEpEntry OBJECT-TYPE
    SYNTAX           CfprApFabricEthMonFiltEpEntry
    MAX-ACCESS       not-accessible
    STATUS           current
    DESCRIPTION
        "Entry for the cfprApFabricEthMonFiltEpTable table."
    INDEX { cfprApFabricEthMonFiltEpInstanceId }
    ::= { cfprApFabricEthMonFiltEpTable 1 }

CfprApFabricEthMonFiltEpEntry ::= SEQUENCE {
    cfprApFabricEthMonFiltEpInstanceId                               CfprApManagedObjectId,
    cfprApFabricEthMonFiltEpDn                                       CfprApManagedObjectDn,
    cfprApFabricEthMonFiltEpRn                                       SnmpAdminString,
    cfprApFabricEthMonFiltEpName                                     SnmpAdminString,
    cfprApFabricEthMonFiltEpSession                                  Gauge32,
    cfprApFabricEthMonFiltEpType                                     CfprApFabricEthMonFiltEpType
}

cfprApFabricEthMonFiltEpInstanceId OBJECT-TYPE
    SYNTAX       CfprApManagedObjectId
    MAX-ACCESS   not-accessible
    STATUS       current
    DESCRIPTION
        "Instance identifier of the managed object."
    ::= { cfprApFabricEthMonFiltEpEntry 1 }

cfprApFabricEthMonFiltEpDn OBJECT-TYPE
    SYNTAX       CfprApManagedObjectDn
    MAX-ACCESS   read-only
    STATUS       current
    DESCRIPTION
        "Cisco Firepower fabric:EthMonFiltEp:dn managed object property"
    ::= { cfprApFabricEthMonFiltEpEntry 2 }

cfprApFabricEthMonFiltEpRn OBJECT-TYPE
    SYNTAX       SnmpAdminString
    MAX-ACCESS   read-only
    STATUS       current
    DESCRIPTION
        "Cisco Firepower fabric:EthMonFiltEp:rn managed object property"
    ::= { cfprApFabricEthMonFiltEpEntry 3 }

cfprApFabricEthMonFiltEpName OBJECT-TYPE
    SYNTAX       SnmpAdminString
    MAX-ACCESS   read-only
    STATUS       current
    DESCRIPTION
        "Cisco Firepower fabric:EthMonFiltEp:name managed object property"
    ::= { cfprApFabricEthMonFiltEpEntry 4 }

cfprApFabricEthMonFiltEpSession OBJECT-TYPE
    SYNTAX       Gauge32
    MAX-ACCESS   read-only
    STATUS       current
    DESCRIPTION
        "Cisco Firepower fabric:EthMonFiltEp:session managed
        object property"
    ::= { cfprApFabricEthMonFiltEpEntry 5 }

cfprApFabricEthMonFiltEpType OBJECT-TYPE
    SYNTAX       CfprApFabricEthMonFiltEpType
    MAX-ACCESS   read-only
    STATUS       current
    DESCRIPTION
        "Cisco Firepower fabric:EthMonFiltEp:type managed object property"
    ::= { cfprApFabricEthMonFiltEpEntry 6 }

cfprApFabricEthMonFiltRefTable OBJECT-TYPE
    SYNTAX           SEQUENCE OF CfprApFabricEthMonFiltRefEntry
    MAX-ACCESS       not-accessible
    STATUS           current
    DESCRIPTION
        "Cisco Firepower fabric:EthMonFiltRef managed object table"
    ::= { cfprApFabricObjects 35 }

cfprApFabricEthMonFiltRefEntry OBJECT-TYPE
    SYNTAX           CfprApFabricEthMonFiltRefEntry
    MAX-ACCESS       not-accessible
    STATUS           current
    DESCRIPTION
        "Entry for the cfprApFabricEthMonFiltRefTable table."
    INDEX { cfprApFabricEthMonFiltRefInstanceId }
    ::= { cfprApFabricEthMonFiltRefTable 1 }

CfprApFabricEthMonFiltRefEntry ::= SEQUENCE {
    cfprApFabricEthMonFiltRefInstanceId                              CfprApManagedObjectId,
    cfprApFabricEthMonFiltRefDn                                      CfprApManagedObjectDn,
    cfprApFabricEthMonFiltRefRn                                      SnmpAdminString,
    cfprApFabricEthMonFiltRefSrcFiltDn                               SnmpAdminString,
    cfprApFabricEthMonFiltRefType                                    CfprApFabricEthMonFiltRefType
}

cfprApFabricEthMonFiltRefInstanceId OBJECT-TYPE
    SYNTAX       CfprApManagedObjectId
    MAX-ACCESS   not-accessible
    STATUS       current
    DESCRIPTION
        "Instance identifier of the managed object."
    ::= { cfprApFabricEthMonFiltRefEntry 1 }

cfprApFabricEthMonFiltRefDn OBJECT-TYPE
    SYNTAX       CfprApManagedObjectDn
    MAX-ACCESS   read-only
    STATUS       current
    DESCRIPTION
        "Cisco Firepower fabric:EthMonFiltRef:dn managed object property"
    ::= { cfprApFabricEthMonFiltRefEntry 2 }

cfprApFabricEthMonFiltRefRn OBJECT-TYPE
    SYNTAX       SnmpAdminString
    MAX-ACCESS   read-only
    STATUS       current
    DESCRIPTION
        "Cisco Firepower fabric:EthMonFiltRef:rn managed object property"
    ::= { cfprApFabricEthMonFiltRefEntry 3 }

cfprApFabricEthMonFiltRefSrcFiltDn OBJECT-TYPE
    SYNTAX       SnmpAdminString
    MAX-ACCESS   read-only
    STATUS       current
    DESCRIPTION
        "Cisco Firepower fabric:EthMonFiltRef:srcFiltDn
        managed object property"
    ::= { cfprApFabricEthMonFiltRefEntry 4 }

cfprApFabricEthMonFiltRefType OBJECT-TYPE
    SYNTAX       CfprApFabricEthMonFiltRefType
    MAX-ACCESS   read-only
    STATUS       current
    DESCRIPTION
        "Cisco Firepower fabric:EthMonFiltRef:type managed
        object property"
    ::= { cfprApFabricEthMonFiltRefEntry 5 }

cfprApFabricEthMonLanTable OBJECT-TYPE
    SYNTAX           SEQUENCE OF CfprApFabricEthMonLanEntry
    MAX-ACCESS       not-accessible
    STATUS           current
    DESCRIPTION
        "Cisco Firepower fabric:EthMonLan managed object table"
    ::= { cfprApFabricObjects 36 }

cfprApFabricEthMonLanEntry OBJECT-TYPE
    SYNTAX           CfprApFabricEthMonLanEntry
    MAX-ACCESS       not-accessible
    STATUS           current
    DESCRIPTION
        "Entry for the cfprApFabricEthMonLanTable table."
    INDEX { cfprApFabricEthMonLanInstanceId }
    ::= { cfprApFabricEthMonLanTable 1 }

CfprApFabricEthMonLanEntry ::= SEQUENCE {
    cfprApFabricEthMonLanInstanceId                                  CfprApManagedObjectId,
    cfprApFabricEthMonLanDn                                          CfprApManagedObjectDn,
    cfprApFabricEthMonLanRn                                          SnmpAdminString,
    cfprApFabricEthMonLanId                                          CfprApNetworkSwitchId,
    cfprApFabricEthMonLanLocale                                      CfprApFabricExternalLocale,
    cfprApFabricEthMonLanName                                        SnmpAdminString,
    cfprApFabricEthMonLanTransport                                   CfprApFabricEthMonLanTransport,
    cfprApFabricEthMonLanType                                        CfprApFabricEthMonLanType
}

cfprApFabricEthMonLanInstanceId OBJECT-TYPE
    SYNTAX       CfprApManagedObjectId
    MAX-ACCESS   not-accessible
    STATUS       current
    DESCRIPTION
        "Instance identifier of the managed object."
    ::= { cfprApFabricEthMonLanEntry 1 }

cfprApFabricEthMonLanDn OBJECT-TYPE
    SYNTAX       CfprApManagedObjectDn
    MAX-ACCESS   read-only
    STATUS       current
    DESCRIPTION
        "Cisco Firepower fabric:EthMonLan:dn managed object property"
    ::= { cfprApFabricEthMonLanEntry 2 }

cfprApFabricEthMonLanRn OBJECT-TYPE
    SYNTAX       SnmpAdminString
    MAX-ACCESS   read-only
    STATUS       current
    DESCRIPTION
        "Cisco Firepower fabric:EthMonLan:rn managed object property"
    ::= { cfprApFabricEthMonLanEntry 3 }

cfprApFabricEthMonLanId OBJECT-TYPE
    SYNTAX       CfprApNetworkSwitchId
    MAX-ACCESS   read-only
    STATUS       current
    DESCRIPTION
        "Cisco Firepower fabric:EthMonLan:id managed object property"
    ::= { cfprApFabricEthMonLanEntry 4 }

cfprApFabricEthMonLanLocale OBJECT-TYPE
    SYNTAX       CfprApFabricExternalLocale
    MAX-ACCESS   read-only
    STATUS       current
    DESCRIPTION
        "Cisco Firepower fabric:EthMonLan:locale managed object property"
    ::= { cfprApFabricEthMonLanEntry 5 }

cfprApFabricEthMonLanName OBJECT-TYPE
    SYNTAX       SnmpAdminString
    MAX-ACCESS   read-only
    STATUS       current
    DESCRIPTION
        "Cisco Firepower fabric:EthMonLan:name managed object property"
    ::= { cfprApFabricEthMonLanEntry 6 }

cfprApFabricEthMonLanTransport OBJECT-TYPE
    SYNTAX       CfprApFabricEthMonLanTransport
    MAX-ACCESS   read-only
    STATUS       current
    DESCRIPTION
        "Cisco Firepower fabric:EthMonLan:transport managed
        object property"
    ::= { cfprApFabricEthMonLanEntry 7 }

cfprApFabricEthMonLanType OBJECT-TYPE
    SYNTAX       CfprApFabricEthMonLanType
    MAX-ACCESS   read-only
    STATUS       current
    DESCRIPTION
        "Cisco Firepower fabric:EthMonLan:type managed object property"
    ::= { cfprApFabricEthMonLanEntry 8 }

cfprApFabricEthMonSrcEpTable OBJECT-TYPE
    SYNTAX           SEQUENCE OF CfprApFabricEthMonSrcEpEntry
    MAX-ACCESS       not-accessible
    STATUS           current
    DESCRIPTION
        "Cisco Firepower fabric:EthMonSrcEp managed object table"
    ::= { cfprApFabricObjects 37 }

cfprApFabricEthMonSrcEpEntry OBJECT-TYPE
    SYNTAX           CfprApFabricEthMonSrcEpEntry
    MAX-ACCESS       not-accessible
    STATUS           current
    DESCRIPTION
        "Entry for the cfprApFabricEthMonSrcEpTable table."
    INDEX { cfprApFabricEthMonSrcEpInstanceId }
    ::= { cfprApFabricEthMonSrcEpTable 1 }

CfprApFabricEthMonSrcEpEntry ::= SEQUENCE {
    cfprApFabricEthMonSrcEpInstanceId                                CfprApManagedObjectId,
    cfprApFabricEthMonSrcEpDn                                        CfprApManagedObjectDn,
    cfprApFabricEthMonSrcEpRn                                        SnmpAdminString,
    cfprApFabricEthMonSrcEpDirection                                 CfprApFabricTrafficDirection,
    cfprApFabricEthMonSrcEpName                                      SnmpAdminString,
    cfprApFabricEthMonSrcEpSession                                   Gauge32,
    cfprApFabricEthMonSrcEpTransport                                 CfprApNetworkTransport,
    cfprApFabricEthMonSrcEpType                                      CfprApFabricEthMonSrcEpType
}

cfprApFabricEthMonSrcEpInstanceId OBJECT-TYPE
    SYNTAX       CfprApManagedObjectId
    MAX-ACCESS   not-accessible
    STATUS       current
    DESCRIPTION
        "Instance identifier of the managed object."
    ::= { cfprApFabricEthMonSrcEpEntry 1 }

cfprApFabricEthMonSrcEpDn OBJECT-TYPE
    SYNTAX       CfprApManagedObjectDn
    MAX-ACCESS   read-only
    STATUS       current
    DESCRIPTION
        "Cisco Firepower fabric:EthMonSrcEp:dn managed object property"
    ::= { cfprApFabricEthMonSrcEpEntry 2 }

cfprApFabricEthMonSrcEpRn OBJECT-TYPE
    SYNTAX       SnmpAdminString
    MAX-ACCESS   read-only
    STATUS       current
    DESCRIPTION
        "Cisco Firepower fabric:EthMonSrcEp:rn managed object property"
    ::= { cfprApFabricEthMonSrcEpEntry 3 }

cfprApFabricEthMonSrcEpDirection OBJECT-TYPE
    SYNTAX       CfprApFabricTrafficDirection
    MAX-ACCESS   read-only
    STATUS       current
    DESCRIPTION
        "Cisco Firepower fabric:EthMonSrcEp:direction managed
        object property"
    ::= { cfprApFabricEthMonSrcEpEntry 4 }

cfprApFabricEthMonSrcEpName OBJECT-TYPE
    SYNTAX       SnmpAdminString
    MAX-ACCESS   read-only
    STATUS       current
    DESCRIPTION
        "Cisco Firepower fabric:EthMonSrcEp:name managed object property"
    ::= { cfprApFabricEthMonSrcEpEntry 5 }

cfprApFabricEthMonSrcEpSession OBJECT-TYPE
    SYNTAX       Gauge32
    MAX-ACCESS   read-only
    STATUS       current
    DESCRIPTION
        "Cisco Firepower fabric:EthMonSrcEp:session managed
        object property"
    ::= { cfprApFabricEthMonSrcEpEntry 6 }

cfprApFabricEthMonSrcEpTransport OBJECT-TYPE
    SYNTAX       CfprApNetworkTransport
    MAX-ACCESS   read-only
    STATUS       current
    DESCRIPTION
        "Cisco Firepower fabric:EthMonSrcEp:transport managed
        object property"
    ::= { cfprApFabricEthMonSrcEpEntry 7 }

cfprApFabricEthMonSrcEpType OBJECT-TYPE
    SYNTAX       CfprApFabricEthMonSrcEpType
    MAX-ACCESS   read-only
    STATUS       current
    DESCRIPTION
        "Cisco Firepower fabric:EthMonSrcEp:type managed object property"
    ::= { cfprApFabricEthMonSrcEpEntry 8 }

cfprApFabricEthMonSrcRefTable OBJECT-TYPE
    SYNTAX           SEQUENCE OF CfprApFabricEthMonSrcRefEntry
    MAX-ACCESS       not-accessible
    STATUS           current
    DESCRIPTION
        "Cisco Firepower fabric:EthMonSrcRef managed object table"
    ::= { cfprApFabricObjects 38 }

cfprApFabricEthMonSrcRefEntry OBJECT-TYPE
    SYNTAX           CfprApFabricEthMonSrcRefEntry
    MAX-ACCESS       not-accessible
    STATUS           current
    DESCRIPTION
        "Entry for the cfprApFabricEthMonSrcRefTable table."
    INDEX { cfprApFabricEthMonSrcRefInstanceId }
    ::= { cfprApFabricEthMonSrcRefTable 1 }

CfprApFabricEthMonSrcRefEntry ::= SEQUENCE {
    cfprApFabricEthMonSrcRefInstanceId                               CfprApManagedObjectId,
    cfprApFabricEthMonSrcRefDn                                       CfprApManagedObjectDn,
    cfprApFabricEthMonSrcRefRn                                       SnmpAdminString,
    cfprApFabricEthMonSrcRefId                                       Unsigned64,
    cfprApFabricEthMonSrcRefSourceDn                                 SnmpAdminString,
    cfprApFabricEthMonSrcRefSourceType                               CfprApFabricEthSourceType,
    cfprApFabricEthMonSrcRefType                                     CfprApFabricEthMonSrcRefType
}

cfprApFabricEthMonSrcRefInstanceId OBJECT-TYPE
    SYNTAX       CfprApManagedObjectId
    MAX-ACCESS   not-accessible
    STATUS       current
    DESCRIPTION
        "Instance identifier of the managed object."
    ::= { cfprApFabricEthMonSrcRefEntry 1 }

cfprApFabricEthMonSrcRefDn OBJECT-TYPE
    SYNTAX       CfprApManagedObjectDn
    MAX-ACCESS   read-only
    STATUS       current
    DESCRIPTION
        "Cisco Firepower fabric:EthMonSrcRef:dn managed object property"
    ::= { cfprApFabricEthMonSrcRefEntry 2 }

cfprApFabricEthMonSrcRefRn OBJECT-TYPE
    SYNTAX       SnmpAdminString
    MAX-ACCESS   read-only
    STATUS       current
    DESCRIPTION
        "Cisco Firepower fabric:EthMonSrcRef:rn managed object property"
    ::= { cfprApFabricEthMonSrcRefEntry 3 }

cfprApFabricEthMonSrcRefId OBJECT-TYPE
    SYNTAX       Unsigned64
    MAX-ACCESS   read-only
    STATUS       current
    DESCRIPTION
        "Cisco Firepower fabric:EthMonSrcRef:id managed object property"
    ::= { cfprApFabricEthMonSrcRefEntry 4 }

cfprApFabricEthMonSrcRefSourceDn OBJECT-TYPE
    SYNTAX       SnmpAdminString
    MAX-ACCESS   read-only
    STATUS       current
    DESCRIPTION
        "Cisco Firepower fabric:EthMonSrcRef:sourceDn managed
        object property"
    ::= { cfprApFabricEthMonSrcRefEntry 5 }

cfprApFabricEthMonSrcRefSourceType OBJECT-TYPE
    SYNTAX       CfprApFabricEthSourceType
    MAX-ACCESS   read-only
    STATUS       current
    DESCRIPTION
        "Cisco Firepower fabric:EthMonSrcRef:sourceType
        managed object property"
    ::= { cfprApFabricEthMonSrcRefEntry 6 }

cfprApFabricEthMonSrcRefType OBJECT-TYPE
    SYNTAX       CfprApFabricEthMonSrcRefType
    MAX-ACCESS   read-only
    STATUS       current
    DESCRIPTION
        "Cisco Firepower fabric:EthMonSrcRef:type managed object property"
    ::= { cfprApFabricEthMonSrcRefEntry 7 }

cfprApFabricEthTargetEpTable OBJECT-TYPE
    SYNTAX           SEQUENCE OF CfprApFabricEthTargetEpEntry
    MAX-ACCESS       not-accessible
    STATUS           current
    DESCRIPTION
        "Cisco Firepower fabric:EthTargetEp managed object table"
    ::= { cfprApFabricObjects 39 }

cfprApFabricEthTargetEpEntry OBJECT-TYPE
    SYNTAX           CfprApFabricEthTargetEpEntry
    MAX-ACCESS       not-accessible
    STATUS           current
    DESCRIPTION
        "Entry for the cfprApFabricEthTargetEpTable table."
    INDEX { cfprApFabricEthTargetEpInstanceId }
    ::= { cfprApFabricEthTargetEpTable 1 }

CfprApFabricEthTargetEpEntry ::= SEQUENCE {
    cfprApFabricEthTargetEpInstanceId                                CfprApManagedObjectId,
    cfprApFabricEthTargetEpDn                                        CfprApManagedObjectDn,
    cfprApFabricEthTargetEpRn                                        SnmpAdminString,
    cfprApFabricEthTargetEpAdminState                                CfprApFabricExternalEpAdminState,
    cfprApFabricEthTargetEpAggrPortId                                Gauge32,
    cfprApFabricEthTargetEpChassisId                                 Gauge32,
    cfprApFabricEthTargetEpEpDn                                      SnmpAdminString,
    cfprApFabricEthTargetEpFltAggr                                   Unsigned64,
    cfprApFabricEthTargetEpIfRole                                    CfprApNetworkPortRole,
    cfprApFabricEthTargetEpIfType                                    CfprApFabricPIoEpIfType,
    cfprApFabricEthTargetEpLicGP                                     Unsigned64,
    cfprApFabricEthTargetEpLicState                                  CfprApLicenseState,
    cfprApFabricEthTargetEpLocale                                    CfprApFabricExternalEpLocale,
    cfprApFabricEthTargetEpMacAddress                                MacAddress,
    cfprApFabricEthTargetEpName                                      SnmpAdminString,
    cfprApFabricEthTargetEpOperState                                 CfprApFabricPIoEpOperState,
    cfprApFabricEthTargetEpOperStateReason                           SnmpAdminString,
    cfprApFabricEthTargetEpPeerAggrPortId                            Gauge32,
    cfprApFabricEthTargetEpPeerChassisId                             Gauge32,
    cfprApFabricEthTargetEpPeerDn                                    SnmpAdminString,
    cfprApFabricEthTargetEpPeerPortId                                Gauge32,
    cfprApFabricEthTargetEpPeerSlotId                                Gauge32,
    cfprApFabricEthTargetEpPortId                                    CfprApFabricPIoEpPortId,
    cfprApFabricEthTargetEpSlotId                                    CfprApFabricPIoEpSlotId,
    cfprApFabricEthTargetEpSwitchId                                  CfprApNetworkSwitchId,
    cfprApFabricEthTargetEpTransport                                 CfprApFabricEthTargetEpTransport,
    cfprApFabricEthTargetEpType                                      CfprApFabricTargetEpType,
    cfprApFabricEthTargetEpWarnings                                  CfprApFabricWarnings
}

cfprApFabricEthTargetEpInstanceId OBJECT-TYPE
    SYNTAX       CfprApManagedObjectId
    MAX-ACCESS   not-accessible
    STATUS       current
    DESCRIPTION
        "Instance identifier of the managed object."
    ::= { cfprApFabricEthTargetEpEntry 1 }

cfprApFabricEthTargetEpDn OBJECT-TYPE
    SYNTAX       CfprApManagedObjectDn
    MAX-ACCESS   read-only
    STATUS       current
    DESCRIPTION
        "Cisco Firepower fabric:EthTargetEp:dn managed object property"
    ::= { cfprApFabricEthTargetEpEntry 2 }

cfprApFabricEthTargetEpRn OBJECT-TYPE
    SYNTAX       SnmpAdminString
    MAX-ACCESS   read-only
    STATUS       current
    DESCRIPTION
        "Cisco Firepower fabric:EthTargetEp:rn managed object property"
    ::= { cfprApFabricEthTargetEpEntry 3 }

cfprApFabricEthTargetEpAdminState OBJECT-TYPE
    SYNTAX       CfprApFabricExternalEpAdminState
    MAX-ACCESS   read-only
    STATUS       current
    DESCRIPTION
        "Cisco Firepower fabric:EthTargetEp:adminState
        managed object property"
    ::= { cfprApFabricEthTargetEpEntry 4 }

cfprApFabricEthTargetEpAggrPortId OBJECT-TYPE
    SYNTAX       Gauge32
    MAX-ACCESS   read-only
    STATUS       current
    DESCRIPTION
        "Cisco Firepower fabric:EthTargetEp:aggrPortId
        managed object property"
    ::= { cfprApFabricEthTargetEpEntry 5 }

cfprApFabricEthTargetEpChassisId OBJECT-TYPE
    SYNTAX       Gauge32
    MAX-ACCESS   read-only
    STATUS       current
    DESCRIPTION
        "Cisco Firepower fabric:EthTargetEp:chassisId managed
        object property"
    ::= { cfprApFabricEthTargetEpEntry 6 }

cfprApFabricEthTargetEpEpDn OBJECT-TYPE
    SYNTAX       SnmpAdminString
    MAX-ACCESS   read-only
    STATUS       current
    DESCRIPTION
        "Cisco Firepower fabric:EthTargetEp:epDn managed object property"
    ::= { cfprApFabricEthTargetEpEntry 7 }

cfprApFabricEthTargetEpFltAggr OBJECT-TYPE
    SYNTAX       Unsigned64
    MAX-ACCESS   read-only
    STATUS       current
    DESCRIPTION
        "Cisco Firepower fabric:EthTargetEp:fltAggr managed
        object property"
    ::= { cfprApFabricEthTargetEpEntry 8 }

cfprApFabricEthTargetEpIfRole OBJECT-TYPE
    SYNTAX       CfprApNetworkPortRole
    MAX-ACCESS   read-only
    STATUS       current
    DESCRIPTION
        "Cisco Firepower fabric:EthTargetEp:ifRole managed
        object property"
    ::= { cfprApFabricEthTargetEpEntry 9 }

cfprApFabricEthTargetEpIfType OBJECT-TYPE
    SYNTAX       CfprApFabricPIoEpIfType
    MAX-ACCESS   read-only
    STATUS       current
    DESCRIPTION
        "Cisco Firepower fabric:EthTargetEp:ifType managed
        object property"
    ::= { cfprApFabricEthTargetEpEntry 10 }

cfprApFabricEthTargetEpLicGP OBJECT-TYPE
    SYNTAX       Unsigned64
    MAX-ACCESS   read-only
    STATUS       current
    DESCRIPTION
        "Cisco Firepower fabric:EthTargetEp:licGP managed object property"
    ::= { cfprApFabricEthTargetEpEntry 11 }

cfprApFabricEthTargetEpLicState OBJECT-TYPE
    SYNTAX       CfprApLicenseState
    MAX-ACCESS   read-only
    STATUS       current
    DESCRIPTION
        "Cisco Firepower fabric:EthTargetEp:licState managed
        object property"
    ::= { cfprApFabricEthTargetEpEntry 12 }

cfprApFabricEthTargetEpLocale OBJECT-TYPE
    SYNTAX       CfprApFabricExternalEpLocale
    MAX-ACCESS   read-only
    STATUS       current
    DESCRIPTION
        "Cisco Firepower fabric:EthTargetEp:locale managed
        object property"
    ::= { cfprApFabricEthTargetEpEntry 13 }

cfprApFabricEthTargetEpMacAddress OBJECT-TYPE
    SYNTAX       MacAddress
    MAX-ACCESS   read-only
    STATUS       current
    DESCRIPTION
        "Cisco Firepower fabric:EthTargetEp:macAddress
        managed object property"
    ::= { cfprApFabricEthTargetEpEntry 14 }

cfprApFabricEthTargetEpName OBJECT-TYPE
    SYNTAX       SnmpAdminString
    MAX-ACCESS   read-only
    STATUS       current
    DESCRIPTION
        "Cisco Firepower fabric:EthTargetEp:name managed object property"
    ::= { cfprApFabricEthTargetEpEntry 15 }

cfprApFabricEthTargetEpOperState OBJECT-TYPE
    SYNTAX       CfprApFabricPIoEpOperState
    MAX-ACCESS   read-only
    STATUS       current
    DESCRIPTION
        "Cisco Firepower fabric:EthTargetEp:operState managed
        object property"
    ::= { cfprApFabricEthTargetEpEntry 16 }

cfprApFabricEthTargetEpOperStateReason OBJECT-TYPE
    SYNTAX       SnmpAdminString
    MAX-ACCESS   read-only
    STATUS       current
    DESCRIPTION
        "Cisco Firepower fabric:EthTargetEp:operStateReason
        managed object property"
    ::= { cfprApFabricEthTargetEpEntry 17 }

cfprApFabricEthTargetEpPeerAggrPortId OBJECT-TYPE
    SYNTAX       Gauge32
    MAX-ACCESS   read-only
    STATUS       current
    DESCRIPTION
        "Cisco Firepower fabric:EthTargetEp:peerAggrPortId
        managed object property"
    ::= { cfprApFabricEthTargetEpEntry 18 }

cfprApFabricEthTargetEpPeerChassisId OBJECT-TYPE
    SYNTAX       Gauge32
    MAX-ACCESS   read-only
    STATUS       current
    DESCRIPTION
        "Cisco Firepower fabric:EthTargetEp:peerChassisId
        managed object property"
    ::= { cfprApFabricEthTargetEpEntry 19 }

cfprApFabricEthTargetEpPeerDn OBJECT-TYPE
    SYNTAX       SnmpAdminString
    MAX-ACCESS   read-only
    STATUS       current
    DESCRIPTION
        "Cisco Firepower fabric:EthTargetEp:peerDn managed
        object property"
    ::= { cfprApFabricEthTargetEpEntry 20 }

cfprApFabricEthTargetEpPeerPortId OBJECT-TYPE
    SYNTAX       Gauge32
    MAX-ACCESS   read-only
    STATUS       current
    DESCRIPTION
        "Cisco Firepower fabric:EthTargetEp:peerPortId
        managed object property"
    ::= { cfprApFabricEthTargetEpEntry 21 }

cfprApFabricEthTargetEpPeerSlotId OBJECT-TYPE
    SYNTAX       Gauge32
    MAX-ACCESS   read-only
    STATUS       current
    DESCRIPTION
        "Cisco Firepower fabric:EthTargetEp:peerSlotId
        managed object property"
    ::= { cfprApFabricEthTargetEpEntry 22 }

cfprApFabricEthTargetEpPortId OBJECT-TYPE
    SYNTAX       CfprApFabricPIoEpPortId
    MAX-ACCESS   read-only
    STATUS       current
    DESCRIPTION
        "Cisco Firepower fabric:EthTargetEp:portId managed
        object property"
    ::= { cfprApFabricEthTargetEpEntry 23 }

cfprApFabricEthTargetEpSlotId OBJECT-TYPE
    SYNTAX       CfprApFabricPIoEpSlotId
    MAX-ACCESS   read-only
    STATUS       current
    DESCRIPTION
        "Cisco Firepower fabric:EthTargetEp:slotId managed
        object property"
    ::= { cfprApFabricEthTargetEpEntry 24 }

cfprApFabricEthTargetEpSwitchId OBJECT-TYPE
    SYNTAX       CfprApNetworkSwitchId
    MAX-ACCESS   read-only
    STATUS       current
    DESCRIPTION
        "Cisco Firepower fabric:EthTargetEp:switchId managed
        object property"
    ::= { cfprApFabricEthTargetEpEntry 25 }

cfprApFabricEthTargetEpTransport OBJECT-TYPE
    SYNTAX       CfprApFabricEthTargetEpTransport
    MAX-ACCESS   read-only
    STATUS       current
    DESCRIPTION
        "Cisco Firepower fabric:EthTargetEp:transport managed
        object property"
    ::= { cfprApFabricEthTargetEpEntry 26 }

cfprApFabricEthTargetEpType OBJECT-TYPE
    SYNTAX       CfprApFabricTargetEpType
    MAX-ACCESS   read-only
    STATUS       current
    DESCRIPTION
        "Cisco Firepower fabric:EthTargetEp:type managed object property"
    ::= { cfprApFabricEthTargetEpEntry 27 }

cfprApFabricEthTargetEpWarnings OBJECT-TYPE
    SYNTAX       CfprApFabricWarnings
    MAX-ACCESS   read-only
    STATUS       current
    DESCRIPTION
        "Cisco Firepower fabric:EthTargetEp:warnings managed
        object property"
    ::= { cfprApFabricEthTargetEpEntry 28 }

cfprApFabricEthVlanPcTable OBJECT-TYPE
    SYNTAX           SEQUENCE OF CfprApFabricEthVlanPcEntry
    MAX-ACCESS       not-accessible
    STATUS           current
    DESCRIPTION
        "Cisco Firepower fabric:EthVlanPc managed object table"
    ::= { cfprApFabricObjects 40 }

cfprApFabricEthVlanPcEntry OBJECT-TYPE
    SYNTAX           CfprApFabricEthVlanPcEntry
    MAX-ACCESS       not-accessible
    STATUS           current
    DESCRIPTION
        "Entry for the cfprApFabricEthVlanPcTable table."
    INDEX { cfprApFabricEthVlanPcInstanceId }
    ::= { cfprApFabricEthVlanPcTable 1 }

CfprApFabricEthVlanPcEntry ::= SEQUENCE {
    cfprApFabricEthVlanPcInstanceId                                  CfprApManagedObjectId,
    cfprApFabricEthVlanPcDn                                          CfprApManagedObjectDn,
    cfprApFabricEthVlanPcRn                                          SnmpAdminString,
    cfprApFabricEthVlanPcAdminSpeed                                  CfprApPortEthAdminSpeed,
    cfprApFabricEthVlanPcAdminState                                  CfprApFabricCIoEpAdminState,
    cfprApFabricEthVlanPcDescr                                       SnmpAdminString,
    cfprApFabricEthVlanPcEpDn                                        SnmpAdminString,
    cfprApFabricEthVlanPcFltAggr                                     Unsigned64,
    cfprApFabricEthVlanPcIfRole                                      CfprApFabricEstcPcIfRole,
    cfprApFabricEthVlanPcIfType                                      CfprApFabricCIoEpIfType,
    cfprApFabricEthVlanPcIsNative                                    TruthValue,
    cfprApFabricEthVlanPcLocale                                      CfprApFabricExternalPcLocale,
    cfprApFabricEthVlanPcName                                        SnmpAdminString,
    cfprApFabricEthVlanPcOperSpeed                                   CfprApPortEthSpeed,
    cfprApFabricEthVlanPcOperState                                   CfprApNetworkPortOperState,
    cfprApFabricEthVlanPcPeerDn                                      SnmpAdminString,
    cfprApFabricEthVlanPcPortId                                      Gauge32,
    cfprApFabricEthVlanPcStateQual                                   SnmpAdminString,
    cfprApFabricEthVlanPcSwitchId                                    CfprApNetworkSwitchId,
    cfprApFabricEthVlanPcTransport                                   CfprApFabricEthVlanPcTransport,
    cfprApFabricEthVlanPcType                                        CfprApFabricEstcPcType,
    cfprApFabricEthVlanPcWarnings                                    CfprApFabricWarnings
}

cfprApFabricEthVlanPcInstanceId OBJECT-TYPE
    SYNTAX       CfprApManagedObjectId
    MAX-ACCESS   not-accessible
    STATUS       current
    DESCRIPTION
        "Instance identifier of the managed object."
    ::= { cfprApFabricEthVlanPcEntry 1 }

cfprApFabricEthVlanPcDn OBJECT-TYPE
    SYNTAX       CfprApManagedObjectDn
    MAX-ACCESS   read-only
    STATUS       current
    DESCRIPTION
        "Cisco Firepower fabric:EthVlanPc:dn managed object property"
    ::= { cfprApFabricEthVlanPcEntry 2 }

cfprApFabricEthVlanPcRn OBJECT-TYPE
    SYNTAX       SnmpAdminString
    MAX-ACCESS   read-only
    STATUS       current
    DESCRIPTION
        "Cisco Firepower fabric:EthVlanPc:rn managed object property"
    ::= { cfprApFabricEthVlanPcEntry 3 }

cfprApFabricEthVlanPcAdminSpeed OBJECT-TYPE
    SYNTAX       CfprApPortEthAdminSpeed
    MAX-ACCESS   read-only
    STATUS       current
    DESCRIPTION
        "Cisco Firepower fabric:EthVlanPc:adminSpeed managed
        object property"
    ::= { cfprApFabricEthVlanPcEntry 4 }

cfprApFabricEthVlanPcAdminState OBJECT-TYPE
    SYNTAX       CfprApFabricCIoEpAdminState
    MAX-ACCESS   read-only
    STATUS       current
    DESCRIPTION
        "Cisco Firepower fabric:EthVlanPc:adminState managed
        object property"
    ::= { cfprApFabricEthVlanPcEntry 5 }

cfprApFabricEthVlanPcDescr OBJECT-TYPE
    SYNTAX       SnmpAdminString
    MAX-ACCESS   read-only
    STATUS       current
    DESCRIPTION
        "Cisco Firepower fabric:EthVlanPc:descr managed object property"
    ::= { cfprApFabricEthVlanPcEntry 6 }

cfprApFabricEthVlanPcEpDn OBJECT-TYPE
    SYNTAX       SnmpAdminString
    MAX-ACCESS   read-only
    STATUS       current
    DESCRIPTION
        "Cisco Firepower fabric:EthVlanPc:epDn managed object property"
    ::= { cfprApFabricEthVlanPcEntry 7 }

cfprApFabricEthVlanPcFltAggr OBJECT-TYPE
    SYNTAX       Unsigned64
    MAX-ACCESS   read-only
    STATUS       current
    DESCRIPTION
        "Cisco Firepower fabric:EthVlanPc:fltAggr managed object property"
    ::= { cfprApFabricEthVlanPcEntry 8 }

cfprApFabricEthVlanPcIfRole OBJECT-TYPE
    SYNTAX       CfprApFabricEstcPcIfRole
    MAX-ACCESS   read-only
    STATUS       current
    DESCRIPTION
        "Cisco Firepower fabric:EthVlanPc:ifRole managed object property"
    ::= { cfprApFabricEthVlanPcEntry 9 }

cfprApFabricEthVlanPcIfType OBJECT-TYPE
    SYNTAX       CfprApFabricCIoEpIfType
    MAX-ACCESS   read-only
    STATUS       current
    DESCRIPTION
        "Cisco Firepower fabric:EthVlanPc:ifType managed object property"
    ::= { cfprApFabricEthVlanPcEntry 10 }

cfprApFabricEthVlanPcIsNative OBJECT-TYPE
    SYNTAX       TruthValue
    MAX-ACCESS   read-only
    STATUS       current
    DESCRIPTION
        "Cisco Firepower fabric:EthVlanPc:isNative managed
        object property"
    ::= { cfprApFabricEthVlanPcEntry 11 }

cfprApFabricEthVlanPcLocale OBJECT-TYPE
    SYNTAX       CfprApFabricExternalPcLocale
    MAX-ACCESS   read-only
    STATUS       current
    DESCRIPTION
        "Cisco Firepower fabric:EthVlanPc:locale managed object property"
    ::= { cfprApFabricEthVlanPcEntry 12 }

cfprApFabricEthVlanPcName OBJECT-TYPE
    SYNTAX       SnmpAdminString
    MAX-ACCESS   read-only
    STATUS       current
    DESCRIPTION
        "Cisco Firepower fabric:EthVlanPc:name managed object property"
    ::= { cfprApFabricEthVlanPcEntry 13 }

cfprApFabricEthVlanPcOperSpeed OBJECT-TYPE
    SYNTAX       CfprApPortEthSpeed
    MAX-ACCESS   read-only
    STATUS       current
    DESCRIPTION
        "Cisco Firepower fabric:EthVlanPc:operSpeed managed
        object property"
    ::= { cfprApFabricEthVlanPcEntry 14 }

cfprApFabricEthVlanPcOperState OBJECT-TYPE
    SYNTAX       CfprApNetworkPortOperState
    MAX-ACCESS   read-only
    STATUS       current
    DESCRIPTION
        "Cisco Firepower fabric:EthVlanPc:operState managed
        object property"
    ::= { cfprApFabricEthVlanPcEntry 15 }

cfprApFabricEthVlanPcPeerDn OBJECT-TYPE
    SYNTAX       SnmpAdminString
    MAX-ACCESS   read-only
    STATUS       current
    DESCRIPTION
        "Cisco Firepower fabric:EthVlanPc:peerDn managed object property"
    ::= { cfprApFabricEthVlanPcEntry 16 }

cfprApFabricEthVlanPcPortId OBJECT-TYPE
    SYNTAX       Gauge32
    MAX-ACCESS   read-only
    STATUS       current
    DESCRIPTION
        "Cisco Firepower fabric:EthVlanPc:portId managed object property"
    ::= { cfprApFabricEthVlanPcEntry 17 }

cfprApFabricEthVlanPcStateQual OBJECT-TYPE
    SYNTAX       SnmpAdminString
    MAX-ACCESS   read-only
    STATUS       current
    DESCRIPTION
        "Cisco Firepower fabric:EthVlanPc:stateQual managed
        object property"
    ::= { cfprApFabricEthVlanPcEntry 18 }

cfprApFabricEthVlanPcSwitchId OBJECT-TYPE
    SYNTAX       CfprApNetworkSwitchId
    MAX-ACCESS   read-only
    STATUS       current
    DESCRIPTION
        "Cisco Firepower fabric:EthVlanPc:switchId managed
        object property"
    ::= { cfprApFabricEthVlanPcEntry 19 }

cfprApFabricEthVlanPcTransport OBJECT-TYPE
    SYNTAX       CfprApFabricEthVlanPcTransport
    MAX-ACCESS   read-only
    STATUS       current
    DESCRIPTION
        "Cisco Firepower fabric:EthVlanPc:transport managed
        object property"
    ::= { cfprApFabricEthVlanPcEntry 20 }

cfprApFabricEthVlanPcType OBJECT-TYPE
    SYNTAX       CfprApFabricEstcPcType
    MAX-ACCESS   read-only
    STATUS       current
    DESCRIPTION
        "Cisco Firepower fabric:EthVlanPc:type managed object property"
    ::= { cfprApFabricEthVlanPcEntry 21 }

cfprApFabricEthVlanPcWarnings OBJECT-TYPE
    SYNTAX       CfprApFabricWarnings
    MAX-ACCESS   read-only
    STATUS       current
    DESCRIPTION
        "Cisco Firepower fabric:EthVlanPc:warnings managed
        object property"
    ::= { cfprApFabricEthVlanPcEntry 22 }

cfprApFabricEthVlanPortEpTable OBJECT-TYPE
    SYNTAX           SEQUENCE OF CfprApFabricEthVlanPortEpEntry
    MAX-ACCESS       not-accessible
    STATUS           current
    DESCRIPTION
        "Cisco Firepower fabric:EthVlanPortEp managed object table"
    ::= { cfprApFabricObjects 41 }

cfprApFabricEthVlanPortEpEntry OBJECT-TYPE
    SYNTAX           CfprApFabricEthVlanPortEpEntry
    MAX-ACCESS       not-accessible
    STATUS           current
    DESCRIPTION
        "Entry for the cfprApFabricEthVlanPortEpTable table."
    INDEX { cfprApFabricEthVlanPortEpInstanceId }
    ::= { cfprApFabricEthVlanPortEpTable 1 }

CfprApFabricEthVlanPortEpEntry ::= SEQUENCE {
    cfprApFabricEthVlanPortEpInstanceId                              CfprApManagedObjectId,
    cfprApFabricEthVlanPortEpDn                                      CfprApManagedObjectDn,
    cfprApFabricEthVlanPortEpRn                                      SnmpAdminString,
    cfprApFabricEthVlanPortEpAdminState                              CfprApFabricExternalEpAdminState,
    cfprApFabricEthVlanPortEpAggrPortId                              Gauge32,
    cfprApFabricEthVlanPortEpChassisId                               Gauge32,
    cfprApFabricEthVlanPortEpEpDn                                    SnmpAdminString,
    cfprApFabricEthVlanPortEpFltAggr                                 Unsigned64,
    cfprApFabricEthVlanPortEpIfRole                                  CfprApFabricLanEpIfRole,
    cfprApFabricEthVlanPortEpIfType                                  CfprApFabricPIoEpIfType,
    cfprApFabricEthVlanPortEpIsNative                                TruthValue,
    cfprApFabricEthVlanPortEpLicGP                                   Unsigned64,
    cfprApFabricEthVlanPortEpLicState                                CfprApLicenseState,
    cfprApFabricEthVlanPortEpLocale                                  CfprApFabricExternalEpLocale,
    cfprApFabricEthVlanPortEpName                                    SnmpAdminString,
    cfprApFabricEthVlanPortEpOperState                               CfprApFabricPIoEpOperState,
    cfprApFabricEthVlanPortEpOperStateReason                         SnmpAdminString,
    cfprApFabricEthVlanPortEpPeerAggrPortId                          Gauge32,
    cfprApFabricEthVlanPortEpPeerChassisId                           Gauge32,
    cfprApFabricEthVlanPortEpPeerDn                                  SnmpAdminString,
    cfprApFabricEthVlanPortEpPeerPortId                              Gauge32,
    cfprApFabricEthVlanPortEpPeerSlotId                              Gauge32,
    cfprApFabricEthVlanPortEpPortId                                  Gauge32,
    cfprApFabricEthVlanPortEpSlotId                                  Gauge32,
    cfprApFabricEthVlanPortEpSwitchId                                CfprApNetworkSwitchId,
    cfprApFabricEthVlanPortEpTransport                               CfprApFabricAEthLanEpTransport,
    cfprApFabricEthVlanPortEpType                                    CfprApFabricLanEpType,
    cfprApFabricEthVlanPortEpWarnings                                CfprApFabricWarnings
}

cfprApFabricEthVlanPortEpInstanceId OBJECT-TYPE
    SYNTAX       CfprApManagedObjectId
    MAX-ACCESS   not-accessible
    STATUS       current
    DESCRIPTION
        "Instance identifier of the managed object."
    ::= { cfprApFabricEthVlanPortEpEntry 1 }

cfprApFabricEthVlanPortEpDn OBJECT-TYPE
    SYNTAX       CfprApManagedObjectDn
    MAX-ACCESS   read-only
    STATUS       current
    DESCRIPTION
        "Cisco Firepower fabric:EthVlanPortEp:dn managed object property"
    ::= { cfprApFabricEthVlanPortEpEntry 2 }

cfprApFabricEthVlanPortEpRn OBJECT-TYPE
    SYNTAX       SnmpAdminString
    MAX-ACCESS   read-only
    STATUS       current
    DESCRIPTION
        "Cisco Firepower fabric:EthVlanPortEp:rn managed object property"
    ::= { cfprApFabricEthVlanPortEpEntry 3 }

cfprApFabricEthVlanPortEpAdminState OBJECT-TYPE
    SYNTAX       CfprApFabricExternalEpAdminState
    MAX-ACCESS   read-only
    STATUS       current
    DESCRIPTION
        "Cisco Firepower fabric:EthVlanPortEp:adminState
        managed object property"
    ::= { cfprApFabricEthVlanPortEpEntry 4 }

cfprApFabricEthVlanPortEpAggrPortId OBJECT-TYPE
    SYNTAX       Gauge32
    MAX-ACCESS   read-only
    STATUS       current
    DESCRIPTION
        "Cisco Firepower fabric:EthVlanPortEp:aggrPortId
        managed object property"
    ::= { cfprApFabricEthVlanPortEpEntry 5 }

cfprApFabricEthVlanPortEpChassisId OBJECT-TYPE
    SYNTAX       Gauge32
    MAX-ACCESS   read-only
    STATUS       current
    DESCRIPTION
        "Cisco Firepower fabric:EthVlanPortEp:chassisId
        managed object property"
    ::= { cfprApFabricEthVlanPortEpEntry 6 }

cfprApFabricEthVlanPortEpEpDn OBJECT-TYPE
    SYNTAX       SnmpAdminString
    MAX-ACCESS   read-only
    STATUS       current
    DESCRIPTION
        "Cisco Firepower fabric:EthVlanPortEp:epDn managed
        object property"
    ::= { cfprApFabricEthVlanPortEpEntry 7 }

cfprApFabricEthVlanPortEpFltAggr OBJECT-TYPE
    SYNTAX       Unsigned64
    MAX-ACCESS   read-only
    STATUS       current
    DESCRIPTION
        "Cisco Firepower fabric:EthVlanPortEp:fltAggr managed
        object property"
    ::= { cfprApFabricEthVlanPortEpEntry 8 }

cfprApFabricEthVlanPortEpIfRole OBJECT-TYPE
    SYNTAX       CfprApFabricLanEpIfRole
    MAX-ACCESS   read-only
    STATUS       current
    DESCRIPTION
        "Cisco Firepower fabric:EthVlanPortEp:ifRole managed
        object property"
    ::= { cfprApFabricEthVlanPortEpEntry 9 }

cfprApFabricEthVlanPortEpIfType OBJECT-TYPE
    SYNTAX       CfprApFabricPIoEpIfType
    MAX-ACCESS   read-only
    STATUS       current
    DESCRIPTION
        "Cisco Firepower fabric:EthVlanPortEp:ifType managed
        object property"
    ::= { cfprApFabricEthVlanPortEpEntry 10 }

cfprApFabricEthVlanPortEpIsNative OBJECT-TYPE
    SYNTAX       TruthValue
    MAX-ACCESS   read-only
    STATUS       current
    DESCRIPTION
        "Cisco Firepower fabric:EthVlanPortEp:isNative
        managed object property"
    ::= { cfprApFabricEthVlanPortEpEntry 11 }

cfprApFabricEthVlanPortEpLicGP OBJECT-TYPE
    SYNTAX       Unsigned64
    MAX-ACCESS   read-only
    STATUS       current
    DESCRIPTION
        "Cisco Firepower fabric:EthVlanPortEp:licGP managed
        object property"
    ::= { cfprApFabricEthVlanPortEpEntry 12 }

cfprApFabricEthVlanPortEpLicState OBJECT-TYPE
    SYNTAX       CfprApLicenseState
    MAX-ACCESS   read-only
    STATUS       current
    DESCRIPTION
        "Cisco Firepower fabric:EthVlanPortEp:licState
        managed object property"
    ::= { cfprApFabricEthVlanPortEpEntry 13 }

cfprApFabricEthVlanPortEpLocale OBJECT-TYPE
    SYNTAX       CfprApFabricExternalEpLocale
    MAX-ACCESS   read-only
    STATUS       current
    DESCRIPTION
        "Cisco Firepower fabric:EthVlanPortEp:locale managed
        object property"
    ::= { cfprApFabricEthVlanPortEpEntry 14 }

cfprApFabricEthVlanPortEpName OBJECT-TYPE
    SYNTAX       SnmpAdminString
    MAX-ACCESS   read-only
    STATUS       current
    DESCRIPTION
        "Cisco Firepower fabric:EthVlanPortEp:name managed
        object property"
    ::= { cfprApFabricEthVlanPortEpEntry 15 }

cfprApFabricEthVlanPortEpOperState OBJECT-TYPE
    SYNTAX       CfprApFabricPIoEpOperState
    MAX-ACCESS   read-only
    STATUS       current
    DESCRIPTION
        "Cisco Firepower fabric:EthVlanPortEp:operState
        managed object property"
    ::= { cfprApFabricEthVlanPortEpEntry 16 }

cfprApFabricEthVlanPortEpOperStateReason OBJECT-TYPE
    SYNTAX       SnmpAdminString
    MAX-ACCESS   read-only
    STATUS       current
    DESCRIPTION
        "Cisco Firepower fabric:EthVlanPortEp:operStateReason
        managed object property"
    ::= { cfprApFabricEthVlanPortEpEntry 17 }

cfprApFabricEthVlanPortEpPeerAggrPortId OBJECT-TYPE
    SYNTAX       Gauge32
    MAX-ACCESS   read-only
    STATUS       current
    DESCRIPTION
        "Cisco Firepower fabric:EthVlanPortEp:peerAggrPortId
        managed object property"
    ::= { cfprApFabricEthVlanPortEpEntry 18 }

cfprApFabricEthVlanPortEpPeerChassisId OBJECT-TYPE
    SYNTAX       Gauge32
    MAX-ACCESS   read-only
    STATUS       current
    DESCRIPTION
        "Cisco Firepower fabric:EthVlanPortEp:peerChassisId
        managed object property"
    ::= { cfprApFabricEthVlanPortEpEntry 19 }

cfprApFabricEthVlanPortEpPeerDn OBJECT-TYPE
    SYNTAX       SnmpAdminString
    MAX-ACCESS   read-only
    STATUS       current
    DESCRIPTION
        "Cisco Firepower fabric:EthVlanPortEp:peerDn managed
        object property"
    ::= { cfprApFabricEthVlanPortEpEntry 20 }

cfprApFabricEthVlanPortEpPeerPortId OBJECT-TYPE
    SYNTAX       Gauge32
    MAX-ACCESS   read-only
    STATUS       current
    DESCRIPTION
        "Cisco Firepower fabric:EthVlanPortEp:peerPortId
        managed object property"
    ::= { cfprApFabricEthVlanPortEpEntry 21 }

cfprApFabricEthVlanPortEpPeerSlotId OBJECT-TYPE
    SYNTAX       Gauge32
    MAX-ACCESS   read-only
    STATUS       current
    DESCRIPTION
        "Cisco Firepower fabric:EthVlanPortEp:peerSlotId
        managed object property"
    ::= { cfprApFabricEthVlanPortEpEntry 22 }

cfprApFabricEthVlanPortEpPortId OBJECT-TYPE
    SYNTAX       Gauge32
    MAX-ACCESS   read-only
    STATUS       current
    DESCRIPTION
        "Cisco Firepower fabric:EthVlanPortEp:portId managed
        object property"
    ::= { cfprApFabricEthVlanPortEpEntry 23 }

cfprApFabricEthVlanPortEpSlotId OBJECT-TYPE
    SYNTAX       Gauge32
    MAX-ACCESS   read-only
    STATUS       current
    DESCRIPTION
        "Cisco Firepower fabric:EthVlanPortEp:slotId managed
        object property"
    ::= { cfprApFabricEthVlanPortEpEntry 24 }

cfprApFabricEthVlanPortEpSwitchId OBJECT-TYPE
    SYNTAX       CfprApNetworkSwitchId
    MAX-ACCESS   read-only
    STATUS       current
    DESCRIPTION
        "Cisco Firepower fabric:EthVlanPortEp:switchId
        managed object property"
    ::= { cfprApFabricEthVlanPortEpEntry 25 }

cfprApFabricEthVlanPortEpTransport OBJECT-TYPE
    SYNTAX       CfprApFabricAEthLanEpTransport
    MAX-ACCESS   read-only
    STATUS       current
    DESCRIPTION
        "Cisco Firepower fabric:EthVlanPortEp:transport
        managed object property"
    ::= { cfprApFabricEthVlanPortEpEntry 26 }

cfprApFabricEthVlanPortEpType OBJECT-TYPE
    SYNTAX       CfprApFabricLanEpType
    MAX-ACCESS   read-only
    STATUS       current
    DESCRIPTION
        "Cisco Firepower fabric:EthVlanPortEp:type managed
        object property"
    ::= { cfprApFabricEthVlanPortEpEntry 27 }

cfprApFabricEthVlanPortEpWarnings OBJECT-TYPE
    SYNTAX       CfprApFabricWarnings
    MAX-ACCESS   read-only
    STATUS       current
    DESCRIPTION
        "Cisco Firepower fabric:EthVlanPortEp:warnings
        managed object property"
    ::= { cfprApFabricEthVlanPortEpEntry 28 }

cfprApFabricFcSanTable OBJECT-TYPE
    SYNTAX           SEQUENCE OF CfprApFabricFcSanEntry
    MAX-ACCESS       not-accessible
    STATUS           current
    DESCRIPTION
        "Cisco Firepower fabric:FcSan managed object table"
    ::= { cfprApFabricObjects 52 }

cfprApFabricFcSanEntry OBJECT-TYPE
    SYNTAX           CfprApFabricFcSanEntry
    MAX-ACCESS       not-accessible
    STATUS           current
    DESCRIPTION
        "Entry for the cfprApFabricFcSanTable table."
    INDEX { cfprApFabricFcSanInstanceId }
    ::= { cfprApFabricFcSanTable 1 }

CfprApFabricFcSanEntry ::= SEQUENCE {
    cfprApFabricFcSanInstanceId                                      CfprApManagedObjectId,
    cfprApFabricFcSanDn                                              CfprApManagedObjectDn,
    cfprApFabricFcSanRn                                              SnmpAdminString,
    cfprApFabricFcSanId                                              CfprApNetworkSwitchId,
    cfprApFabricFcSanLocale                                          CfprApFabricExternalLocale,
    cfprApFabricFcSanName                                            SnmpAdminString,
    cfprApFabricFcSanTransport                                       CfprApFabricFcSanTransport,
    cfprApFabricFcSanType                                            CfprApFabricSanType,
    cfprApFabricFcSanUplinkTrunking                                  CfprApFabricFcSanUplinkTrunking
}

cfprApFabricFcSanInstanceId OBJECT-TYPE
    SYNTAX       CfprApManagedObjectId
    MAX-ACCESS   not-accessible
    STATUS       current
    DESCRIPTION
        "Instance identifier of the managed object."
    ::= { cfprApFabricFcSanEntry 1 }

cfprApFabricFcSanDn OBJECT-TYPE
    SYNTAX       CfprApManagedObjectDn
    MAX-ACCESS   read-only
    STATUS       current
    DESCRIPTION
        "Cisco Firepower fabric:FcSan:dn managed object property"
    ::= { cfprApFabricFcSanEntry 2 }

cfprApFabricFcSanRn OBJECT-TYPE
    SYNTAX       SnmpAdminString
    MAX-ACCESS   read-only
    STATUS       current
    DESCRIPTION
        "Cisco Firepower fabric:FcSan:rn managed object property"
    ::= { cfprApFabricFcSanEntry 3 }

cfprApFabricFcSanId OBJECT-TYPE
    SYNTAX       CfprApNetworkSwitchId
    MAX-ACCESS   read-only
    STATUS       current
    DESCRIPTION
        "Cisco Firepower fabric:FcSan:id managed object property"
    ::= { cfprApFabricFcSanEntry 4 }

cfprApFabricFcSanLocale OBJECT-TYPE
    SYNTAX       CfprApFabricExternalLocale
    MAX-ACCESS   read-only
    STATUS       current
    DESCRIPTION
        "Cisco Firepower fabric:FcSan:locale managed object property"
    ::= { cfprApFabricFcSanEntry 5 }

cfprApFabricFcSanName OBJECT-TYPE
    SYNTAX       SnmpAdminString
    MAX-ACCESS   read-only
    STATUS       current
    DESCRIPTION
        "Cisco Firepower fabric:FcSan:name managed object property"
    ::= { cfprApFabricFcSanEntry 6 }

cfprApFabricFcSanTransport OBJECT-TYPE
    SYNTAX       CfprApFabricFcSanTransport
    MAX-ACCESS   read-only
    STATUS       current
    DESCRIPTION
        "Cisco Firepower fabric:FcSan:transport managed object property"
    ::= { cfprApFabricFcSanEntry 7 }

cfprApFabricFcSanType OBJECT-TYPE
    SYNTAX       CfprApFabricSanType
    MAX-ACCESS   read-only
    STATUS       current
    DESCRIPTION
        "Cisco Firepower fabric:FcSan:type managed object property"
    ::= { cfprApFabricFcSanEntry 8 }

cfprApFabricFcSanUplinkTrunking OBJECT-TYPE
    SYNTAX       CfprApFabricFcSanUplinkTrunking
    MAX-ACCESS   read-only
    STATUS       current
    DESCRIPTION
        "Cisco Firepower fabric:FcSan:uplinkTrunking managed
        object property"
    ::= { cfprApFabricFcSanEntry 9 }

cfprApFabricFcSanEpTable OBJECT-TYPE
    SYNTAX           SEQUENCE OF CfprApFabricFcSanEpEntry
    MAX-ACCESS       not-accessible
    STATUS           current
    DESCRIPTION
        "Cisco Firepower fabric:FcSanEp managed object table"
    ::= { cfprApFabricObjects 53 }

cfprApFabricFcSanEpEntry OBJECT-TYPE
    SYNTAX           CfprApFabricFcSanEpEntry
    MAX-ACCESS       not-accessible
    STATUS           current
    DESCRIPTION
        "Entry for the cfprApFabricFcSanEpTable table."
    INDEX { cfprApFabricFcSanEpInstanceId }
    ::= { cfprApFabricFcSanEpTable 1 }

CfprApFabricFcSanEpEntry ::= SEQUENCE {
    cfprApFabricFcSanEpInstanceId                                    CfprApManagedObjectId,
    cfprApFabricFcSanEpDn                                            CfprApManagedObjectDn,
    cfprApFabricFcSanEpRn                                            SnmpAdminString,
    cfprApFabricFcSanEpAdminState                                    CfprApFabricExternalEpAdminState,
    cfprApFabricFcSanEpAggrPortId                                    Gauge32,
    cfprApFabricFcSanEpChassisId                                     Gauge32,
    cfprApFabricFcSanEpEpDn                                          SnmpAdminString,
    cfprApFabricFcSanEpFillPattern                                   CfprApFabricFillPattern,
    cfprApFabricFcSanEpFltAggr                                       Unsigned64,
    cfprApFabricFcSanEpIfRole                                        CfprApFabricSanEpIfRole,
    cfprApFabricFcSanEpIfType                                        CfprApFabricPIoEpIfType,
    cfprApFabricFcSanEpLicGP                                         Unsigned64,
    cfprApFabricFcSanEpLicState                                      CfprApLicenseState,
    cfprApFabricFcSanEpLocale                                        CfprApFabricExternalEpLocale,
    cfprApFabricFcSanEpName                                          SnmpAdminString,
    cfprApFabricFcSanEpOperState                                     CfprApFabricPIoEpOperState,
    cfprApFabricFcSanEpOperStateReason                               SnmpAdminString,
    cfprApFabricFcSanEpPeerAggrPortId                                Gauge32,
    cfprApFabricFcSanEpPeerChassisId                                 Gauge32,
    cfprApFabricFcSanEpPeerDn                                        SnmpAdminString,
    cfprApFabricFcSanEpPeerPortId                                    Gauge32,
    cfprApFabricFcSanEpPeerSlotId                                    Gauge32,
    cfprApFabricFcSanEpPortId                                        CfprApFabricFcSanEpPortId,
    cfprApFabricFcSanEpSlotId                                        CfprApFabricFcSanEpSlotId,
    cfprApFabricFcSanEpSwitchId                                      CfprApNetworkSwitchId,
    cfprApFabricFcSanEpTransport                                     CfprApFabricAFcSanEpTransport,
    cfprApFabricFcSanEpType                                          CfprApFabricSanEpType,
    cfprApFabricFcSanEpUsrLbl                                        SnmpAdminString,
    cfprApFabricFcSanEpWarnings                                      CfprApFabricWarnings
}

cfprApFabricFcSanEpInstanceId OBJECT-TYPE
    SYNTAX       CfprApManagedObjectId
    MAX-ACCESS   not-accessible
    STATUS       current
    DESCRIPTION
        "Instance identifier of the managed object."
    ::= { cfprApFabricFcSanEpEntry 1 }

cfprApFabricFcSanEpDn OBJECT-TYPE
    SYNTAX       CfprApManagedObjectDn
    MAX-ACCESS   read-only
    STATUS       current
    DESCRIPTION
        "Cisco Firepower fabric:FcSanEp:dn managed object property"
    ::= { cfprApFabricFcSanEpEntry 2 }

cfprApFabricFcSanEpRn OBJECT-TYPE
    SYNTAX       SnmpAdminString
    MAX-ACCESS   read-only
    STATUS       current
    DESCRIPTION
        "Cisco Firepower fabric:FcSanEp:rn managed object property"
    ::= { cfprApFabricFcSanEpEntry 3 }

cfprApFabricFcSanEpAdminState OBJECT-TYPE
    SYNTAX       CfprApFabricExternalEpAdminState
    MAX-ACCESS   read-only
    STATUS       current
    DESCRIPTION
        "Cisco Firepower fabric:FcSanEp:adminState managed
        object property"
    ::= { cfprApFabricFcSanEpEntry 4 }

cfprApFabricFcSanEpAggrPortId OBJECT-TYPE
    SYNTAX       Gauge32
    MAX-ACCESS   read-only
    STATUS       current
    DESCRIPTION
        "Cisco Firepower fabric:FcSanEp:aggrPortId managed
        object property"
    ::= { cfprApFabricFcSanEpEntry 5 }

cfprApFabricFcSanEpChassisId OBJECT-TYPE
    SYNTAX       Gauge32
    MAX-ACCESS   read-only
    STATUS       current
    DESCRIPTION
        "Cisco Firepower fabric:FcSanEp:chassisId managed object property"
    ::= { cfprApFabricFcSanEpEntry 6 }

cfprApFabricFcSanEpEpDn OBJECT-TYPE
    SYNTAX       SnmpAdminString
    MAX-ACCESS   read-only
    STATUS       current
    DESCRIPTION
        "Cisco Firepower fabric:FcSanEp:epDn managed object property"
    ::= { cfprApFabricFcSanEpEntry 7 }

cfprApFabricFcSanEpFillPattern OBJECT-TYPE
    SYNTAX       CfprApFabricFillPattern
    MAX-ACCESS   read-only
    STATUS       current
    DESCRIPTION
        "Cisco Firepower fabric:FcSanEp:fillPattern managed
        object property"
    ::= { cfprApFabricFcSanEpEntry 8 }

cfprApFabricFcSanEpFltAggr OBJECT-TYPE
    SYNTAX       Unsigned64
    MAX-ACCESS   read-only
    STATUS       current
    DESCRIPTION
        "Cisco Firepower fabric:FcSanEp:fltAggr managed object property"
    ::= { cfprApFabricFcSanEpEntry 9 }

cfprApFabricFcSanEpIfRole OBJECT-TYPE
    SYNTAX       CfprApFabricSanEpIfRole
    MAX-ACCESS   read-only
    STATUS       current
    DESCRIPTION
        "Cisco Firepower fabric:FcSanEp:ifRole managed object property"
    ::= { cfprApFabricFcSanEpEntry 10 }

cfprApFabricFcSanEpIfType OBJECT-TYPE
    SYNTAX       CfprApFabricPIoEpIfType
    MAX-ACCESS   read-only
    STATUS       current
    DESCRIPTION
        "Cisco Firepower fabric:FcSanEp:ifType managed object property"
    ::= { cfprApFabricFcSanEpEntry 11 }

cfprApFabricFcSanEpLicGP OBJECT-TYPE
    SYNTAX       Unsigned64
    MAX-ACCESS   read-only
    STATUS       current
    DESCRIPTION
        "Cisco Firepower fabric:FcSanEp:licGP managed object property"
    ::= { cfprApFabricFcSanEpEntry 12 }

cfprApFabricFcSanEpLicState OBJECT-TYPE
    SYNTAX       CfprApLicenseState
    MAX-ACCESS   read-only
    STATUS       current
    DESCRIPTION
        "Cisco Firepower fabric:FcSanEp:licState managed object property"
    ::= { cfprApFabricFcSanEpEntry 13 }

cfprApFabricFcSanEpLocale OBJECT-TYPE
    SYNTAX       CfprApFabricExternalEpLocale
    MAX-ACCESS   read-only
    STATUS       current
    DESCRIPTION
        "Cisco Firepower fabric:FcSanEp:locale managed object property"
    ::= { cfprApFabricFcSanEpEntry 14 }

cfprApFabricFcSanEpName OBJECT-TYPE
    SYNTAX       SnmpAdminString
    MAX-ACCESS   read-only
    STATUS       current
    DESCRIPTION
        "Cisco Firepower fabric:FcSanEp:name managed object property"
    ::= { cfprApFabricFcSanEpEntry 15 }

cfprApFabricFcSanEpOperState OBJECT-TYPE
    SYNTAX       CfprApFabricPIoEpOperState
    MAX-ACCESS   read-only
    STATUS       current
    DESCRIPTION
        "Cisco Firepower fabric:FcSanEp:operState managed object property"
    ::= { cfprApFabricFcSanEpEntry 16 }

cfprApFabricFcSanEpOperStateReason OBJECT-TYPE
    SYNTAX       SnmpAdminString
    MAX-ACCESS   read-only
    STATUS       current
    DESCRIPTION
        "Cisco Firepower fabric:FcSanEp:operStateReason
        managed object property"
    ::= { cfprApFabricFcSanEpEntry 17 }

cfprApFabricFcSanEpPeerAggrPortId OBJECT-TYPE
    SYNTAX       Gauge32
    MAX-ACCESS   read-only
    STATUS       current
    DESCRIPTION
        "Cisco Firepower fabric:FcSanEp:peerAggrPortId
        managed object property"
    ::= { cfprApFabricFcSanEpEntry 18 }

cfprApFabricFcSanEpPeerChassisId OBJECT-TYPE
    SYNTAX       Gauge32
    MAX-ACCESS   read-only
    STATUS       current
    DESCRIPTION
        "Cisco Firepower fabric:FcSanEp:peerChassisId managed
        object property"
    ::= { cfprApFabricFcSanEpEntry 19 }

cfprApFabricFcSanEpPeerDn OBJECT-TYPE
    SYNTAX       SnmpAdminString
    MAX-ACCESS   read-only
    STATUS       current
    DESCRIPTION
        "Cisco Firepower fabric:FcSanEp:peerDn managed object property"
    ::= { cfprApFabricFcSanEpEntry 20 }

cfprApFabricFcSanEpPeerPortId OBJECT-TYPE
    SYNTAX       Gauge32
    MAX-ACCESS   read-only
    STATUS       current
    DESCRIPTION
        "Cisco Firepower fabric:FcSanEp:peerPortId managed
        object property"
    ::= { cfprApFabricFcSanEpEntry 21 }

cfprApFabricFcSanEpPeerSlotId OBJECT-TYPE
    SYNTAX       Gauge32
    MAX-ACCESS   read-only
    STATUS       current
    DESCRIPTION
        "Cisco Firepower fabric:FcSanEp:peerSlotId managed
        object property"
    ::= { cfprApFabricFcSanEpEntry 22 }

cfprApFabricFcSanEpPortId OBJECT-TYPE
    SYNTAX       CfprApFabricFcSanEpPortId
    MAX-ACCESS   read-only
    STATUS       current
    DESCRIPTION
        "Cisco Firepower fabric:FcSanEp:portId managed object property"
    ::= { cfprApFabricFcSanEpEntry 23 }

cfprApFabricFcSanEpSlotId OBJECT-TYPE
    SYNTAX       CfprApFabricFcSanEpSlotId
    MAX-ACCESS   read-only
    STATUS       current
    DESCRIPTION
        "Cisco Firepower fabric:FcSanEp:slotId managed object property"
    ::= { cfprApFabricFcSanEpEntry 24 }

cfprApFabricFcSanEpSwitchId OBJECT-TYPE
    SYNTAX       CfprApNetworkSwitchId
    MAX-ACCESS   read-only
    STATUS       current
    DESCRIPTION
        "Cisco Firepower fabric:FcSanEp:switchId managed object property"
    ::= { cfprApFabricFcSanEpEntry 25 }

cfprApFabricFcSanEpTransport OBJECT-TYPE
    SYNTAX       CfprApFabricAFcSanEpTransport
    MAX-ACCESS   read-only
    STATUS       current
    DESCRIPTION
        "Cisco Firepower fabric:FcSanEp:transport managed object property"
    ::= { cfprApFabricFcSanEpEntry 26 }

cfprApFabricFcSanEpType OBJECT-TYPE
    SYNTAX       CfprApFabricSanEpType
    MAX-ACCESS   read-only
    STATUS       current
    DESCRIPTION
        "Cisco Firepower fabric:FcSanEp:type managed object property"
    ::= { cfprApFabricFcSanEpEntry 27 }

cfprApFabricFcSanEpUsrLbl OBJECT-TYPE
    SYNTAX       SnmpAdminString
    MAX-ACCESS   read-only
    STATUS       current
    DESCRIPTION
        "Cisco Firepower fabric:FcSanEp:usrLbl managed object property"
    ::= { cfprApFabricFcSanEpEntry 28 }

cfprApFabricFcSanEpWarnings OBJECT-TYPE
    SYNTAX       CfprApFabricWarnings
    MAX-ACCESS   read-only
    STATUS       current
    DESCRIPTION
        "Cisco Firepower fabric:FcSanEp:warnings managed object property"
    ::= { cfprApFabricFcSanEpEntry 29 }

cfprApFabricFcSanPcTable OBJECT-TYPE
    SYNTAX           SEQUENCE OF CfprApFabricFcSanPcEntry
    MAX-ACCESS       not-accessible
    STATUS           current
    DESCRIPTION
        "Cisco Firepower fabric:FcSanPc managed object table"
    ::= { cfprApFabricObjects 54 }

cfprApFabricFcSanPcEntry OBJECT-TYPE
    SYNTAX           CfprApFabricFcSanPcEntry
    MAX-ACCESS       not-accessible
    STATUS           current
    DESCRIPTION
        "Entry for the cfprApFabricFcSanPcTable table."
    INDEX { cfprApFabricFcSanPcInstanceId }
    ::= { cfprApFabricFcSanPcTable 1 }

CfprApFabricFcSanPcEntry ::= SEQUENCE {
    cfprApFabricFcSanPcInstanceId                                    CfprApManagedObjectId,
    cfprApFabricFcSanPcDn                                            CfprApManagedObjectDn,
    cfprApFabricFcSanPcRn                                            SnmpAdminString,
    cfprApFabricFcSanPcAdminSpeed                                    CfprApPortSpeed,
    cfprApFabricFcSanPcAdminState                                    CfprApFabricCIoEpAdminState,
    cfprApFabricFcSanPcConfigState                                   CfprApFabricConfigState,
    cfprApFabricFcSanPcConfigStatus                                  CfprApFabricPcConfigStatus,
    cfprApFabricFcSanPcDescr                                         SnmpAdminString,
    cfprApFabricFcSanPcEpDn                                          SnmpAdminString,
    cfprApFabricFcSanPcFltAggr                                       Unsigned64,
    cfprApFabricFcSanPcIfRole                                        CfprApFabricSanPcIfRole,
    cfprApFabricFcSanPcIfType                                        CfprApFabricCIoEpIfType,
    cfprApFabricFcSanPcLocale                                        CfprApFabricExternalPcLocale,
    cfprApFabricFcSanPcName                                          SnmpAdminString,
    cfprApFabricFcSanPcOperSpeed                                     Gauge32,
    cfprApFabricFcSanPcOperState                                     CfprApNetworkPortOperState,
    cfprApFabricFcSanPcPeerDn                                        SnmpAdminString,
    cfprApFabricFcSanPcPortId                                        Gauge32,
    cfprApFabricFcSanPcStateQual                                     SnmpAdminString,
    cfprApFabricFcSanPcSwitchId                                      CfprApNetworkSwitchId,
    cfprApFabricFcSanPcTransport                                     CfprApFabricFcSanPcTransport,
    cfprApFabricFcSanPcType                                          CfprApFabricSanPcType,
    cfprApFabricFcSanPcWarnings                                      CfprApFabricWarnings
}

cfprApFabricFcSanPcInstanceId OBJECT-TYPE
    SYNTAX       CfprApManagedObjectId
    MAX-ACCESS   not-accessible
    STATUS       current
    DESCRIPTION
        "Instance identifier of the managed object."
    ::= { cfprApFabricFcSanPcEntry 1 }

cfprApFabricFcSanPcDn OBJECT-TYPE
    SYNTAX       CfprApManagedObjectDn
    MAX-ACCESS   read-only
    STATUS       current
    DESCRIPTION
        "Cisco Firepower fabric:FcSanPc:dn managed object property"
    ::= { cfprApFabricFcSanPcEntry 2 }

cfprApFabricFcSanPcRn OBJECT-TYPE
    SYNTAX       SnmpAdminString
    MAX-ACCESS   read-only
    STATUS       current
    DESCRIPTION
        "Cisco Firepower fabric:FcSanPc:rn managed object property"
    ::= { cfprApFabricFcSanPcEntry 3 }

cfprApFabricFcSanPcAdminSpeed OBJECT-TYPE
    SYNTAX       CfprApPortSpeed
    MAX-ACCESS   read-only
    STATUS       current
    DESCRIPTION
        "Cisco Firepower fabric:FcSanPc:adminSpeed managed
        object property"
    ::= { cfprApFabricFcSanPcEntry 4 }

cfprApFabricFcSanPcAdminState OBJECT-TYPE
    SYNTAX       CfprApFabricCIoEpAdminState
    MAX-ACCESS   read-only
    STATUS       current
    DESCRIPTION
        "Cisco Firepower fabric:FcSanPc:adminState managed
        object property"
    ::= { cfprApFabricFcSanPcEntry 5 }

cfprApFabricFcSanPcConfigState OBJECT-TYPE
    SYNTAX       CfprApFabricConfigState
    MAX-ACCESS   read-only
    STATUS       current
    DESCRIPTION
        "Cisco Firepower fabric:FcSanPc:configState managed
        object property"
    ::= { cfprApFabricFcSanPcEntry 6 }

cfprApFabricFcSanPcConfigStatus OBJECT-TYPE
    SYNTAX       CfprApFabricPcConfigStatus
    MAX-ACCESS   read-only
    STATUS       current
    DESCRIPTION
        "Cisco Firepower fabric:FcSanPc:configStatus managed
        object property"
    ::= { cfprApFabricFcSanPcEntry 7 }

cfprApFabricFcSanPcDescr OBJECT-TYPE
    SYNTAX       SnmpAdminString
    MAX-ACCESS   read-only
    STATUS       current
    DESCRIPTION
        "Cisco Firepower fabric:FcSanPc:descr managed object property"
    ::= { cfprApFabricFcSanPcEntry 8 }

cfprApFabricFcSanPcEpDn OBJECT-TYPE
    SYNTAX       SnmpAdminString
    MAX-ACCESS   read-only
    STATUS       current
    DESCRIPTION
        "Cisco Firepower fabric:FcSanPc:epDn managed object property"
    ::= { cfprApFabricFcSanPcEntry 9 }

cfprApFabricFcSanPcFltAggr OBJECT-TYPE
    SYNTAX       Unsigned64
    MAX-ACCESS   read-only
    STATUS       current
    DESCRIPTION
        "Cisco Firepower fabric:FcSanPc:fltAggr managed object property"
    ::= { cfprApFabricFcSanPcEntry 10 }

cfprApFabricFcSanPcIfRole OBJECT-TYPE
    SYNTAX       CfprApFabricSanPcIfRole
    MAX-ACCESS   read-only
    STATUS       current
    DESCRIPTION
        "Cisco Firepower fabric:FcSanPc:ifRole managed object property"
    ::= { cfprApFabricFcSanPcEntry 11 }

cfprApFabricFcSanPcIfType OBJECT-TYPE
    SYNTAX       CfprApFabricCIoEpIfType
    MAX-ACCESS   read-only
    STATUS       current
    DESCRIPTION
        "Cisco Firepower fabric:FcSanPc:ifType managed object property"
    ::= { cfprApFabricFcSanPcEntry 12 }

cfprApFabricFcSanPcLocale OBJECT-TYPE
    SYNTAX       CfprApFabricExternalPcLocale
    MAX-ACCESS   read-only
    STATUS       current
    DESCRIPTION
        "Cisco Firepower fabric:FcSanPc:locale managed object property"
    ::= { cfprApFabricFcSanPcEntry 13 }

cfprApFabricFcSanPcName OBJECT-TYPE
    SYNTAX       SnmpAdminString
    MAX-ACCESS   read-only
    STATUS       current
    DESCRIPTION
        "Cisco Firepower fabric:FcSanPc:name managed object property"
    ::= { cfprApFabricFcSanPcEntry 14 }

cfprApFabricFcSanPcOperSpeed OBJECT-TYPE
    SYNTAX       Gauge32
    MAX-ACCESS   read-only
    STATUS       current
    DESCRIPTION
        "Cisco Firepower fabric:FcSanPc:operSpeed managed object property"
    ::= { cfprApFabricFcSanPcEntry 15 }

cfprApFabricFcSanPcOperState OBJECT-TYPE
    SYNTAX       CfprApNetworkPortOperState
    MAX-ACCESS   read-only
    STATUS       current
    DESCRIPTION
        "Cisco Firepower fabric:FcSanPc:operState managed object property"
    ::= { cfprApFabricFcSanPcEntry 16 }

cfprApFabricFcSanPcPeerDn OBJECT-TYPE
    SYNTAX       SnmpAdminString
    MAX-ACCESS   read-only
    STATUS       current
    DESCRIPTION
        "Cisco Firepower fabric:FcSanPc:peerDn managed object property"
    ::= { cfprApFabricFcSanPcEntry 17 }

cfprApFabricFcSanPcPortId OBJECT-TYPE
    SYNTAX       Gauge32
    MAX-ACCESS   read-only
    STATUS       current
    DESCRIPTION
        "Cisco Firepower fabric:FcSanPc:portId managed object property"
    ::= { cfprApFabricFcSanPcEntry 18 }

cfprApFabricFcSanPcStateQual OBJECT-TYPE
    SYNTAX       SnmpAdminString
    MAX-ACCESS   read-only
    STATUS       current
    DESCRIPTION
        "Cisco Firepower fabric:FcSanPc:stateQual managed object property"
    ::= { cfprApFabricFcSanPcEntry 19 }

cfprApFabricFcSanPcSwitchId OBJECT-TYPE
    SYNTAX       CfprApNetworkSwitchId
    MAX-ACCESS   read-only
    STATUS       current
    DESCRIPTION
        "Cisco Firepower fabric:FcSanPc:switchId managed object property"
    ::= { cfprApFabricFcSanPcEntry 20 }

cfprApFabricFcSanPcTransport OBJECT-TYPE
    SYNTAX       CfprApFabricFcSanPcTransport
    MAX-ACCESS   read-only
    STATUS       current
    DESCRIPTION
        "Cisco Firepower fabric:FcSanPc:transport managed object property"
    ::= { cfprApFabricFcSanPcEntry 21 }

cfprApFabricFcSanPcType OBJECT-TYPE
    SYNTAX       CfprApFabricSanPcType
    MAX-ACCESS   read-only
    STATUS       current
    DESCRIPTION
        "Cisco Firepower fabric:FcSanPc:type managed object property"
    ::= { cfprApFabricFcSanPcEntry 22 }

cfprApFabricFcSanPcWarnings OBJECT-TYPE
    SYNTAX       CfprApFabricWarnings
    MAX-ACCESS   read-only
    STATUS       current
    DESCRIPTION
        "Cisco Firepower fabric:FcSanPc:warnings managed object property"
    ::= { cfprApFabricFcSanPcEntry 23 }

cfprApFabricFcSanPcEpTable OBJECT-TYPE
    SYNTAX           SEQUENCE OF CfprApFabricFcSanPcEpEntry
    MAX-ACCESS       not-accessible
    STATUS           current
    DESCRIPTION
        "Cisco Firepower fabric:FcSanPcEp managed object table"
    ::= { cfprApFabricObjects 55 }

cfprApFabricFcSanPcEpEntry OBJECT-TYPE
    SYNTAX           CfprApFabricFcSanPcEpEntry
    MAX-ACCESS       not-accessible
    STATUS           current
    DESCRIPTION
        "Entry for the cfprApFabricFcSanPcEpTable table."
    INDEX { cfprApFabricFcSanPcEpInstanceId }
    ::= { cfprApFabricFcSanPcEpTable 1 }

CfprApFabricFcSanPcEpEntry ::= SEQUENCE {
    cfprApFabricFcSanPcEpInstanceId                                  CfprApManagedObjectId,
    cfprApFabricFcSanPcEpDnData                                      CfprApManagedObjectDn,
    cfprApFabricFcSanPcEpRn                                          SnmpAdminString,
    cfprApFabricFcSanPcEpAdminSpeed                                  CfprApPortSpeed,
    cfprApFabricFcSanPcEpAdminState                                  CfprApFabricExternalEpAdminState,
    cfprApFabricFcSanPcEpAggrPortId                                  Gauge32,
    cfprApFabricFcSanPcEpChassisId                                   Gauge32,
    cfprApFabricFcSanPcEpEpDn                                        SnmpAdminString,
    cfprApFabricFcSanPcEpFillPattern                                 CfprApFabricFillPattern,
    cfprApFabricFcSanPcEpFltAggr                                     Unsigned64,
    cfprApFabricFcSanPcEpIfRole                                      CfprApFabricSanEpIfRole,
    cfprApFabricFcSanPcEpIfType                                      CfprApFabricPIoEpIfType,
    cfprApFabricFcSanPcEpLicGP                                       Unsigned64,
    cfprApFabricFcSanPcEpLicState                                    CfprApLicenseState,
    cfprApFabricFcSanPcEpLocale                                      CfprApFabricExternalEpLocale,
    cfprApFabricFcSanPcEpMembership                                  CfprApFabricMembershipStatus,
    cfprApFabricFcSanPcEpName                                        SnmpAdminString,
    cfprApFabricFcSanPcEpOperState                                   CfprApFabricPIoEpOperState,
    cfprApFabricFcSanPcEpOperStateReason                             SnmpAdminString,
    cfprApFabricFcSanPcEpPeerAggrPortId                              Gauge32,
    cfprApFabricFcSanPcEpPeerChassisId                               Gauge32,
    cfprApFabricFcSanPcEpPeerDn                                      SnmpAdminString,
    cfprApFabricFcSanPcEpPeerPortId                                  Gauge32,
    cfprApFabricFcSanPcEpPeerSlotId                                  Gauge32,
    cfprApFabricFcSanPcEpPortId                                      CfprApFabricFcSanPcEpPortId,
    cfprApFabricFcSanPcEpSlotId                                      CfprApFabricFcSanPcEpSlotId,
    cfprApFabricFcSanPcEpSwitchId                                    CfprApNetworkSwitchId,
    cfprApFabricFcSanPcEpTransport                                   CfprApFabricAFcSanEpTransport,
    cfprApFabricFcSanPcEpType                                        CfprApFabricSanEpType,
    cfprApFabricFcSanPcEpWarnings                                    CfprApFabricWarnings
}

cfprApFabricFcSanPcEpInstanceId OBJECT-TYPE
    SYNTAX       CfprApManagedObjectId
    MAX-ACCESS   not-accessible
    STATUS       current
    DESCRIPTION
        "Instance identifier of the managed object."
    ::= { cfprApFabricFcSanPcEpEntry 1 }

cfprApFabricFcSanPcEpDnData OBJECT-TYPE
    SYNTAX       CfprApManagedObjectDn
    MAX-ACCESS   read-only
    STATUS       current
    DESCRIPTION
        "Cisco Firepower fabric:FcSanPcEp:dn managed object property"
    ::= { cfprApFabricFcSanPcEpEntry 2 }

cfprApFabricFcSanPcEpRn OBJECT-TYPE
    SYNTAX       SnmpAdminString
    MAX-ACCESS   read-only
    STATUS       current
    DESCRIPTION
        "Cisco Firepower fabric:FcSanPcEp:rn managed object property"
    ::= { cfprApFabricFcSanPcEpEntry 3 }

cfprApFabricFcSanPcEpAdminSpeed OBJECT-TYPE
    SYNTAX       CfprApPortSpeed
    MAX-ACCESS   read-only
    STATUS       current
    DESCRIPTION
        "Cisco Firepower fabric:FcSanPcEp:adminSpeed managed
        object property"
    ::= { cfprApFabricFcSanPcEpEntry 4 }

cfprApFabricFcSanPcEpAdminState OBJECT-TYPE
    SYNTAX       CfprApFabricExternalEpAdminState
    MAX-ACCESS   read-only
    STATUS       current
    DESCRIPTION
        "Cisco Firepower fabric:FcSanPcEp:adminState managed
        object property"
    ::= { cfprApFabricFcSanPcEpEntry 5 }

cfprApFabricFcSanPcEpAggrPortId OBJECT-TYPE
    SYNTAX       Gauge32
    MAX-ACCESS   read-only
    STATUS       current
    DESCRIPTION
        "Cisco Firepower fabric:FcSanPcEp:aggrPortId managed
        object property"
    ::= { cfprApFabricFcSanPcEpEntry 6 }

cfprApFabricFcSanPcEpChassisId OBJECT-TYPE
    SYNTAX       Gauge32
    MAX-ACCESS   read-only
    STATUS       current
    DESCRIPTION
        "Cisco Firepower fabric:FcSanPcEp:chassisId managed
        object property"
    ::= { cfprApFabricFcSanPcEpEntry 7 }

cfprApFabricFcSanPcEpEpDn OBJECT-TYPE
    SYNTAX       SnmpAdminString
    MAX-ACCESS   read-only
    STATUS       current
    DESCRIPTION
        "Cisco Firepower fabric:FcSanPcEp:epDn managed object property"
    ::= { cfprApFabricFcSanPcEpEntry 8 }

cfprApFabricFcSanPcEpFillPattern OBJECT-TYPE
    SYNTAX       CfprApFabricFillPattern
    MAX-ACCESS   read-only
    STATUS       current
    DESCRIPTION
        "Cisco Firepower fabric:FcSanPcEp:fillPattern managed
        object property"
    ::= { cfprApFabricFcSanPcEpEntry 9 }

cfprApFabricFcSanPcEpFltAggr OBJECT-TYPE
    SYNTAX       Unsigned64
    MAX-ACCESS   read-only
    STATUS       current
    DESCRIPTION
        "Cisco Firepower fabric:FcSanPcEp:fltAggr managed object property"
    ::= { cfprApFabricFcSanPcEpEntry 10 }

cfprApFabricFcSanPcEpIfRole OBJECT-TYPE
    SYNTAX       CfprApFabricSanEpIfRole
    MAX-ACCESS   read-only
    STATUS       current
    DESCRIPTION
        "Cisco Firepower fabric:FcSanPcEp:ifRole managed object property"
    ::= { cfprApFabricFcSanPcEpEntry 11 }

cfprApFabricFcSanPcEpIfType OBJECT-TYPE
    SYNTAX       CfprApFabricPIoEpIfType
    MAX-ACCESS   read-only
    STATUS       current
    DESCRIPTION
        "Cisco Firepower fabric:FcSanPcEp:ifType managed object property"
    ::= { cfprApFabricFcSanPcEpEntry 12 }

cfprApFabricFcSanPcEpLicGP OBJECT-TYPE
    SYNTAX       Unsigned64
    MAX-ACCESS   read-only
    STATUS       current
    DESCRIPTION
        "Cisco Firepower fabric:FcSanPcEp:licGP managed object property"
    ::= { cfprApFabricFcSanPcEpEntry 13 }

cfprApFabricFcSanPcEpLicState OBJECT-TYPE
    SYNTAX       CfprApLicenseState
    MAX-ACCESS   read-only
    STATUS       current
    DESCRIPTION
        "Cisco Firepower fabric:FcSanPcEp:licState managed
        object property"
    ::= { cfprApFabricFcSanPcEpEntry 14 }

cfprApFabricFcSanPcEpLocale OBJECT-TYPE
    SYNTAX       CfprApFabricExternalEpLocale
    MAX-ACCESS   read-only
    STATUS       current
    DESCRIPTION
        "Cisco Firepower fabric:FcSanPcEp:locale managed object property"
    ::= { cfprApFabricFcSanPcEpEntry 15 }

cfprApFabricFcSanPcEpMembership OBJECT-TYPE
    SYNTAX       CfprApFabricMembershipStatus
    MAX-ACCESS   read-only
    STATUS       current
    DESCRIPTION
        "Cisco Firepower fabric:FcSanPcEp:membership managed
        object property"
    ::= { cfprApFabricFcSanPcEpEntry 16 }

cfprApFabricFcSanPcEpName OBJECT-TYPE
    SYNTAX       SnmpAdminString
    MAX-ACCESS   read-only
    STATUS       current
    DESCRIPTION
        "Cisco Firepower fabric:FcSanPcEp:name managed object property"
    ::= { cfprApFabricFcSanPcEpEntry 17 }

cfprApFabricFcSanPcEpOperState OBJECT-TYPE
    SYNTAX       CfprApFabricPIoEpOperState
    MAX-ACCESS   read-only
    STATUS       current
    DESCRIPTION
        "Cisco Firepower fabric:FcSanPcEp:operState managed
        object property"
    ::= { cfprApFabricFcSanPcEpEntry 18 }

cfprApFabricFcSanPcEpOperStateReason OBJECT-TYPE
    SYNTAX       SnmpAdminString
    MAX-ACCESS   read-only
    STATUS       current
    DESCRIPTION
        "Cisco Firepower fabric:FcSanPcEp:operStateReason
        managed object property"
    ::= { cfprApFabricFcSanPcEpEntry 19 }

cfprApFabricFcSanPcEpPeerAggrPortId OBJECT-TYPE
    SYNTAX       Gauge32
    MAX-ACCESS   read-only
    STATUS       current
    DESCRIPTION
        "Cisco Firepower fabric:FcSanPcEp:peerAggrPortId
        managed object property"
    ::= { cfprApFabricFcSanPcEpEntry 20 }

cfprApFabricFcSanPcEpPeerChassisId OBJECT-TYPE
    SYNTAX       Gauge32
    MAX-ACCESS   read-only
    STATUS       current
    DESCRIPTION
        "Cisco Firepower fabric:FcSanPcEp:peerChassisId
        managed object property"
    ::= { cfprApFabricFcSanPcEpEntry 21 }

cfprApFabricFcSanPcEpPeerDn OBJECT-TYPE
    SYNTAX       SnmpAdminString
    MAX-ACCESS   read-only
    STATUS       current
    DESCRIPTION
        "Cisco Firepower fabric:FcSanPcEp:peerDn managed object property"
    ::= { cfprApFabricFcSanPcEpEntry 22 }

cfprApFabricFcSanPcEpPeerPortId OBJECT-TYPE
    SYNTAX       Gauge32
    MAX-ACCESS   read-only
    STATUS       current
    DESCRIPTION
        "Cisco Firepower fabric:FcSanPcEp:peerPortId managed
        object property"
    ::= { cfprApFabricFcSanPcEpEntry 23 }

cfprApFabricFcSanPcEpPeerSlotId OBJECT-TYPE
    SYNTAX       Gauge32
    MAX-ACCESS   read-only
    STATUS       current
    DESCRIPTION
        "Cisco Firepower fabric:FcSanPcEp:peerSlotId managed
        object property"
    ::= { cfprApFabricFcSanPcEpEntry 24 }

cfprApFabricFcSanPcEpPortId OBJECT-TYPE
    SYNTAX       CfprApFabricFcSanPcEpPortId
    MAX-ACCESS   read-only
    STATUS       current
    DESCRIPTION
        "Cisco Firepower fabric:FcSanPcEp:portId managed object property"
    ::= { cfprApFabricFcSanPcEpEntry 25 }

cfprApFabricFcSanPcEpSlotId OBJECT-TYPE
    SYNTAX       CfprApFabricFcSanPcEpSlotId
    MAX-ACCESS   read-only
    STATUS       current
    DESCRIPTION
        "Cisco Firepower fabric:FcSanPcEp:slotId managed object property"
    ::= { cfprApFabricFcSanPcEpEntry 26 }

cfprApFabricFcSanPcEpSwitchId OBJECT-TYPE
    SYNTAX       CfprApNetworkSwitchId
    MAX-ACCESS   read-only
    STATUS       current
    DESCRIPTION
        "Cisco Firepower fabric:FcSanPcEp:switchId managed
        object property"
    ::= { cfprApFabricFcSanPcEpEntry 27 }

cfprApFabricFcSanPcEpTransport OBJECT-TYPE
    SYNTAX       CfprApFabricAFcSanEpTransport
    MAX-ACCESS   read-only
    STATUS       current
    DESCRIPTION
        "Cisco Firepower fabric:FcSanPcEp:transport managed
        object property"
    ::= { cfprApFabricFcSanPcEpEntry 28 }

cfprApFabricFcSanPcEpType OBJECT-TYPE
    SYNTAX       CfprApFabricSanEpType
    MAX-ACCESS   read-only
    STATUS       current
    DESCRIPTION
        "Cisco Firepower fabric:FcSanPcEp:type managed object property"
    ::= { cfprApFabricFcSanPcEpEntry 29 }

cfprApFabricFcSanPcEpWarnings OBJECT-TYPE
    SYNTAX       CfprApFabricWarnings
    MAX-ACCESS   read-only
    STATUS       current
    DESCRIPTION
        "Cisco Firepower fabric:FcSanPcEp:warnings managed
        object property"
    ::= { cfprApFabricFcSanPcEpEntry 30 }

cfprApFabricFcVsanPcTable OBJECT-TYPE
    SYNTAX           SEQUENCE OF CfprApFabricFcVsanPcEntry
    MAX-ACCESS       not-accessible
    STATUS           current
    DESCRIPTION
        "Cisco Firepower fabric:FcVsanPc managed object table"
    ::= { cfprApFabricObjects 56 }

cfprApFabricFcVsanPcEntry OBJECT-TYPE
    SYNTAX           CfprApFabricFcVsanPcEntry
    MAX-ACCESS       not-accessible
    STATUS           current
    DESCRIPTION
        "Entry for the cfprApFabricFcVsanPcTable table."
    INDEX { cfprApFabricFcVsanPcInstanceId }
    ::= { cfprApFabricFcVsanPcTable 1 }

CfprApFabricFcVsanPcEntry ::= SEQUENCE {
    cfprApFabricFcVsanPcInstanceId                                   CfprApManagedObjectId,
    cfprApFabricFcVsanPcDn                                           CfprApManagedObjectDn,
    cfprApFabricFcVsanPcRn                                           SnmpAdminString,
    cfprApFabricFcVsanPcAdminState                                   CfprApFabricCIoEpAdminState,
    cfprApFabricFcVsanPcDescr                                        SnmpAdminString,
    cfprApFabricFcVsanPcEpDn                                         SnmpAdminString,
    cfprApFabricFcVsanPcFltAggr                                      Unsigned64,
    cfprApFabricFcVsanPcIfRole                                       CfprApFabricSanPcIfRole,
    cfprApFabricFcVsanPcIfType                                       CfprApFabricCIoEpIfType,
    cfprApFabricFcVsanPcLocale                                       CfprApFabricExternalPcLocale,
    cfprApFabricFcVsanPcName                                         SnmpAdminString,
    cfprApFabricFcVsanPcOperState                                    CfprApNetworkPortOperState,
    cfprApFabricFcVsanPcPeerDn                                       SnmpAdminString,
    cfprApFabricFcVsanPcPortId                                       Gauge32,
    cfprApFabricFcVsanPcStateQual                                    SnmpAdminString,
    cfprApFabricFcVsanPcSwitchId                                     CfprApNetworkSwitchId,
    cfprApFabricFcVsanPcTransport                                    CfprApFabricFcVsanPcTransport,
    cfprApFabricFcVsanPcType                                         CfprApFabricSanPcType,
    cfprApFabricFcVsanPcWarnings                                     CfprApFabricWarnings
}

cfprApFabricFcVsanPcInstanceId OBJECT-TYPE
    SYNTAX       CfprApManagedObjectId
    MAX-ACCESS   not-accessible
    STATUS       current
    DESCRIPTION
        "Instance identifier of the managed object."
    ::= { cfprApFabricFcVsanPcEntry 1 }

cfprApFabricFcVsanPcDn OBJECT-TYPE
    SYNTAX       CfprApManagedObjectDn
    MAX-ACCESS   read-only
    STATUS       current
    DESCRIPTION
        "Cisco Firepower fabric:FcVsanPc:dn managed object property"
    ::= { cfprApFabricFcVsanPcEntry 2 }

cfprApFabricFcVsanPcRn OBJECT-TYPE
    SYNTAX       SnmpAdminString
    MAX-ACCESS   read-only
    STATUS       current
    DESCRIPTION
        "Cisco Firepower fabric:FcVsanPc:rn managed object property"
    ::= { cfprApFabricFcVsanPcEntry 3 }

cfprApFabricFcVsanPcAdminState OBJECT-TYPE
    SYNTAX       CfprApFabricCIoEpAdminState
    MAX-ACCESS   read-only
    STATUS       current
    DESCRIPTION
        "Cisco Firepower fabric:FcVsanPc:adminState managed
        object property"
    ::= { cfprApFabricFcVsanPcEntry 4 }

cfprApFabricFcVsanPcDescr OBJECT-TYPE
    SYNTAX       SnmpAdminString
    MAX-ACCESS   read-only
    STATUS       current
    DESCRIPTION
        "Cisco Firepower fabric:FcVsanPc:descr managed object property"
    ::= { cfprApFabricFcVsanPcEntry 5 }

cfprApFabricFcVsanPcEpDn OBJECT-TYPE
    SYNTAX       SnmpAdminString
    MAX-ACCESS   read-only
    STATUS       current
    DESCRIPTION
        "Cisco Firepower fabric:FcVsanPc:epDn managed object property"
    ::= { cfprApFabricFcVsanPcEntry 6 }

cfprApFabricFcVsanPcFltAggr OBJECT-TYPE
    SYNTAX       Unsigned64
    MAX-ACCESS   read-only
    STATUS       current
    DESCRIPTION
        "Cisco Firepower fabric:FcVsanPc:fltAggr managed object property"
    ::= { cfprApFabricFcVsanPcEntry 7 }

cfprApFabricFcVsanPcIfRole OBJECT-TYPE
    SYNTAX       CfprApFabricSanPcIfRole
    MAX-ACCESS   read-only
    STATUS       current
    DESCRIPTION
        "Cisco Firepower fabric:FcVsanPc:ifRole managed object property"
    ::= { cfprApFabricFcVsanPcEntry 8 }

cfprApFabricFcVsanPcIfType OBJECT-TYPE
    SYNTAX       CfprApFabricCIoEpIfType
    MAX-ACCESS   read-only
    STATUS       current
    DESCRIPTION
        "Cisco Firepower fabric:FcVsanPc:ifType managed object property"
    ::= { cfprApFabricFcVsanPcEntry 9 }

cfprApFabricFcVsanPcLocale OBJECT-TYPE
    SYNTAX       CfprApFabricExternalPcLocale
    MAX-ACCESS   read-only
    STATUS       current
    DESCRIPTION
        "Cisco Firepower fabric:FcVsanPc:locale managed object property"
    ::= { cfprApFabricFcVsanPcEntry 10 }

cfprApFabricFcVsanPcName OBJECT-TYPE
    SYNTAX       SnmpAdminString
    MAX-ACCESS   read-only
    STATUS       current
    DESCRIPTION
        "Cisco Firepower fabric:FcVsanPc:name managed object property"
    ::= { cfprApFabricFcVsanPcEntry 11 }

cfprApFabricFcVsanPcOperState OBJECT-TYPE
    SYNTAX       CfprApNetworkPortOperState
    MAX-ACCESS   read-only
    STATUS       current
    DESCRIPTION
        "Cisco Firepower fabric:FcVsanPc:operState managed
        object property"
    ::= { cfprApFabricFcVsanPcEntry 12 }

cfprApFabricFcVsanPcPeerDn OBJECT-TYPE
    SYNTAX       SnmpAdminString
    MAX-ACCESS   read-only
    STATUS       current
    DESCRIPTION
        "Cisco Firepower fabric:FcVsanPc:peerDn managed object property"
    ::= { cfprApFabricFcVsanPcEntry 13 }

cfprApFabricFcVsanPcPortId OBJECT-TYPE
    SYNTAX       Gauge32
    MAX-ACCESS   read-only
    STATUS       current
    DESCRIPTION
        "Cisco Firepower fabric:FcVsanPc:portId managed object property"
    ::= { cfprApFabricFcVsanPcEntry 14 }

cfprApFabricFcVsanPcStateQual OBJECT-TYPE
    SYNTAX       SnmpAdminString
    MAX-ACCESS   read-only
    STATUS       current
    DESCRIPTION
        "Cisco Firepower fabric:FcVsanPc:stateQual managed
        object property"
    ::= { cfprApFabricFcVsanPcEntry 15 }

cfprApFabricFcVsanPcSwitchId OBJECT-TYPE
    SYNTAX       CfprApNetworkSwitchId
    MAX-ACCESS   read-only
    STATUS       current
    DESCRIPTION
        "Cisco Firepower fabric:FcVsanPc:switchId managed object property"
    ::= { cfprApFabricFcVsanPcEntry 16 }

cfprApFabricFcVsanPcTransport OBJECT-TYPE
    SYNTAX       CfprApFabricFcVsanPcTransport
    MAX-ACCESS   read-only
    STATUS       current
    DESCRIPTION
        "Cisco Firepower fabric:FcVsanPc:transport managed
        object property"
    ::= { cfprApFabricFcVsanPcEntry 17 }

cfprApFabricFcVsanPcType OBJECT-TYPE
    SYNTAX       CfprApFabricSanPcType
    MAX-ACCESS   read-only
    STATUS       current
    DESCRIPTION
        "Cisco Firepower fabric:FcVsanPc:type managed object property"
    ::= { cfprApFabricFcVsanPcEntry 18 }

cfprApFabricFcVsanPcWarnings OBJECT-TYPE
    SYNTAX       CfprApFabricWarnings
    MAX-ACCESS   read-only
    STATUS       current
    DESCRIPTION
        "Cisco Firepower fabric:FcVsanPc:warnings managed object property"
    ::= { cfprApFabricFcVsanPcEntry 19 }

cfprApFabricFcVsanPortEpTable OBJECT-TYPE
    SYNTAX           SEQUENCE OF CfprApFabricFcVsanPortEpEntry
    MAX-ACCESS       not-accessible
    STATUS           current
    DESCRIPTION
        "Cisco Firepower fabric:FcVsanPortEp managed object table"
    ::= { cfprApFabricObjects 57 }

cfprApFabricFcVsanPortEpEntry OBJECT-TYPE
    SYNTAX           CfprApFabricFcVsanPortEpEntry
    MAX-ACCESS       not-accessible
    STATUS           current
    DESCRIPTION
        "Entry for the cfprApFabricFcVsanPortEpTable table."
    INDEX { cfprApFabricFcVsanPortEpInstanceId }
    ::= { cfprApFabricFcVsanPortEpTable 1 }

CfprApFabricFcVsanPortEpEntry ::= SEQUENCE {
    cfprApFabricFcVsanPortEpInstanceId                               CfprApManagedObjectId,
    cfprApFabricFcVsanPortEpDn                                       CfprApManagedObjectDn,
    cfprApFabricFcVsanPortEpRn                                       SnmpAdminString,
    cfprApFabricFcVsanPortEpAdminState                               CfprApFabricExternalEpAdminState,
    cfprApFabricFcVsanPortEpAggrPortId                               Gauge32,
    cfprApFabricFcVsanPortEpChassisId                                Gauge32,
    cfprApFabricFcVsanPortEpEpDn                                     SnmpAdminString,
    cfprApFabricFcVsanPortEpFltAggr                                  Unsigned64,
    cfprApFabricFcVsanPortEpIfRole                                   CfprApFabricSanEpIfRole,
    cfprApFabricFcVsanPortEpIfType                                   CfprApFabricPIoEpIfType,
    cfprApFabricFcVsanPortEpLicGP                                    Unsigned64,
    cfprApFabricFcVsanPortEpLicState                                 CfprApLicenseState,
    cfprApFabricFcVsanPortEpLocale                                   CfprApFabricExternalEpLocale,
    cfprApFabricFcVsanPortEpName                                     SnmpAdminString,
    cfprApFabricFcVsanPortEpOperState                                CfprApFabricPIoEpOperState,
    cfprApFabricFcVsanPortEpOperStateReason                          SnmpAdminString,
    cfprApFabricFcVsanPortEpPeerAggrPortId                           Gauge32,
    cfprApFabricFcVsanPortEpPeerChassisId                            Gauge32,
    cfprApFabricFcVsanPortEpPeerDn                                   SnmpAdminString,
    cfprApFabricFcVsanPortEpPeerPortId                               Gauge32,
    cfprApFabricFcVsanPortEpPeerSlotId                               Gauge32,
    cfprApFabricFcVsanPortEpPortId                                   CfprApFabricFcVsanPortEpPortId,
    cfprApFabricFcVsanPortEpSlotId                                   CfprApFabricFcVsanPortEpSlotId,
    cfprApFabricFcVsanPortEpSwitchId                                 CfprApNetworkSwitchId,
    cfprApFabricFcVsanPortEpTransport                                CfprApFabricAFcSanEpTransport,
    cfprApFabricFcVsanPortEpType                                     CfprApFabricSanEpType,
    cfprApFabricFcVsanPortEpWarnings                                 CfprApFabricWarnings
}

cfprApFabricFcVsanPortEpInstanceId OBJECT-TYPE
    SYNTAX       CfprApManagedObjectId
    MAX-ACCESS   not-accessible
    STATUS       current
    DESCRIPTION
        "Instance identifier of the managed object."
    ::= { cfprApFabricFcVsanPortEpEntry 1 }

cfprApFabricFcVsanPortEpDn OBJECT-TYPE
    SYNTAX       CfprApManagedObjectDn
    MAX-ACCESS   read-only
    STATUS       current
    DESCRIPTION
        "Cisco Firepower fabric:FcVsanPortEp:dn managed object property"
    ::= { cfprApFabricFcVsanPortEpEntry 2 }

cfprApFabricFcVsanPortEpRn OBJECT-TYPE
    SYNTAX       SnmpAdminString
    MAX-ACCESS   read-only
    STATUS       current
    DESCRIPTION
        "Cisco Firepower fabric:FcVsanPortEp:rn managed object property"
    ::= { cfprApFabricFcVsanPortEpEntry 3 }

cfprApFabricFcVsanPortEpAdminState OBJECT-TYPE
    SYNTAX       CfprApFabricExternalEpAdminState
    MAX-ACCESS   read-only
    STATUS       current
    DESCRIPTION
        "Cisco Firepower fabric:FcVsanPortEp:adminState
        managed object property"
    ::= { cfprApFabricFcVsanPortEpEntry 4 }

cfprApFabricFcVsanPortEpAggrPortId OBJECT-TYPE
    SYNTAX       Gauge32
    MAX-ACCESS   read-only
    STATUS       current
    DESCRIPTION
        "Cisco Firepower fabric:FcVsanPortEp:aggrPortId
        managed object property"
    ::= { cfprApFabricFcVsanPortEpEntry 5 }

cfprApFabricFcVsanPortEpChassisId OBJECT-TYPE
    SYNTAX       Gauge32
    MAX-ACCESS   read-only
    STATUS       current
    DESCRIPTION
        "Cisco Firepower fabric:FcVsanPortEp:chassisId
        managed object property"
    ::= { cfprApFabricFcVsanPortEpEntry 6 }

cfprApFabricFcVsanPortEpEpDn OBJECT-TYPE
    SYNTAX       SnmpAdminString
    MAX-ACCESS   read-only
    STATUS       current
    DESCRIPTION
        "Cisco Firepower fabric:FcVsanPortEp:epDn managed object property"
    ::= { cfprApFabricFcVsanPortEpEntry 7 }

cfprApFabricFcVsanPortEpFltAggr OBJECT-TYPE
    SYNTAX       Unsigned64
    MAX-ACCESS   read-only
    STATUS       current
    DESCRIPTION
        "Cisco Firepower fabric:FcVsanPortEp:fltAggr managed
        object property"
    ::= { cfprApFabricFcVsanPortEpEntry 8 }

cfprApFabricFcVsanPortEpIfRole OBJECT-TYPE
    SYNTAX       CfprApFabricSanEpIfRole
    MAX-ACCESS   read-only
    STATUS       current
    DESCRIPTION
        "Cisco Firepower fabric:FcVsanPortEp:ifRole managed
        object property"
    ::= { cfprApFabricFcVsanPortEpEntry 9 }

cfprApFabricFcVsanPortEpIfType OBJECT-TYPE
    SYNTAX       CfprApFabricPIoEpIfType
    MAX-ACCESS   read-only
    STATUS       current
    DESCRIPTION
        "Cisco Firepower fabric:FcVsanPortEp:ifType managed
        object property"
    ::= { cfprApFabricFcVsanPortEpEntry 10 }

cfprApFabricFcVsanPortEpLicGP OBJECT-TYPE
    SYNTAX       Unsigned64
    MAX-ACCESS   read-only
    STATUS       current
    DESCRIPTION
        "Cisco Firepower fabric:FcVsanPortEp:licGP managed
        object property"
    ::= { cfprApFabricFcVsanPortEpEntry 11 }

cfprApFabricFcVsanPortEpLicState OBJECT-TYPE
    SYNTAX       CfprApLicenseState
    MAX-ACCESS   read-only
    STATUS       current
    DESCRIPTION
        "Cisco Firepower fabric:FcVsanPortEp:licState managed
        object property"
    ::= { cfprApFabricFcVsanPortEpEntry 12 }

cfprApFabricFcVsanPortEpLocale OBJECT-TYPE
    SYNTAX       CfprApFabricExternalEpLocale
    MAX-ACCESS   read-only
    STATUS       current
    DESCRIPTION
        "Cisco Firepower fabric:FcVsanPortEp:locale managed
        object property"
    ::= { cfprApFabricFcVsanPortEpEntry 13 }

cfprApFabricFcVsanPortEpName OBJECT-TYPE
    SYNTAX       SnmpAdminString
    MAX-ACCESS   read-only
    STATUS       current
    DESCRIPTION
        "Cisco Firepower fabric:FcVsanPortEp:name managed object property"
    ::= { cfprApFabricFcVsanPortEpEntry 14 }

cfprApFabricFcVsanPortEpOperState OBJECT-TYPE
    SYNTAX       CfprApFabricPIoEpOperState
    MAX-ACCESS   read-only
    STATUS       current
    DESCRIPTION
        "Cisco Firepower fabric:FcVsanPortEp:operState
        managed object property"
    ::= { cfprApFabricFcVsanPortEpEntry 15 }

cfprApFabricFcVsanPortEpOperStateReason OBJECT-TYPE
    SYNTAX       SnmpAdminString
    MAX-ACCESS   read-only
    STATUS       current
    DESCRIPTION
        "Cisco Firepower fabric:FcVsanPortEp:operStateReason
        managed object property"
    ::= { cfprApFabricFcVsanPortEpEntry 16 }

cfprApFabricFcVsanPortEpPeerAggrPortId OBJECT-TYPE
    SYNTAX       Gauge32
    MAX-ACCESS   read-only
    STATUS       current
    DESCRIPTION
        "Cisco Firepower fabric:FcVsanPortEp:peerAggrPortId
        managed object property"
    ::= { cfprApFabricFcVsanPortEpEntry 17 }

cfprApFabricFcVsanPortEpPeerChassisId OBJECT-TYPE
    SYNTAX       Gauge32
    MAX-ACCESS   read-only
    STATUS       current
    DESCRIPTION
        "Cisco Firepower fabric:FcVsanPortEp:peerChassisId
        managed object property"
    ::= { cfprApFabricFcVsanPortEpEntry 18 }

cfprApFabricFcVsanPortEpPeerDn OBJECT-TYPE
    SYNTAX       SnmpAdminString
    MAX-ACCESS   read-only
    STATUS       current
    DESCRIPTION
        "Cisco Firepower fabric:FcVsanPortEp:peerDn managed
        object property"
    ::= { cfprApFabricFcVsanPortEpEntry 19 }

cfprApFabricFcVsanPortEpPeerPortId OBJECT-TYPE
    SYNTAX       Gauge32
    MAX-ACCESS   read-only
    STATUS       current
    DESCRIPTION
        "Cisco Firepower fabric:FcVsanPortEp:peerPortId
        managed object property"
    ::= { cfprApFabricFcVsanPortEpEntry 20 }

cfprApFabricFcVsanPortEpPeerSlotId OBJECT-TYPE
    SYNTAX       Gauge32
    MAX-ACCESS   read-only
    STATUS       current
    DESCRIPTION
        "Cisco Firepower fabric:FcVsanPortEp:peerSlotId
        managed object property"
    ::= { cfprApFabricFcVsanPortEpEntry 21 }

cfprApFabricFcVsanPortEpPortId OBJECT-TYPE
    SYNTAX       CfprApFabricFcVsanPortEpPortId
    MAX-ACCESS   read-only
    STATUS       current
    DESCRIPTION
        "Cisco Firepower fabric:FcVsanPortEp:portId managed
        object property"
    ::= { cfprApFabricFcVsanPortEpEntry 22 }

cfprApFabricFcVsanPortEpSlotId OBJECT-TYPE
    SYNTAX       CfprApFabricFcVsanPortEpSlotId
    MAX-ACCESS   read-only
    STATUS       current
    DESCRIPTION
        "Cisco Firepower fabric:FcVsanPortEp:slotId managed
        object property"
    ::= { cfprApFabricFcVsanPortEpEntry 23 }

cfprApFabricFcVsanPortEpSwitchId OBJECT-TYPE
    SYNTAX       CfprApNetworkSwitchId
    MAX-ACCESS   read-only
    STATUS       current
    DESCRIPTION
        "Cisco Firepower fabric:FcVsanPortEp:switchId managed
        object property"
    ::= { cfprApFabricFcVsanPortEpEntry 24 }

cfprApFabricFcVsanPortEpTransport OBJECT-TYPE
    SYNTAX       CfprApFabricAFcSanEpTransport
    MAX-ACCESS   read-only
    STATUS       current
    DESCRIPTION
        "Cisco Firepower fabric:FcVsanPortEp:transport
        managed object property"
    ::= { cfprApFabricFcVsanPortEpEntry 25 }

cfprApFabricFcVsanPortEpType OBJECT-TYPE
    SYNTAX       CfprApFabricSanEpType
    MAX-ACCESS   read-only
    STATUS       current
    DESCRIPTION
        "Cisco Firepower fabric:FcVsanPortEp:type managed object property"
    ::= { cfprApFabricFcVsanPortEpEntry 26 }

cfprApFabricFcVsanPortEpWarnings OBJECT-TYPE
    SYNTAX       CfprApFabricWarnings
    MAX-ACCESS   read-only
    STATUS       current
    DESCRIPTION
        "Cisco Firepower fabric:FcVsanPortEp:warnings managed
        object property"
    ::= { cfprApFabricFcVsanPortEpEntry 27 }

cfprApFabricFcoeSanEpTable OBJECT-TYPE
    SYNTAX           SEQUENCE OF CfprApFabricFcoeSanEpEntry
    MAX-ACCESS       not-accessible
    STATUS           current
    DESCRIPTION
        "Cisco Firepower fabric:FcoeSanEp managed object table"
    ::= { cfprApFabricObjects 59 }

cfprApFabricFcoeSanEpEntry OBJECT-TYPE
    SYNTAX           CfprApFabricFcoeSanEpEntry
    MAX-ACCESS       not-accessible
    STATUS           current
    DESCRIPTION
        "Entry for the cfprApFabricFcoeSanEpTable table."
    INDEX { cfprApFabricFcoeSanEpInstanceId }
    ::= { cfprApFabricFcoeSanEpTable 1 }

CfprApFabricFcoeSanEpEntry ::= SEQUENCE {
    cfprApFabricFcoeSanEpInstanceId                                  CfprApManagedObjectId,
    cfprApFabricFcoeSanEpDn                                          CfprApManagedObjectDn,
    cfprApFabricFcoeSanEpRn                                          SnmpAdminString,
    cfprApFabricFcoeSanEpAdminState                                  CfprApFabricExternalEpAdminState,
    cfprApFabricFcoeSanEpAggrPortId                                  Gauge32,
    cfprApFabricFcoeSanEpChassisId                                   Gauge32,
    cfprApFabricFcoeSanEpConfigState                                 CfprApFabricConfigState,
    cfprApFabricFcoeSanEpEpDn                                        SnmpAdminString,
    cfprApFabricFcoeSanEpEthLinkProfileName                          SnmpAdminString,
    cfprApFabricFcoeSanEpFcoeState                                   CfprApNetworkPortOperState,
    cfprApFabricFcoeSanEpFcoeStateReason                             SnmpAdminString,
    cfprApFabricFcoeSanEpFltAggr                                     Unsigned64,
    cfprApFabricFcoeSanEpIfRole                                      CfprApFabricSanEpIfRole,
    cfprApFabricFcoeSanEpIfType                                      CfprApFabricPIoEpIfType,
    cfprApFabricFcoeSanEpLicGP                                       Unsigned64,
    cfprApFabricFcoeSanEpLicState                                    CfprApLicenseState,
    cfprApFabricFcoeSanEpLocale                                      CfprApFabricExternalEpLocale,
    cfprApFabricFcoeSanEpName                                        SnmpAdminString,
    cfprApFabricFcoeSanEpOperEthLinkProfileName                      SnmpAdminString,
    cfprApFabricFcoeSanEpOperState                                   CfprApFabricPIoEpOperState,
    cfprApFabricFcoeSanEpOperStateReason                             SnmpAdminString,
    cfprApFabricFcoeSanEpPeerAggrPortId                              Gauge32,
    cfprApFabricFcoeSanEpPeerChassisId                               Gauge32,
    cfprApFabricFcoeSanEpPeerDn                                      SnmpAdminString,
    cfprApFabricFcoeSanEpPeerPortId                                  Gauge32,
    cfprApFabricFcoeSanEpPeerSlotId                                  Gauge32,
    cfprApFabricFcoeSanEpPortId                                      CfprApFabricFcoeSanEpPortId,
    cfprApFabricFcoeSanEpSlotId                                      CfprApFabricFcoeSanEpSlotId,
    cfprApFabricFcoeSanEpSwitchId                                    CfprApNetworkSwitchId,
    cfprApFabricFcoeSanEpTransport                                   CfprApFabricAFcoeSanEpTransport,
    cfprApFabricFcoeSanEpType                                        CfprApFabricSanEpType,
    cfprApFabricFcoeSanEpUdldOperState                               CfprApFabricUdldOperState,
    cfprApFabricFcoeSanEpUsrLbl                                      SnmpAdminString,
    cfprApFabricFcoeSanEpWarnings                                    CfprApFabricWarnings
}

cfprApFabricFcoeSanEpInstanceId OBJECT-TYPE
    SYNTAX       CfprApManagedObjectId
    MAX-ACCESS   not-accessible
    STATUS       current
    DESCRIPTION
        "Instance identifier of the managed object."
    ::= { cfprApFabricFcoeSanEpEntry 1 }

cfprApFabricFcoeSanEpDn OBJECT-TYPE
    SYNTAX       CfprApManagedObjectDn
    MAX-ACCESS   read-only
    STATUS       current
    DESCRIPTION
        "Cisco Firepower fabric:FcoeSanEp:dn managed object property"
    ::= { cfprApFabricFcoeSanEpEntry 2 }

cfprApFabricFcoeSanEpRn OBJECT-TYPE
    SYNTAX       SnmpAdminString
    MAX-ACCESS   read-only
    STATUS       current
    DESCRIPTION
        "Cisco Firepower fabric:FcoeSanEp:rn managed object property"
    ::= { cfprApFabricFcoeSanEpEntry 3 }

cfprApFabricFcoeSanEpAdminState OBJECT-TYPE
    SYNTAX       CfprApFabricExternalEpAdminState
    MAX-ACCESS   read-only
    STATUS       current
    DESCRIPTION
        "Cisco Firepower fabric:FcoeSanEp:adminState managed
        object property"
    ::= { cfprApFabricFcoeSanEpEntry 4 }

cfprApFabricFcoeSanEpAggrPortId OBJECT-TYPE
    SYNTAX       Gauge32
    MAX-ACCESS   read-only
    STATUS       current
    DESCRIPTION
        "Cisco Firepower fabric:FcoeSanEp:aggrPortId managed
        object property"
    ::= { cfprApFabricFcoeSanEpEntry 5 }

cfprApFabricFcoeSanEpChassisId OBJECT-TYPE
    SYNTAX       Gauge32
    MAX-ACCESS   read-only
    STATUS       current
    DESCRIPTION
        "Cisco Firepower fabric:FcoeSanEp:chassisId managed
        object property"
    ::= { cfprApFabricFcoeSanEpEntry 6 }

cfprApFabricFcoeSanEpConfigState OBJECT-TYPE
    SYNTAX       CfprApFabricConfigState
    MAX-ACCESS   read-only
    STATUS       current
    DESCRIPTION
        "Cisco Firepower fabric:FcoeSanEp:configState managed
        object property"
    ::= { cfprApFabricFcoeSanEpEntry 7 }

cfprApFabricFcoeSanEpEpDn OBJECT-TYPE
    SYNTAX       SnmpAdminString
    MAX-ACCESS   read-only
    STATUS       current
    DESCRIPTION
        "Cisco Firepower fabric:FcoeSanEp:epDn managed object property"
    ::= { cfprApFabricFcoeSanEpEntry 8 }

cfprApFabricFcoeSanEpEthLinkProfileName OBJECT-TYPE
    SYNTAX       SnmpAdminString
    MAX-ACCESS   read-only
    STATUS       current
    DESCRIPTION
        "Cisco Firepower fabric:FcoeSanEp:ethLinkProfileName
        managed object property"
    ::= { cfprApFabricFcoeSanEpEntry 9 }

cfprApFabricFcoeSanEpFcoeState OBJECT-TYPE
    SYNTAX       CfprApNetworkPortOperState
    MAX-ACCESS   read-only
    STATUS       current
    DESCRIPTION
        "Cisco Firepower fabric:FcoeSanEp:fcoeState managed
        object property"
    ::= { cfprApFabricFcoeSanEpEntry 10 }

cfprApFabricFcoeSanEpFcoeStateReason OBJECT-TYPE
    SYNTAX       SnmpAdminString
    MAX-ACCESS   read-only
    STATUS       current
    DESCRIPTION
        "Cisco Firepower fabric:FcoeSanEp:fcoeStateReason
        managed object property"
    ::= { cfprApFabricFcoeSanEpEntry 11 }

cfprApFabricFcoeSanEpFltAggr OBJECT-TYPE
    SYNTAX       Unsigned64
    MAX-ACCESS   read-only
    STATUS       current
    DESCRIPTION
        "Cisco Firepower fabric:FcoeSanEp:fltAggr managed object property"
    ::= { cfprApFabricFcoeSanEpEntry 12 }

cfprApFabricFcoeSanEpIfRole OBJECT-TYPE
    SYNTAX       CfprApFabricSanEpIfRole
    MAX-ACCESS   read-only
    STATUS       current
    DESCRIPTION
        "Cisco Firepower fabric:FcoeSanEp:ifRole managed object property"
    ::= { cfprApFabricFcoeSanEpEntry 13 }

cfprApFabricFcoeSanEpIfType OBJECT-TYPE
    SYNTAX       CfprApFabricPIoEpIfType
    MAX-ACCESS   read-only
    STATUS       current
    DESCRIPTION
        "Cisco Firepower fabric:FcoeSanEp:ifType managed object property"
    ::= { cfprApFabricFcoeSanEpEntry 14 }

cfprApFabricFcoeSanEpLicGP OBJECT-TYPE
    SYNTAX       Unsigned64
    MAX-ACCESS   read-only
    STATUS       current
    DESCRIPTION
        "Cisco Firepower fabric:FcoeSanEp:licGP managed object property"
    ::= { cfprApFabricFcoeSanEpEntry 15 }

cfprApFabricFcoeSanEpLicState OBJECT-TYPE
    SYNTAX       CfprApLicenseState
    MAX-ACCESS   read-only
    STATUS       current
    DESCRIPTION
        "Cisco Firepower fabric:FcoeSanEp:licState managed
        object property"
    ::= { cfprApFabricFcoeSanEpEntry 16 }

cfprApFabricFcoeSanEpLocale OBJECT-TYPE
    SYNTAX       CfprApFabricExternalEpLocale
    MAX-ACCESS   read-only
    STATUS       current
    DESCRIPTION
        "Cisco Firepower fabric:FcoeSanEp:locale managed object property"
    ::= { cfprApFabricFcoeSanEpEntry 17 }

cfprApFabricFcoeSanEpName OBJECT-TYPE
    SYNTAX       SnmpAdminString
    MAX-ACCESS   read-only
    STATUS       current
    DESCRIPTION
        "Cisco Firepower fabric:FcoeSanEp:name managed object property"
    ::= { cfprApFabricFcoeSanEpEntry 18 }

cfprApFabricFcoeSanEpOperEthLinkProfileName OBJECT-TYPE
    SYNTAX       SnmpAdminString
    MAX-ACCESS   read-only
    STATUS       current
    DESCRIPTION
        "Cisco Firepower fabric:FcoeSanEp:operEthLinkProfileName
        managed object property"
    ::= { cfprApFabricFcoeSanEpEntry 19 }

cfprApFabricFcoeSanEpOperState OBJECT-TYPE
    SYNTAX       CfprApFabricPIoEpOperState
    MAX-ACCESS   read-only
    STATUS       current
    DESCRIPTION
        "Cisco Firepower fabric:FcoeSanEp:operState managed
        object property"
    ::= { cfprApFabricFcoeSanEpEntry 20 }

cfprApFabricFcoeSanEpOperStateReason OBJECT-TYPE
    SYNTAX       SnmpAdminString
    MAX-ACCESS   read-only
    STATUS       current
    DESCRIPTION
        "Cisco Firepower fabric:FcoeSanEp:operStateReason
        managed object property"
    ::= { cfprApFabricFcoeSanEpEntry 21 }

cfprApFabricFcoeSanEpPeerAggrPortId OBJECT-TYPE
    SYNTAX       Gauge32
    MAX-ACCESS   read-only
    STATUS       current
    DESCRIPTION
        "Cisco Firepower fabric:FcoeSanEp:peerAggrPortId
        managed object property"
    ::= { cfprApFabricFcoeSanEpEntry 22 }

cfprApFabricFcoeSanEpPeerChassisId OBJECT-TYPE
    SYNTAX       Gauge32
    MAX-ACCESS   read-only
    STATUS       current
    DESCRIPTION
        "Cisco Firepower fabric:FcoeSanEp:peerChassisId
        managed object property"
    ::= { cfprApFabricFcoeSanEpEntry 23 }

cfprApFabricFcoeSanEpPeerDn OBJECT-TYPE
    SYNTAX       SnmpAdminString
    MAX-ACCESS   read-only
    STATUS       current
    DESCRIPTION
        "Cisco Firepower fabric:FcoeSanEp:peerDn managed object property"
    ::= { cfprApFabricFcoeSanEpEntry 24 }

cfprApFabricFcoeSanEpPeerPortId OBJECT-TYPE
    SYNTAX       Gauge32
    MAX-ACCESS   read-only
    STATUS       current
    DESCRIPTION
        "Cisco Firepower fabric:FcoeSanEp:peerPortId managed
        object property"
    ::= { cfprApFabricFcoeSanEpEntry 25 }

cfprApFabricFcoeSanEpPeerSlotId OBJECT-TYPE
    SYNTAX       Gauge32
    MAX-ACCESS   read-only
    STATUS       current
    DESCRIPTION
        "Cisco Firepower fabric:FcoeSanEp:peerSlotId managed
        object property"
    ::= { cfprApFabricFcoeSanEpEntry 26 }

cfprApFabricFcoeSanEpPortId OBJECT-TYPE
    SYNTAX       CfprApFabricFcoeSanEpPortId
    MAX-ACCESS   read-only
    STATUS       current
    DESCRIPTION
        "Cisco Firepower fabric:FcoeSanEp:portId managed object property"
    ::= { cfprApFabricFcoeSanEpEntry 27 }

cfprApFabricFcoeSanEpSlotId OBJECT-TYPE
    SYNTAX       CfprApFabricFcoeSanEpSlotId
    MAX-ACCESS   read-only
    STATUS       current
    DESCRIPTION
        "Cisco Firepower fabric:FcoeSanEp:slotId managed object property"
    ::= { cfprApFabricFcoeSanEpEntry 28 }

cfprApFabricFcoeSanEpSwitchId OBJECT-TYPE
    SYNTAX       CfprApNetworkSwitchId
    MAX-ACCESS   read-only
    STATUS       current
    DESCRIPTION
        "Cisco Firepower fabric:FcoeSanEp:switchId managed
        object property"
    ::= { cfprApFabricFcoeSanEpEntry 29 }

cfprApFabricFcoeSanEpTransport OBJECT-TYPE
    SYNTAX       CfprApFabricAFcoeSanEpTransport
    MAX-ACCESS   read-only
    STATUS       current
    DESCRIPTION
        "Cisco Firepower fabric:FcoeSanEp:transport managed
        object property"
    ::= { cfprApFabricFcoeSanEpEntry 30 }

cfprApFabricFcoeSanEpType OBJECT-TYPE
    SYNTAX       CfprApFabricSanEpType
    MAX-ACCESS   read-only
    STATUS       current
    DESCRIPTION
        "Cisco Firepower fabric:FcoeSanEp:type managed object property"
    ::= { cfprApFabricFcoeSanEpEntry 31 }

cfprApFabricFcoeSanEpUdldOperState OBJECT-TYPE
    SYNTAX       CfprApFabricUdldOperState
    MAX-ACCESS   read-only
    STATUS       current
    DESCRIPTION
        "Cisco Firepower fabric:FcoeSanEp:udldOperState
        managed object property"
    ::= { cfprApFabricFcoeSanEpEntry 32 }

cfprApFabricFcoeSanEpUsrLbl OBJECT-TYPE
    SYNTAX       SnmpAdminString
    MAX-ACCESS   read-only
    STATUS       current
    DESCRIPTION
        "Cisco Firepower fabric:FcoeSanEp:usrLbl managed object property"
    ::= { cfprApFabricFcoeSanEpEntry 33 }

cfprApFabricFcoeSanEpWarnings OBJECT-TYPE
    SYNTAX       CfprApFabricWarnings
    MAX-ACCESS   read-only
    STATUS       current
    DESCRIPTION
        "Cisco Firepower fabric:FcoeSanEp:warnings managed
        object property"
    ::= { cfprApFabricFcoeSanEpEntry 34 }

cfprApFabricFcoeSanPcTable OBJECT-TYPE
    SYNTAX           SEQUENCE OF CfprApFabricFcoeSanPcEntry
    MAX-ACCESS       not-accessible
    STATUS           current
    DESCRIPTION
        "Cisco Firepower fabric:FcoeSanPc managed object table"
    ::= { cfprApFabricObjects 60 }

cfprApFabricFcoeSanPcEntry OBJECT-TYPE
    SYNTAX           CfprApFabricFcoeSanPcEntry
    MAX-ACCESS       not-accessible
    STATUS           current
    DESCRIPTION
        "Entry for the cfprApFabricFcoeSanPcTable table."
    INDEX { cfprApFabricFcoeSanPcInstanceId }
    ::= { cfprApFabricFcoeSanPcTable 1 }

CfprApFabricFcoeSanPcEntry ::= SEQUENCE {
    cfprApFabricFcoeSanPcInstanceId                                  CfprApManagedObjectId,
    cfprApFabricFcoeSanPcDn                                          CfprApManagedObjectDn,
    cfprApFabricFcoeSanPcRn                                          SnmpAdminString,
    cfprApFabricFcoeSanPcAdminState                                  CfprApFabricCIoEpAdminState,
    cfprApFabricFcoeSanPcConfigState                                 CfprApFabricConfigState,
    cfprApFabricFcoeSanPcDescr                                       SnmpAdminString,
    cfprApFabricFcoeSanPcEpDn                                        SnmpAdminString,
    cfprApFabricFcoeSanPcFcoeState                                   CfprApNetworkPortOperState,
    cfprApFabricFcoeSanPcFcoeStateReason                             SnmpAdminString,
    cfprApFabricFcoeSanPcFltAggr                                     Unsigned64,
    cfprApFabricFcoeSanPcIfRole                                      CfprApFabricSanPcIfRole,
    cfprApFabricFcoeSanPcIfType                                      CfprApFabricCIoEpIfType,
    cfprApFabricFcoeSanPcLacpPolicyName                              SnmpAdminString,
    cfprApFabricFcoeSanPcLocale                                      CfprApFabricExternalPcLocale,
    cfprApFabricFcoeSanPcName                                        SnmpAdminString,
    cfprApFabricFcoeSanPcOperLacpPolicyName                          SnmpAdminString,
    cfprApFabricFcoeSanPcOperState                                   CfprApNetworkPortOperState,
    cfprApFabricFcoeSanPcPeerDn                                      SnmpAdminString,
    cfprApFabricFcoeSanPcPortId                                      Gauge32,
    cfprApFabricFcoeSanPcStateQual                                   SnmpAdminString,
    cfprApFabricFcoeSanPcSwitchId                                    CfprApNetworkSwitchId,
    cfprApFabricFcoeSanPcTransport                                   CfprApFabricFcoeSanPcTransport,
    cfprApFabricFcoeSanPcType                                        CfprApFabricSanPcType,
    cfprApFabricFcoeSanPcWarnings                                    CfprApFabricWarnings
}

cfprApFabricFcoeSanPcInstanceId OBJECT-TYPE
    SYNTAX       CfprApManagedObjectId
    MAX-ACCESS   not-accessible
    STATUS       current
    DESCRIPTION
        "Instance identifier of the managed object."
    ::= { cfprApFabricFcoeSanPcEntry 1 }

cfprApFabricFcoeSanPcDn OBJECT-TYPE
    SYNTAX       CfprApManagedObjectDn
    MAX-ACCESS   read-only
    STATUS       current
    DESCRIPTION
        "Cisco Firepower fabric:FcoeSanPc:dn managed object property"
    ::= { cfprApFabricFcoeSanPcEntry 2 }

cfprApFabricFcoeSanPcRn OBJECT-TYPE
    SYNTAX       SnmpAdminString
    MAX-ACCESS   read-only
    STATUS       current
    DESCRIPTION
        "Cisco Firepower fabric:FcoeSanPc:rn managed object property"
    ::= { cfprApFabricFcoeSanPcEntry 3 }

cfprApFabricFcoeSanPcAdminState OBJECT-TYPE
    SYNTAX       CfprApFabricCIoEpAdminState
    MAX-ACCESS   read-only
    STATUS       current
    DESCRIPTION
        "Cisco Firepower fabric:FcoeSanPc:adminState managed
        object property"
    ::= { cfprApFabricFcoeSanPcEntry 4 }

cfprApFabricFcoeSanPcConfigState OBJECT-TYPE
    SYNTAX       CfprApFabricConfigState
    MAX-ACCESS   read-only
    STATUS       current
    DESCRIPTION
        "Cisco Firepower fabric:FcoeSanPc:configState managed
        object property"
    ::= { cfprApFabricFcoeSanPcEntry 5 }

cfprApFabricFcoeSanPcDescr OBJECT-TYPE
    SYNTAX       SnmpAdminString
    MAX-ACCESS   read-only
    STATUS       current
    DESCRIPTION
        "Cisco Firepower fabric:FcoeSanPc:descr managed object property"
    ::= { cfprApFabricFcoeSanPcEntry 6 }

cfprApFabricFcoeSanPcEpDn OBJECT-TYPE
    SYNTAX       SnmpAdminString
    MAX-ACCESS   read-only
    STATUS       current
    DESCRIPTION
        "Cisco Firepower fabric:FcoeSanPc:epDn managed object property"
    ::= { cfprApFabricFcoeSanPcEntry 7 }

cfprApFabricFcoeSanPcFcoeState OBJECT-TYPE
    SYNTAX       CfprApNetworkPortOperState
    MAX-ACCESS   read-only
    STATUS       current
    DESCRIPTION
        "Cisco Firepower fabric:FcoeSanPc:fcoeState managed
        object property"
    ::= { cfprApFabricFcoeSanPcEntry 8 }

cfprApFabricFcoeSanPcFcoeStateReason OBJECT-TYPE
    SYNTAX       SnmpAdminString
    MAX-ACCESS   read-only
    STATUS       current
    DESCRIPTION
        "Cisco Firepower fabric:FcoeSanPc:fcoeStateReason
        managed object property"
    ::= { cfprApFabricFcoeSanPcEntry 9 }

cfprApFabricFcoeSanPcFltAggr OBJECT-TYPE
    SYNTAX       Unsigned64
    MAX-ACCESS   read-only
    STATUS       current
    DESCRIPTION
        "Cisco Firepower fabric:FcoeSanPc:fltAggr managed object property"
    ::= { cfprApFabricFcoeSanPcEntry 10 }

cfprApFabricFcoeSanPcIfRole OBJECT-TYPE
    SYNTAX       CfprApFabricSanPcIfRole
    MAX-ACCESS   read-only
    STATUS       current
    DESCRIPTION
        "Cisco Firepower fabric:FcoeSanPc:ifRole managed object property"
    ::= { cfprApFabricFcoeSanPcEntry 11 }

cfprApFabricFcoeSanPcIfType OBJECT-TYPE
    SYNTAX       CfprApFabricCIoEpIfType
    MAX-ACCESS   read-only
    STATUS       current
    DESCRIPTION
        "Cisco Firepower fabric:FcoeSanPc:ifType managed object property"
    ::= { cfprApFabricFcoeSanPcEntry 12 }

cfprApFabricFcoeSanPcLacpPolicyName OBJECT-TYPE
    SYNTAX       SnmpAdminString
    MAX-ACCESS   read-only
    STATUS       current
    DESCRIPTION
        "Cisco Firepower fabric:FcoeSanPc:lacpPolicyName
        managed object property"
    ::= { cfprApFabricFcoeSanPcEntry 13 }

cfprApFabricFcoeSanPcLocale OBJECT-TYPE
    SYNTAX       CfprApFabricExternalPcLocale
    MAX-ACCESS   read-only
    STATUS       current
    DESCRIPTION
        "Cisco Firepower fabric:FcoeSanPc:locale managed object property"
    ::= { cfprApFabricFcoeSanPcEntry 14 }

cfprApFabricFcoeSanPcName OBJECT-TYPE
    SYNTAX       SnmpAdminString
    MAX-ACCESS   read-only
    STATUS       current
    DESCRIPTION
        "Cisco Firepower fabric:FcoeSanPc:name managed object property"
    ::= { cfprApFabricFcoeSanPcEntry 15 }

cfprApFabricFcoeSanPcOperLacpPolicyName OBJECT-TYPE
    SYNTAX       SnmpAdminString
    MAX-ACCESS   read-only
    STATUS       current
    DESCRIPTION
        "Cisco Firepower fabric:FcoeSanPc:operLacpPolicyName
        managed object property"
    ::= { cfprApFabricFcoeSanPcEntry 16 }

cfprApFabricFcoeSanPcOperState OBJECT-TYPE
    SYNTAX       CfprApNetworkPortOperState
    MAX-ACCESS   read-only
    STATUS       current
    DESCRIPTION
        "Cisco Firepower fabric:FcoeSanPc:operState managed
        object property"
    ::= { cfprApFabricFcoeSanPcEntry 17 }

cfprApFabricFcoeSanPcPeerDn OBJECT-TYPE
    SYNTAX       SnmpAdminString
    MAX-ACCESS   read-only
    STATUS       current
    DESCRIPTION
        "Cisco Firepower fabric:FcoeSanPc:peerDn managed object property"
    ::= { cfprApFabricFcoeSanPcEntry 18 }

cfprApFabricFcoeSanPcPortId OBJECT-TYPE
    SYNTAX       Gauge32
    MAX-ACCESS   read-only
    STATUS       current
    DESCRIPTION
        "Cisco Firepower fabric:FcoeSanPc:portId managed object property"
    ::= { cfprApFabricFcoeSanPcEntry 19 }

cfprApFabricFcoeSanPcStateQual OBJECT-TYPE
    SYNTAX       SnmpAdminString
    MAX-ACCESS   read-only
    STATUS       current
    DESCRIPTION
        "Cisco Firepower fabric:FcoeSanPc:stateQual managed
        object property"
    ::= { cfprApFabricFcoeSanPcEntry 20 }

cfprApFabricFcoeSanPcSwitchId OBJECT-TYPE
    SYNTAX       CfprApNetworkSwitchId
    MAX-ACCESS   read-only
    STATUS       current
    DESCRIPTION
        "Cisco Firepower fabric:FcoeSanPc:switchId managed
        object property"
    ::= { cfprApFabricFcoeSanPcEntry 21 }

cfprApFabricFcoeSanPcTransport OBJECT-TYPE
    SYNTAX       CfprApFabricFcoeSanPcTransport
    MAX-ACCESS   read-only
    STATUS       current
    DESCRIPTION
        "Cisco Firepower fabric:FcoeSanPc:transport managed
        object property"
    ::= { cfprApFabricFcoeSanPcEntry 22 }

cfprApFabricFcoeSanPcType OBJECT-TYPE
    SYNTAX       CfprApFabricSanPcType
    MAX-ACCESS   read-only
    STATUS       current
    DESCRIPTION
        "Cisco Firepower fabric:FcoeSanPc:type managed object property"
    ::= { cfprApFabricFcoeSanPcEntry 23 }

cfprApFabricFcoeSanPcWarnings OBJECT-TYPE
    SYNTAX       CfprApFabricWarnings
    MAX-ACCESS   read-only
    STATUS       current
    DESCRIPTION
        "Cisco Firepower fabric:FcoeSanPc:warnings managed
        object property"
    ::= { cfprApFabricFcoeSanPcEntry 24 }

cfprApFabricFcoeSanPcEpTable OBJECT-TYPE
    SYNTAX           SEQUENCE OF CfprApFabricFcoeSanPcEpEntry
    MAX-ACCESS       not-accessible
    STATUS           current
    DESCRIPTION
        "Cisco Firepower fabric:FcoeSanPcEp managed object table"
    ::= { cfprApFabricObjects 61 }

cfprApFabricFcoeSanPcEpEntry OBJECT-TYPE
    SYNTAX           CfprApFabricFcoeSanPcEpEntry
    MAX-ACCESS       not-accessible
    STATUS           current
    DESCRIPTION
        "Entry for the cfprApFabricFcoeSanPcEpTable table."
    INDEX { cfprApFabricFcoeSanPcEpInstanceId }
    ::= { cfprApFabricFcoeSanPcEpTable 1 }

CfprApFabricFcoeSanPcEpEntry ::= SEQUENCE {
    cfprApFabricFcoeSanPcEpInstanceId                                CfprApManagedObjectId,
    cfprApFabricFcoeSanPcEpDnData                                    CfprApManagedObjectDn,
    cfprApFabricFcoeSanPcEpRn                                        SnmpAdminString,
    cfprApFabricFcoeSanPcEpAdminState                                CfprApFabricExternalEpAdminState,
    cfprApFabricFcoeSanPcEpAggrPortId                                Gauge32,
    cfprApFabricFcoeSanPcEpChassisId                                 Gauge32,
    cfprApFabricFcoeSanPcEpEpDn                                      SnmpAdminString,
    cfprApFabricFcoeSanPcEpEthLinkProfileName                        SnmpAdminString,
    cfprApFabricFcoeSanPcEpFltAggr                                   Unsigned64,
    cfprApFabricFcoeSanPcEpIfRole                                    CfprApFabricSanEpIfRole,
    cfprApFabricFcoeSanPcEpIfType                                    CfprApFabricPIoEpIfType,
    cfprApFabricFcoeSanPcEpLicGP                                     Unsigned64,
    cfprApFabricFcoeSanPcEpLicState                                  CfprApLicenseState,
    cfprApFabricFcoeSanPcEpLocale                                    CfprApFabricExternalEpLocale,
    cfprApFabricFcoeSanPcEpMembership                                CfprApFabricMembershipStatus,
    cfprApFabricFcoeSanPcEpName                                      SnmpAdminString,
    cfprApFabricFcoeSanPcEpOperEthLinkProfileName                    SnmpAdminString,
    cfprApFabricFcoeSanPcEpOperState                                 CfprApFabricPIoEpOperState,
    cfprApFabricFcoeSanPcEpOperStateReason                           SnmpAdminString,
    cfprApFabricFcoeSanPcEpPeerAggrPortId                            Gauge32,
    cfprApFabricFcoeSanPcEpPeerChassisId                             Gauge32,
    cfprApFabricFcoeSanPcEpPeerDn                                    SnmpAdminString,
    cfprApFabricFcoeSanPcEpPeerPortId                                Gauge32,
    cfprApFabricFcoeSanPcEpPeerSlotId                                Gauge32,
    cfprApFabricFcoeSanPcEpPortId                                    CfprApFabricFcoeSanPcEpPortId,
    cfprApFabricFcoeSanPcEpSlotId                                    CfprApFabricFcoeSanPcEpSlotId,
    cfprApFabricFcoeSanPcEpSwitchId                                  CfprApNetworkSwitchId,
    cfprApFabricFcoeSanPcEpTransport                                 CfprApFabricAFcoeSanEpTransport,
    cfprApFabricFcoeSanPcEpType                                      CfprApFabricSanEpType,
    cfprApFabricFcoeSanPcEpUdldOperState                             CfprApFabricUdldOperState,
    cfprApFabricFcoeSanPcEpWarnings                                  CfprApFabricWarnings
}

cfprApFabricFcoeSanPcEpInstanceId OBJECT-TYPE
    SYNTAX       CfprApManagedObjectId
    MAX-ACCESS   not-accessible
    STATUS       current
    DESCRIPTION
        "Instance identifier of the managed object."
    ::= { cfprApFabricFcoeSanPcEpEntry 1 }

cfprApFabricFcoeSanPcEpDnData OBJECT-TYPE
    SYNTAX       CfprApManagedObjectDn
    MAX-ACCESS   read-only
    STATUS       current
    DESCRIPTION
        "Cisco Firepower fabric:FcoeSanPcEp:dn managed object property"
    ::= { cfprApFabricFcoeSanPcEpEntry 2 }

cfprApFabricFcoeSanPcEpRn OBJECT-TYPE
    SYNTAX       SnmpAdminString
    MAX-ACCESS   read-only
    STATUS       current
    DESCRIPTION
        "Cisco Firepower fabric:FcoeSanPcEp:rn managed object property"
    ::= { cfprApFabricFcoeSanPcEpEntry 3 }

cfprApFabricFcoeSanPcEpAdminState OBJECT-TYPE
    SYNTAX       CfprApFabricExternalEpAdminState
    MAX-ACCESS   read-only
    STATUS       current
    DESCRIPTION
        "Cisco Firepower fabric:FcoeSanPcEp:adminState
        managed object property"
    ::= { cfprApFabricFcoeSanPcEpEntry 4 }

cfprApFabricFcoeSanPcEpAggrPortId OBJECT-TYPE
    SYNTAX       Gauge32
    MAX-ACCESS   read-only
    STATUS       current
    DESCRIPTION
        "Cisco Firepower fabric:FcoeSanPcEp:aggrPortId
        managed object property"
    ::= { cfprApFabricFcoeSanPcEpEntry 5 }

cfprApFabricFcoeSanPcEpChassisId OBJECT-TYPE
    SYNTAX       Gauge32
    MAX-ACCESS   read-only
    STATUS       current
    DESCRIPTION
        "Cisco Firepower fabric:FcoeSanPcEp:chassisId managed
        object property"
    ::= { cfprApFabricFcoeSanPcEpEntry 6 }

cfprApFabricFcoeSanPcEpEpDn OBJECT-TYPE
    SYNTAX       SnmpAdminString
    MAX-ACCESS   read-only
    STATUS       current
    DESCRIPTION
        "Cisco Firepower fabric:FcoeSanPcEp:epDn managed object property"
    ::= { cfprApFabricFcoeSanPcEpEntry 7 }

cfprApFabricFcoeSanPcEpEthLinkProfileName OBJECT-TYPE
    SYNTAX       SnmpAdminString
    MAX-ACCESS   read-only
    STATUS       current
    DESCRIPTION
        "Cisco Firepower fabric:FcoeSanPcEp:ethLinkProfileName
        managed object property"
    ::= { cfprApFabricFcoeSanPcEpEntry 8 }

cfprApFabricFcoeSanPcEpFltAggr OBJECT-TYPE
    SYNTAX       Unsigned64
    MAX-ACCESS   read-only
    STATUS       current
    DESCRIPTION
        "Cisco Firepower fabric:FcoeSanPcEp:fltAggr managed
        object property"
    ::= { cfprApFabricFcoeSanPcEpEntry 9 }

cfprApFabricFcoeSanPcEpIfRole OBJECT-TYPE
    SYNTAX       CfprApFabricSanEpIfRole
    MAX-ACCESS   read-only
    STATUS       current
    DESCRIPTION
        "Cisco Firepower fabric:FcoeSanPcEp:ifRole managed
        object property"
    ::= { cfprApFabricFcoeSanPcEpEntry 10 }

cfprApFabricFcoeSanPcEpIfType OBJECT-TYPE
    SYNTAX       CfprApFabricPIoEpIfType
    MAX-ACCESS   read-only
    STATUS       current
    DESCRIPTION
        "Cisco Firepower fabric:FcoeSanPcEp:ifType managed
        object property"
    ::= { cfprApFabricFcoeSanPcEpEntry 11 }

cfprApFabricFcoeSanPcEpLicGP OBJECT-TYPE
    SYNTAX       Unsigned64
    MAX-ACCESS   read-only
    STATUS       current
    DESCRIPTION
        "Cisco Firepower fabric:FcoeSanPcEp:licGP managed object property"
    ::= { cfprApFabricFcoeSanPcEpEntry 12 }

cfprApFabricFcoeSanPcEpLicState OBJECT-TYPE
    SYNTAX       CfprApLicenseState
    MAX-ACCESS   read-only
    STATUS       current
    DESCRIPTION
        "Cisco Firepower fabric:FcoeSanPcEp:licState managed
        object property"
    ::= { cfprApFabricFcoeSanPcEpEntry 13 }

cfprApFabricFcoeSanPcEpLocale OBJECT-TYPE
    SYNTAX       CfprApFabricExternalEpLocale
    MAX-ACCESS   read-only
    STATUS       current
    DESCRIPTION
        "Cisco Firepower fabric:FcoeSanPcEp:locale managed
        object property"
    ::= { cfprApFabricFcoeSanPcEpEntry 14 }

cfprApFabricFcoeSanPcEpMembership OBJECT-TYPE
    SYNTAX       CfprApFabricMembershipStatus
    MAX-ACCESS   read-only
    STATUS       current
    DESCRIPTION
        "Cisco Firepower fabric:FcoeSanPcEp:membership
        managed object property"
    ::= { cfprApFabricFcoeSanPcEpEntry 15 }

cfprApFabricFcoeSanPcEpName OBJECT-TYPE
    SYNTAX       SnmpAdminString
    MAX-ACCESS   read-only
    STATUS       current
    DESCRIPTION
        "Cisco Firepower fabric:FcoeSanPcEp:name managed object property"
    ::= { cfprApFabricFcoeSanPcEpEntry 16 }

cfprApFabricFcoeSanPcEpOperEthLinkProfileName OBJECT-TYPE
    SYNTAX       SnmpAdminString
    MAX-ACCESS   read-only
    STATUS       current
    DESCRIPTION
        "Cisco Firepower fabric:FcoeSanPcEp:operEthLinkProfileName
        managed object property"
    ::= { cfprApFabricFcoeSanPcEpEntry 17 }

cfprApFabricFcoeSanPcEpOperState OBJECT-TYPE
    SYNTAX       CfprApFabricPIoEpOperState
    MAX-ACCESS   read-only
    STATUS       current
    DESCRIPTION
        "Cisco Firepower fabric:FcoeSanPcEp:operState managed
        object property"
    ::= { cfprApFabricFcoeSanPcEpEntry 18 }

cfprApFabricFcoeSanPcEpOperStateReason OBJECT-TYPE
    SYNTAX       SnmpAdminString
    MAX-ACCESS   read-only
    STATUS       current
    DESCRIPTION
        "Cisco Firepower fabric:FcoeSanPcEp:operStateReason
        managed object property"
    ::= { cfprApFabricFcoeSanPcEpEntry 19 }

cfprApFabricFcoeSanPcEpPeerAggrPortId OBJECT-TYPE
    SYNTAX       Gauge32
    MAX-ACCESS   read-only
    STATUS       current
    DESCRIPTION
        "Cisco Firepower fabric:FcoeSanPcEp:peerAggrPortId
        managed object property"
    ::= { cfprApFabricFcoeSanPcEpEntry 20 }

cfprApFabricFcoeSanPcEpPeerChassisId OBJECT-TYPE
    SYNTAX       Gauge32
    MAX-ACCESS   read-only
    STATUS       current
    DESCRIPTION
        "Cisco Firepower fabric:FcoeSanPcEp:peerChassisId
        managed object property"
    ::= { cfprApFabricFcoeSanPcEpEntry 21 }

cfprApFabricFcoeSanPcEpPeerDn OBJECT-TYPE
    SYNTAX       SnmpAdminString
    MAX-ACCESS   read-only
    STATUS       current
    DESCRIPTION
        "Cisco Firepower fabric:FcoeSanPcEp:peerDn managed
        object property"
    ::= { cfprApFabricFcoeSanPcEpEntry 22 }

cfprApFabricFcoeSanPcEpPeerPortId OBJECT-TYPE
    SYNTAX       Gauge32
    MAX-ACCESS   read-only
    STATUS       current
    DESCRIPTION
        "Cisco Firepower fabric:FcoeSanPcEp:peerPortId
        managed object property"
    ::= { cfprApFabricFcoeSanPcEpEntry 23 }

cfprApFabricFcoeSanPcEpPeerSlotId OBJECT-TYPE
    SYNTAX       Gauge32
    MAX-ACCESS   read-only
    STATUS       current
    DESCRIPTION
        "Cisco Firepower fabric:FcoeSanPcEp:peerSlotId
        managed object property"
    ::= { cfprApFabricFcoeSanPcEpEntry 24 }

cfprApFabricFcoeSanPcEpPortId OBJECT-TYPE
    SYNTAX       CfprApFabricFcoeSanPcEpPortId
    MAX-ACCESS   read-only
    STATUS       current
    DESCRIPTION
        "Cisco Firepower fabric:FcoeSanPcEp:portId managed
        object property"
    ::= { cfprApFabricFcoeSanPcEpEntry 25 }

cfprApFabricFcoeSanPcEpSlotId OBJECT-TYPE
    SYNTAX       CfprApFabricFcoeSanPcEpSlotId
    MAX-ACCESS   read-only
    STATUS       current
    DESCRIPTION
        "Cisco Firepower fabric:FcoeSanPcEp:slotId managed
        object property"
    ::= { cfprApFabricFcoeSanPcEpEntry 26 }

cfprApFabricFcoeSanPcEpSwitchId OBJECT-TYPE
    SYNTAX       CfprApNetworkSwitchId
    MAX-ACCESS   read-only
    STATUS       current
    DESCRIPTION
        "Cisco Firepower fabric:FcoeSanPcEp:switchId managed
        object property"
    ::= { cfprApFabricFcoeSanPcEpEntry 27 }

cfprApFabricFcoeSanPcEpTransport OBJECT-TYPE
    SYNTAX       CfprApFabricAFcoeSanEpTransport
    MAX-ACCESS   read-only
    STATUS       current
    DESCRIPTION
        "Cisco Firepower fabric:FcoeSanPcEp:transport managed
        object property"
    ::= { cfprApFabricFcoeSanPcEpEntry 28 }

cfprApFabricFcoeSanPcEpType OBJECT-TYPE
    SYNTAX       CfprApFabricSanEpType
    MAX-ACCESS   read-only
    STATUS       current
    DESCRIPTION
        "Cisco Firepower fabric:FcoeSanPcEp:type managed object property"
    ::= { cfprApFabricFcoeSanPcEpEntry 29 }

cfprApFabricFcoeSanPcEpUdldOperState OBJECT-TYPE
    SYNTAX       CfprApFabricUdldOperState
    MAX-ACCESS   read-only
    STATUS       current
    DESCRIPTION
        "Cisco Firepower fabric:FcoeSanPcEp:udldOperState
        managed object property"
    ::= { cfprApFabricFcoeSanPcEpEntry 30 }

cfprApFabricFcoeSanPcEpWarnings OBJECT-TYPE
    SYNTAX       CfprApFabricWarnings
    MAX-ACCESS   read-only
    STATUS       current
    DESCRIPTION
        "Cisco Firepower fabric:FcoeSanPcEp:warnings managed
        object property"
    ::= { cfprApFabricFcoeSanPcEpEntry 31 }

cfprApFabricFcoeVsanPcTable OBJECT-TYPE
    SYNTAX           SEQUENCE OF CfprApFabricFcoeVsanPcEntry
    MAX-ACCESS       not-accessible
    STATUS           current
    DESCRIPTION
        "Cisco Firepower fabric:FcoeVsanPc managed object table"
    ::= { cfprApFabricObjects 62 }

cfprApFabricFcoeVsanPcEntry OBJECT-TYPE
    SYNTAX           CfprApFabricFcoeVsanPcEntry
    MAX-ACCESS       not-accessible
    STATUS           current
    DESCRIPTION
        "Entry for the cfprApFabricFcoeVsanPcTable table."
    INDEX { cfprApFabricFcoeVsanPcInstanceId }
    ::= { cfprApFabricFcoeVsanPcTable 1 }

CfprApFabricFcoeVsanPcEntry ::= SEQUENCE {
    cfprApFabricFcoeVsanPcInstanceId                                 CfprApManagedObjectId,
    cfprApFabricFcoeVsanPcDn                                         CfprApManagedObjectDn,
    cfprApFabricFcoeVsanPcRn                                         SnmpAdminString,
    cfprApFabricFcoeVsanPcAdminState                                 CfprApFabricCIoEpAdminState,
    cfprApFabricFcoeVsanPcDescr                                      SnmpAdminString,
    cfprApFabricFcoeVsanPcEpDn                                       SnmpAdminString,
    cfprApFabricFcoeVsanPcFltAggr                                    Unsigned64,
    cfprApFabricFcoeVsanPcIfRole                                     CfprApFabricSanPcIfRole,
    cfprApFabricFcoeVsanPcIfType                                     CfprApFabricCIoEpIfType,
    cfprApFabricFcoeVsanPcLocale                                     CfprApFabricExternalPcLocale,
    cfprApFabricFcoeVsanPcName                                       SnmpAdminString,
    cfprApFabricFcoeVsanPcOperState                                  CfprApNetworkPortOperState,
    cfprApFabricFcoeVsanPcPeerDn                                     SnmpAdminString,
    cfprApFabricFcoeVsanPcPortId                                     Gauge32,
    cfprApFabricFcoeVsanPcStateQual                                  SnmpAdminString,
    cfprApFabricFcoeVsanPcSwitchId                                   CfprApNetworkSwitchId,
    cfprApFabricFcoeVsanPcTransport                                  CfprApFabricFcoeVsanPcTransport,
    cfprApFabricFcoeVsanPcType                                       CfprApFabricSanPcType,
    cfprApFabricFcoeVsanPcWarnings                                   CfprApFabricWarnings
}

cfprApFabricFcoeVsanPcInstanceId OBJECT-TYPE
    SYNTAX       CfprApManagedObjectId
    MAX-ACCESS   not-accessible
    STATUS       current
    DESCRIPTION
        "Instance identifier of the managed object."
    ::= { cfprApFabricFcoeVsanPcEntry 1 }

cfprApFabricFcoeVsanPcDn OBJECT-TYPE
    SYNTAX       CfprApManagedObjectDn
    MAX-ACCESS   read-only
    STATUS       current
    DESCRIPTION
        "Cisco Firepower fabric:FcoeVsanPc:dn managed object property"
    ::= { cfprApFabricFcoeVsanPcEntry 2 }

cfprApFabricFcoeVsanPcRn OBJECT-TYPE
    SYNTAX       SnmpAdminString
    MAX-ACCESS   read-only
    STATUS       current
    DESCRIPTION
        "Cisco Firepower fabric:FcoeVsanPc:rn managed object property"
    ::= { cfprApFabricFcoeVsanPcEntry 3 }

cfprApFabricFcoeVsanPcAdminState OBJECT-TYPE
    SYNTAX       CfprApFabricCIoEpAdminState
    MAX-ACCESS   read-only
    STATUS       current
    DESCRIPTION
        "Cisco Firepower fabric:FcoeVsanPc:adminState managed
        object property"
    ::= { cfprApFabricFcoeVsanPcEntry 4 }

cfprApFabricFcoeVsanPcDescr OBJECT-TYPE
    SYNTAX       SnmpAdminString
    MAX-ACCESS   read-only
    STATUS       current
    DESCRIPTION
        "Cisco Firepower fabric:FcoeVsanPc:descr managed object property"
    ::= { cfprApFabricFcoeVsanPcEntry 5 }

cfprApFabricFcoeVsanPcEpDn OBJECT-TYPE
    SYNTAX       SnmpAdminString
    MAX-ACCESS   read-only
    STATUS       current
    DESCRIPTION
        "Cisco Firepower fabric:FcoeVsanPc:epDn managed object property"
    ::= { cfprApFabricFcoeVsanPcEntry 6 }

cfprApFabricFcoeVsanPcFltAggr OBJECT-TYPE
    SYNTAX       Unsigned64
    MAX-ACCESS   read-only
    STATUS       current
    DESCRIPTION
        "Cisco Firepower fabric:FcoeVsanPc:fltAggr managed
        object property"
    ::= { cfprApFabricFcoeVsanPcEntry 7 }

cfprApFabricFcoeVsanPcIfRole OBJECT-TYPE
    SYNTAX       CfprApFabricSanPcIfRole
    MAX-ACCESS   read-only
    STATUS       current
    DESCRIPTION
        "Cisco Firepower fabric:FcoeVsanPc:ifRole managed object property"
    ::= { cfprApFabricFcoeVsanPcEntry 8 }

cfprApFabricFcoeVsanPcIfType OBJECT-TYPE
    SYNTAX       CfprApFabricCIoEpIfType
    MAX-ACCESS   read-only
    STATUS       current
    DESCRIPTION
        "Cisco Firepower fabric:FcoeVsanPc:ifType managed object property"
    ::= { cfprApFabricFcoeVsanPcEntry 9 }

cfprApFabricFcoeVsanPcLocale OBJECT-TYPE
    SYNTAX       CfprApFabricExternalPcLocale
    MAX-ACCESS   read-only
    STATUS       current
    DESCRIPTION
        "Cisco Firepower fabric:FcoeVsanPc:locale managed object property"
    ::= { cfprApFabricFcoeVsanPcEntry 10 }

cfprApFabricFcoeVsanPcName OBJECT-TYPE
    SYNTAX       SnmpAdminString
    MAX-ACCESS   read-only
    STATUS       current
    DESCRIPTION
        "Cisco Firepower fabric:FcoeVsanPc:name managed object property"
    ::= { cfprApFabricFcoeVsanPcEntry 11 }

cfprApFabricFcoeVsanPcOperState OBJECT-TYPE
    SYNTAX       CfprApNetworkPortOperState
    MAX-ACCESS   read-only
    STATUS       current
    DESCRIPTION
        "Cisco Firepower fabric:FcoeVsanPc:operState managed
        object property"
    ::= { cfprApFabricFcoeVsanPcEntry 12 }

cfprApFabricFcoeVsanPcPeerDn OBJECT-TYPE
    SYNTAX       SnmpAdminString
    MAX-ACCESS   read-only
    STATUS       current
    DESCRIPTION
        "Cisco Firepower fabric:FcoeVsanPc:peerDn managed object property"
    ::= { cfprApFabricFcoeVsanPcEntry 13 }

cfprApFabricFcoeVsanPcPortId OBJECT-TYPE
    SYNTAX       Gauge32
    MAX-ACCESS   read-only
    STATUS       current
    DESCRIPTION
        "Cisco Firepower fabric:FcoeVsanPc:portId managed object property"
    ::= { cfprApFabricFcoeVsanPcEntry 14 }

cfprApFabricFcoeVsanPcStateQual OBJECT-TYPE
    SYNTAX       SnmpAdminString
    MAX-ACCESS   read-only
    STATUS       current
    DESCRIPTION
        "Cisco Firepower fabric:FcoeVsanPc:stateQual managed
        object property"
    ::= { cfprApFabricFcoeVsanPcEntry 15 }

cfprApFabricFcoeVsanPcSwitchId OBJECT-TYPE
    SYNTAX       CfprApNetworkSwitchId
    MAX-ACCESS   read-only
    STATUS       current
    DESCRIPTION
        "Cisco Firepower fabric:FcoeVsanPc:switchId managed
        object property"
    ::= { cfprApFabricFcoeVsanPcEntry 16 }

cfprApFabricFcoeVsanPcTransport OBJECT-TYPE
    SYNTAX       CfprApFabricFcoeVsanPcTransport
    MAX-ACCESS   read-only
    STATUS       current
    DESCRIPTION
        "Cisco Firepower fabric:FcoeVsanPc:transport managed
        object property"
    ::= { cfprApFabricFcoeVsanPcEntry 17 }

cfprApFabricFcoeVsanPcType OBJECT-TYPE
    SYNTAX       CfprApFabricSanPcType
    MAX-ACCESS   read-only
    STATUS       current
    DESCRIPTION
        "Cisco Firepower fabric:FcoeVsanPc:type managed object property"
    ::= { cfprApFabricFcoeVsanPcEntry 18 }

cfprApFabricFcoeVsanPcWarnings OBJECT-TYPE
    SYNTAX       CfprApFabricWarnings
    MAX-ACCESS   read-only
    STATUS       current
    DESCRIPTION
        "Cisco Firepower fabric:FcoeVsanPc:warnings managed
        object property"
    ::= { cfprApFabricFcoeVsanPcEntry 19 }

cfprApFabricFcoeVsanPortEpTable OBJECT-TYPE
    SYNTAX           SEQUENCE OF CfprApFabricFcoeVsanPortEpEntry
    MAX-ACCESS       not-accessible
    STATUS           current
    DESCRIPTION
        "Cisco Firepower fabric:FcoeVsanPortEp managed object table"
    ::= { cfprApFabricObjects 63 }

cfprApFabricFcoeVsanPortEpEntry OBJECT-TYPE
    SYNTAX           CfprApFabricFcoeVsanPortEpEntry
    MAX-ACCESS       not-accessible
    STATUS           current
    DESCRIPTION
        "Entry for the cfprApFabricFcoeVsanPortEpTable table."
    INDEX { cfprApFabricFcoeVsanPortEpInstanceId }
    ::= { cfprApFabricFcoeVsanPortEpTable 1 }

CfprApFabricFcoeVsanPortEpEntry ::= SEQUENCE {
    cfprApFabricFcoeVsanPortEpInstanceId                             CfprApManagedObjectId,
    cfprApFabricFcoeVsanPortEpDn                                     CfprApManagedObjectDn,
    cfprApFabricFcoeVsanPortEpRn                                     SnmpAdminString,
    cfprApFabricFcoeVsanPortEpAdminState                             CfprApFabricExternalEpAdminState,
    cfprApFabricFcoeVsanPortEpAggrPortId                             Gauge32,
    cfprApFabricFcoeVsanPortEpChassisId                              Gauge32,
    cfprApFabricFcoeVsanPortEpEpDn                                   SnmpAdminString,
    cfprApFabricFcoeVsanPortEpFltAggr                                Unsigned64,
    cfprApFabricFcoeVsanPortEpIfRole                                 CfprApFabricSanEpIfRole,
    cfprApFabricFcoeVsanPortEpIfType                                 CfprApFabricPIoEpIfType,
    cfprApFabricFcoeVsanPortEpLicGP                                  Unsigned64,
    cfprApFabricFcoeVsanPortEpLicState                               CfprApLicenseState,
    cfprApFabricFcoeVsanPortEpLocale                                 CfprApFabricExternalEpLocale,
    cfprApFabricFcoeVsanPortEpName                                   SnmpAdminString,
    cfprApFabricFcoeVsanPortEpOperState                              CfprApFabricPIoEpOperState,
    cfprApFabricFcoeVsanPortEpOperStateReason                        SnmpAdminString,
    cfprApFabricFcoeVsanPortEpPeerAggrPortId                         Gauge32,
    cfprApFabricFcoeVsanPortEpPeerChassisId                          Gauge32,
    cfprApFabricFcoeVsanPortEpPeerDn                                 SnmpAdminString,
    cfprApFabricFcoeVsanPortEpPeerPortId                             Gauge32,
    cfprApFabricFcoeVsanPortEpPeerSlotId                             Gauge32,
    cfprApFabricFcoeVsanPortEpPortId                                 CfprApFabricFcoeVsanPortEpPortId,
    cfprApFabricFcoeVsanPortEpSlotId                                 CfprApFabricFcoeVsanPortEpSlotId,
    cfprApFabricFcoeVsanPortEpSwitchId                               CfprApNetworkSwitchId,
    cfprApFabricFcoeVsanPortEpTransport                              CfprApFabricAFcSanEpTransport,
    cfprApFabricFcoeVsanPortEpType                                   CfprApFabricSanEpType,
    cfprApFabricFcoeVsanPortEpWarnings                               CfprApFabricWarnings
}

cfprApFabricFcoeVsanPortEpInstanceId OBJECT-TYPE
    SYNTAX       CfprApManagedObjectId
    MAX-ACCESS   not-accessible
    STATUS       current
    DESCRIPTION
        "Instance identifier of the managed object."
    ::= { cfprApFabricFcoeVsanPortEpEntry 1 }

cfprApFabricFcoeVsanPortEpDn OBJECT-TYPE
    SYNTAX       CfprApManagedObjectDn
    MAX-ACCESS   read-only
    STATUS       current
    DESCRIPTION
        "Cisco Firepower fabric:FcoeVsanPortEp:dn managed object property"
    ::= { cfprApFabricFcoeVsanPortEpEntry 2 }

cfprApFabricFcoeVsanPortEpRn OBJECT-TYPE
    SYNTAX       SnmpAdminString
    MAX-ACCESS   read-only
    STATUS       current
    DESCRIPTION
        "Cisco Firepower fabric:FcoeVsanPortEp:rn managed object property"
    ::= { cfprApFabricFcoeVsanPortEpEntry 3 }

cfprApFabricFcoeVsanPortEpAdminState OBJECT-TYPE
    SYNTAX       CfprApFabricExternalEpAdminState
    MAX-ACCESS   read-only
    STATUS       current
    DESCRIPTION
        "Cisco Firepower fabric:FcoeVsanPortEp:adminState
        managed object property"
    ::= { cfprApFabricFcoeVsanPortEpEntry 4 }

cfprApFabricFcoeVsanPortEpAggrPortId OBJECT-TYPE
    SYNTAX       Gauge32
    MAX-ACCESS   read-only
    STATUS       current
    DESCRIPTION
        "Cisco Firepower fabric:FcoeVsanPortEp:aggrPortId
        managed object property"
    ::= { cfprApFabricFcoeVsanPortEpEntry 5 }

cfprApFabricFcoeVsanPortEpChassisId OBJECT-TYPE
    SYNTAX       Gauge32
    MAX-ACCESS   read-only
    STATUS       current
    DESCRIPTION
        "Cisco Firepower fabric:FcoeVsanPortEp:chassisId
        managed object property"
    ::= { cfprApFabricFcoeVsanPortEpEntry 6 }

cfprApFabricFcoeVsanPortEpEpDn OBJECT-TYPE
    SYNTAX       SnmpAdminString
    MAX-ACCESS   read-only
    STATUS       current
    DESCRIPTION
        "Cisco Firepower fabric:FcoeVsanPortEp:epDn managed
        object property"
    ::= { cfprApFabricFcoeVsanPortEpEntry 7 }

cfprApFabricFcoeVsanPortEpFltAggr OBJECT-TYPE
    SYNTAX       Unsigned64
    MAX-ACCESS   read-only
    STATUS       current
    DESCRIPTION
        "Cisco Firepower fabric:FcoeVsanPortEp:fltAggr
        managed object property"
    ::= { cfprApFabricFcoeVsanPortEpEntry 8 }

cfprApFabricFcoeVsanPortEpIfRole OBJECT-TYPE
    SYNTAX       CfprApFabricSanEpIfRole
    MAX-ACCESS   read-only
    STATUS       current
    DESCRIPTION
        "Cisco Firepower fabric:FcoeVsanPortEp:ifRole managed
        object property"
    ::= { cfprApFabricFcoeVsanPortEpEntry 9 }

cfprApFabricFcoeVsanPortEpIfType OBJECT-TYPE
    SYNTAX       CfprApFabricPIoEpIfType
    MAX-ACCESS   read-only
    STATUS       current
    DESCRIPTION
        "Cisco Firepower fabric:FcoeVsanPortEp:ifType managed
        object property"
    ::= { cfprApFabricFcoeVsanPortEpEntry 10 }

cfprApFabricFcoeVsanPortEpLicGP OBJECT-TYPE
    SYNTAX       Unsigned64
    MAX-ACCESS   read-only
    STATUS       current
    DESCRIPTION
        "Cisco Firepower fabric:FcoeVsanPortEp:licGP managed
        object property"
    ::= { cfprApFabricFcoeVsanPortEpEntry 11 }

cfprApFabricFcoeVsanPortEpLicState OBJECT-TYPE
    SYNTAX       CfprApLicenseState
    MAX-ACCESS   read-only
    STATUS       current
    DESCRIPTION
        "Cisco Firepower fabric:FcoeVsanPortEp:licState
        managed object property"
    ::= { cfprApFabricFcoeVsanPortEpEntry 12 }

cfprApFabricFcoeVsanPortEpLocale OBJECT-TYPE
    SYNTAX       CfprApFabricExternalEpLocale
    MAX-ACCESS   read-only
    STATUS       current
    DESCRIPTION
        "Cisco Firepower fabric:FcoeVsanPortEp:locale managed
        object property"
    ::= { cfprApFabricFcoeVsanPortEpEntry 13 }

cfprApFabricFcoeVsanPortEpName OBJECT-TYPE
    SYNTAX       SnmpAdminString
    MAX-ACCESS   read-only
    STATUS       current
    DESCRIPTION
        "Cisco Firepower fabric:FcoeVsanPortEp:name managed
        object property"
    ::= { cfprApFabricFcoeVsanPortEpEntry 14 }

cfprApFabricFcoeVsanPortEpOperState OBJECT-TYPE
    SYNTAX       CfprApFabricPIoEpOperState
    MAX-ACCESS   read-only
    STATUS       current
    DESCRIPTION
        "Cisco Firepower fabric:FcoeVsanPortEp:operState
        managed object property"
    ::= { cfprApFabricFcoeVsanPortEpEntry 15 }

cfprApFabricFcoeVsanPortEpOperStateReason OBJECT-TYPE
    SYNTAX       SnmpAdminString
    MAX-ACCESS   read-only
    STATUS       current
    DESCRIPTION
        "Cisco Firepower fabric:FcoeVsanPortEp:operStateReason
        managed object property"
    ::= { cfprApFabricFcoeVsanPortEpEntry 16 }

cfprApFabricFcoeVsanPortEpPeerAggrPortId OBJECT-TYPE
    SYNTAX       Gauge32
    MAX-ACCESS   read-only
    STATUS       current
    DESCRIPTION
        "Cisco Firepower fabric:FcoeVsanPortEp:peerAggrPortId
        managed object property"
    ::= { cfprApFabricFcoeVsanPortEpEntry 17 }

cfprApFabricFcoeVsanPortEpPeerChassisId OBJECT-TYPE
    SYNTAX       Gauge32
    MAX-ACCESS   read-only
    STATUS       current
    DESCRIPTION
        "Cisco Firepower fabric:FcoeVsanPortEp:peerChassisId
        managed object property"
    ::= { cfprApFabricFcoeVsanPortEpEntry 18 }

cfprApFabricFcoeVsanPortEpPeerDn OBJECT-TYPE
    SYNTAX       SnmpAdminString
    MAX-ACCESS   read-only
    STATUS       current
    DESCRIPTION
        "Cisco Firepower fabric:FcoeVsanPortEp:peerDn managed
        object property"
    ::= { cfprApFabricFcoeVsanPortEpEntry 19 }

cfprApFabricFcoeVsanPortEpPeerPortId OBJECT-TYPE
    SYNTAX       Gauge32
    MAX-ACCESS   read-only
    STATUS       current
    DESCRIPTION
        "Cisco Firepower fabric:FcoeVsanPortEp:peerPortId
        managed object property"
    ::= { cfprApFabricFcoeVsanPortEpEntry 20 }

cfprApFabricFcoeVsanPortEpPeerSlotId OBJECT-TYPE
    SYNTAX       Gauge32
    MAX-ACCESS   read-only
    STATUS       current
    DESCRIPTION
        "Cisco Firepower fabric:FcoeVsanPortEp:peerSlotId
        managed object property"
    ::= { cfprApFabricFcoeVsanPortEpEntry 21 }

cfprApFabricFcoeVsanPortEpPortId OBJECT-TYPE
    SYNTAX       CfprApFabricFcoeVsanPortEpPortId
    MAX-ACCESS   read-only
    STATUS       current
    DESCRIPTION
        "Cisco Firepower fabric:FcoeVsanPortEp:portId managed
        object property"
    ::= { cfprApFabricFcoeVsanPortEpEntry 22 }

cfprApFabricFcoeVsanPortEpSlotId OBJECT-TYPE
    SYNTAX       CfprApFabricFcoeVsanPortEpSlotId
    MAX-ACCESS   read-only
    STATUS       current
    DESCRIPTION
        "Cisco Firepower fabric:FcoeVsanPortEp:slotId managed
        object property"
    ::= { cfprApFabricFcoeVsanPortEpEntry 23 }

cfprApFabricFcoeVsanPortEpSwitchId OBJECT-TYPE
    SYNTAX       CfprApNetworkSwitchId
    MAX-ACCESS   read-only
    STATUS       current
    DESCRIPTION
        "Cisco Firepower fabric:FcoeVsanPortEp:switchId
        managed object property"
    ::= { cfprApFabricFcoeVsanPortEpEntry 24 }

cfprApFabricFcoeVsanPortEpTransport OBJECT-TYPE
    SYNTAX       CfprApFabricAFcSanEpTransport
    MAX-ACCESS   read-only
    STATUS       current
    DESCRIPTION
        "Cisco Firepower fabric:FcoeVsanPortEp:transport
        managed object property"
    ::= { cfprApFabricFcoeVsanPortEpEntry 25 }

cfprApFabricFcoeVsanPortEpType OBJECT-TYPE
    SYNTAX       CfprApFabricSanEpType
    MAX-ACCESS   read-only
    STATUS       current
    DESCRIPTION
        "Cisco Firepower fabric:FcoeVsanPortEp:type managed
        object property"
    ::= { cfprApFabricFcoeVsanPortEpEntry 26 }

cfprApFabricFcoeVsanPortEpWarnings OBJECT-TYPE
    SYNTAX       CfprApFabricWarnings
    MAX-ACCESS   read-only
    STATUS       current
    DESCRIPTION
        "Cisco Firepower fabric:FcoeVsanPortEp:warnings
        managed object property"
    ::= { cfprApFabricFcoeVsanPortEpEntry 27 }

cfprApFabricIfTable OBJECT-TYPE
    SYNTAX           SEQUENCE OF CfprApFabricIfEntry
    MAX-ACCESS       not-accessible
    STATUS           current
    DESCRIPTION
        "Cisco Firepower fabric:If managed object table"
    ::= { cfprApFabricObjects 66 }

cfprApFabricIfEntry OBJECT-TYPE
    SYNTAX           CfprApFabricIfEntry
    MAX-ACCESS       not-accessible
    STATUS           current
    DESCRIPTION
        "Entry for the cfprApFabricIfTable table."
    INDEX { cfprApFabricIfInstanceId }
    ::= { cfprApFabricIfTable 1 }

CfprApFabricIfEntry ::= SEQUENCE {
    cfprApFabricIfInstanceId                                         CfprApManagedObjectId,
    cfprApFabricIfDn                                                 CfprApManagedObjectDn,
    cfprApFabricIfRn                                                 SnmpAdminString,
    cfprApFabricIfAddr                                               InetAddressIPv4,
    cfprApFabricIfId                                                 CfprApNetworkSwitchId
}

cfprApFabricIfInstanceId OBJECT-TYPE
    SYNTAX       CfprApManagedObjectId
    MAX-ACCESS   not-accessible
    STATUS       current
    DESCRIPTION
        "Instance identifier of the managed object."
    ::= { cfprApFabricIfEntry 1 }

cfprApFabricIfDn OBJECT-TYPE
    SYNTAX       CfprApManagedObjectDn
    MAX-ACCESS   read-only
    STATUS       current
    DESCRIPTION
        "Cisco Firepower fabric:If:dn managed object property"
    ::= { cfprApFabricIfEntry 2 }

cfprApFabricIfRn OBJECT-TYPE
    SYNTAX       SnmpAdminString
    MAX-ACCESS   read-only
    STATUS       current
    DESCRIPTION
        "Cisco Firepower fabric:If:rn managed object property"
    ::= { cfprApFabricIfEntry 3 }

cfprApFabricIfAddr OBJECT-TYPE
    SYNTAX       InetAddressIPv4
    MAX-ACCESS   read-only
    STATUS       current
    DESCRIPTION
        "Cisco Firepower fabric:If:addr managed object property"
    ::= { cfprApFabricIfEntry 4 }

cfprApFabricIfId OBJECT-TYPE
    SYNTAX       CfprApNetworkSwitchId
    MAX-ACCESS   read-only
    STATUS       current
    DESCRIPTION
        "Cisco Firepower fabric:If:id managed object property"
    ::= { cfprApFabricIfEntry 5 }

cfprApFabricLacpPolicyTable OBJECT-TYPE
    SYNTAX           SEQUENCE OF CfprApFabricLacpPolicyEntry
    MAX-ACCESS       not-accessible
    STATUS           current
    DESCRIPTION
        "Cisco Firepower fabric:LacpPolicy managed object table"
    ::= { cfprApFabricObjects 67 }

cfprApFabricLacpPolicyEntry OBJECT-TYPE
    SYNTAX           CfprApFabricLacpPolicyEntry
    MAX-ACCESS       not-accessible
    STATUS           current
    DESCRIPTION
        "Entry for the cfprApFabricLacpPolicyTable table."
    INDEX { cfprApFabricLacpPolicyInstanceId }
    ::= { cfprApFabricLacpPolicyTable 1 }

CfprApFabricLacpPolicyEntry ::= SEQUENCE {
    cfprApFabricLacpPolicyInstanceId                                 CfprApManagedObjectId,
    cfprApFabricLacpPolicyDn                                         CfprApManagedObjectDn,
    cfprApFabricLacpPolicyRn                                         SnmpAdminString,
    cfprApFabricLacpPolicyDescr                                      SnmpAdminString,
    cfprApFabricLacpPolicyFastTimer                                  CfprApFabricLacpRate,
    cfprApFabricLacpPolicyIntId                                      SnmpAdminString,
    cfprApFabricLacpPolicyName                                       SnmpAdminString,
    cfprApFabricLacpPolicyPolicyLevel                                Gauge32,
    cfprApFabricLacpPolicyPolicyOwner                                CfprApPolicyPolicyOwner,
    cfprApFabricLacpPolicySuspendIndividual                          CfprApFabricLacpSuspend
}

cfprApFabricLacpPolicyInstanceId OBJECT-TYPE
    SYNTAX       CfprApManagedObjectId
    MAX-ACCESS   not-accessible
    STATUS       current
    DESCRIPTION
        "Instance identifier of the managed object."
    ::= { cfprApFabricLacpPolicyEntry 1 }

cfprApFabricLacpPolicyDn OBJECT-TYPE
    SYNTAX       CfprApManagedObjectDn
    MAX-ACCESS   read-only
    STATUS       current
    DESCRIPTION
        "Cisco Firepower fabric:LacpPolicy:dn managed object property"
    ::= { cfprApFabricLacpPolicyEntry 2 }

cfprApFabricLacpPolicyRn OBJECT-TYPE
    SYNTAX       SnmpAdminString
    MAX-ACCESS   read-only
    STATUS       current
    DESCRIPTION
        "Cisco Firepower fabric:LacpPolicy:rn managed object property"
    ::= { cfprApFabricLacpPolicyEntry 3 }

cfprApFabricLacpPolicyDescr OBJECT-TYPE
    SYNTAX       SnmpAdminString
    MAX-ACCESS   read-only
    STATUS       current
    DESCRIPTION
        "Cisco Firepower fabric:LacpPolicy:descr managed object property"
    ::= { cfprApFabricLacpPolicyEntry 4 }

cfprApFabricLacpPolicyFastTimer OBJECT-TYPE
    SYNTAX       CfprApFabricLacpRate
    MAX-ACCESS   read-only
    STATUS       current
    DESCRIPTION
        "Cisco Firepower fabric:LacpPolicy:fastTimer managed
        object property"
    ::= { cfprApFabricLacpPolicyEntry 5 }

cfprApFabricLacpPolicyIntId OBJECT-TYPE
    SYNTAX       SnmpAdminString
    MAX-ACCESS   read-only
    STATUS       current
    DESCRIPTION
        "Cisco Firepower fabric:LacpPolicy:intId managed object property"
    ::= { cfprApFabricLacpPolicyEntry 6 }

cfprApFabricLacpPolicyName OBJECT-TYPE
    SYNTAX       SnmpAdminString
    MAX-ACCESS   read-only
    STATUS       current
    DESCRIPTION
        "Cisco Firepower fabric:LacpPolicy:name managed object property"
    ::= { cfprApFabricLacpPolicyEntry 7 }

cfprApFabricLacpPolicyPolicyLevel OBJECT-TYPE
    SYNTAX       Gauge32
    MAX-ACCESS   read-only
    STATUS       current
    DESCRIPTION
        "Cisco Firepower fabric:LacpPolicy:policyLevel
        managed object property"
    ::= { cfprApFabricLacpPolicyEntry 8 }

cfprApFabricLacpPolicyPolicyOwner OBJECT-TYPE
    SYNTAX       CfprApPolicyPolicyOwner
    MAX-ACCESS   read-only
    STATUS       current
    DESCRIPTION
        "Cisco Firepower fabric:LacpPolicy:policyOwner
        managed object property"
    ::= { cfprApFabricLacpPolicyEntry 9 }

cfprApFabricLacpPolicySuspendIndividual OBJECT-TYPE
    SYNTAX       CfprApFabricLacpSuspend
    MAX-ACCESS   read-only
    STATUS       current
    DESCRIPTION
        "Cisco Firepower fabric:LacpPolicy:suspendIndividual
        managed object property"
    ::= { cfprApFabricLacpPolicyEntry 10 }

cfprApFabricLanAccessMgrTable OBJECT-TYPE
    SYNTAX           SEQUENCE OF CfprApFabricLanAccessMgrEntry
    MAX-ACCESS       not-accessible
    STATUS           current
    DESCRIPTION
        "Cisco Firepower fabric:LanAccessMgr managed object table"
    ::= { cfprApFabricObjects 68 }

cfprApFabricLanAccessMgrEntry OBJECT-TYPE
    SYNTAX           CfprApFabricLanAccessMgrEntry
    MAX-ACCESS       not-accessible
    STATUS           current
    DESCRIPTION
        "Entry for the cfprApFabricLanAccessMgrTable table."
    INDEX { cfprApFabricLanAccessMgrInstanceId }
    ::= { cfprApFabricLanAccessMgrTable 1 }

CfprApFabricLanAccessMgrEntry ::= SEQUENCE {
    cfprApFabricLanAccessMgrInstanceId                               CfprApManagedObjectId,
    cfprApFabricLanAccessMgrDn                                       CfprApManagedObjectDn,
    cfprApFabricLanAccessMgrRn                                       SnmpAdminString
}

cfprApFabricLanAccessMgrInstanceId OBJECT-TYPE
    SYNTAX       CfprApManagedObjectId
    MAX-ACCESS   not-accessible
    STATUS       current
    DESCRIPTION
        "Instance identifier of the managed object."
    ::= { cfprApFabricLanAccessMgrEntry 1 }

cfprApFabricLanAccessMgrDn OBJECT-TYPE
    SYNTAX       CfprApManagedObjectDn
    MAX-ACCESS   read-only
    STATUS       current
    DESCRIPTION
        "Cisco Firepower fabric:LanAccessMgr:dn managed object property"
    ::= { cfprApFabricLanAccessMgrEntry 2 }

cfprApFabricLanAccessMgrRn OBJECT-TYPE
    SYNTAX       SnmpAdminString
    MAX-ACCESS   read-only
    STATUS       current
    DESCRIPTION
        "Cisco Firepower fabric:LanAccessMgr:rn managed object property"
    ::= { cfprApFabricLanAccessMgrEntry 3 }

cfprApFabricLanCloudTable OBJECT-TYPE
    SYNTAX           SEQUENCE OF CfprApFabricLanCloudEntry
    MAX-ACCESS       not-accessible
    STATUS           current
    DESCRIPTION
        "Cisco Firepower fabric:LanCloud managed object table"
    ::= { cfprApFabricObjects 69 }

cfprApFabricLanCloudEntry OBJECT-TYPE
    SYNTAX           CfprApFabricLanCloudEntry
    MAX-ACCESS       not-accessible
    STATUS           current
    DESCRIPTION
        "Entry for the cfprApFabricLanCloudTable table."
    INDEX { cfprApFabricLanCloudInstanceId }
    ::= { cfprApFabricLanCloudTable 1 }

CfprApFabricLanCloudEntry ::= SEQUENCE {
    cfprApFabricLanCloudInstanceId                                   CfprApManagedObjectId,
    cfprApFabricLanCloudDn                                           CfprApManagedObjectDn,
    cfprApFabricLanCloudRn                                           SnmpAdminString,
    cfprApFabricLanCloudFsmDescr                                     SnmpAdminString,
    cfprApFabricLanCloudFsmPrev                                      SnmpAdminString,
    cfprApFabricLanCloudFsmProgr                                     Gauge32,
    cfprApFabricLanCloudFsmRmtInvErrCode                             Gauge32,
    cfprApFabricLanCloudFsmRmtInvErrDescr                            SnmpAdminString,
    cfprApFabricLanCloudFsmRmtInvRslt                                CfprApConditionRemoteInvRslt,
    cfprApFabricLanCloudFsmStageDescr                                SnmpAdminString,
    cfprApFabricLanCloudFsmStamp                                     DateAndTime,
    cfprApFabricLanCloudFsmStatus                                    SnmpAdminString,
    cfprApFabricLanCloudFsmTry                                       Gauge32,
    cfprApFabricLanCloudMacAging                                     TimeIntervalSec,
    cfprApFabricLanCloudMode                                         CfprApFabricSwitchingMode,
    cfprApFabricLanCloudVlanCompression                              CfprApFabricLanCloudVlanCompression
}

cfprApFabricLanCloudInstanceId OBJECT-TYPE
    SYNTAX       CfprApManagedObjectId
    MAX-ACCESS   not-accessible
    STATUS       current
    DESCRIPTION
        "Instance identifier of the managed object."
    ::= { cfprApFabricLanCloudEntry 1 }

cfprApFabricLanCloudDn OBJECT-TYPE
    SYNTAX       CfprApManagedObjectDn
    MAX-ACCESS   read-only
    STATUS       current
    DESCRIPTION
        "Cisco Firepower fabric:LanCloud:dn managed object property"
    ::= { cfprApFabricLanCloudEntry 2 }

cfprApFabricLanCloudRn OBJECT-TYPE
    SYNTAX       SnmpAdminString
    MAX-ACCESS   read-only
    STATUS       current
    DESCRIPTION
        "Cisco Firepower fabric:LanCloud:rn managed object property"
    ::= { cfprApFabricLanCloudEntry 3 }

cfprApFabricLanCloudFsmDescr OBJECT-TYPE
    SYNTAX       SnmpAdminString
    MAX-ACCESS   read-only
    STATUS       current
    DESCRIPTION
        "Cisco Firepower fabric:LanCloud:fsmDescr managed object property"
    ::= { cfprApFabricLanCloudEntry 4 }

cfprApFabricLanCloudFsmPrev OBJECT-TYPE
    SYNTAX       SnmpAdminString
    MAX-ACCESS   read-only
    STATUS       current
    DESCRIPTION
        "Cisco Firepower fabric:LanCloud:fsmPrev managed object property"
    ::= { cfprApFabricLanCloudEntry 5 }

cfprApFabricLanCloudFsmProgr OBJECT-TYPE
    SYNTAX       Gauge32
    MAX-ACCESS   read-only
    STATUS       current
    DESCRIPTION
        "Cisco Firepower fabric:LanCloud:fsmProgr managed object property"
    ::= { cfprApFabricLanCloudEntry 6 }

cfprApFabricLanCloudFsmRmtInvErrCode OBJECT-TYPE
    SYNTAX       Gauge32
    MAX-ACCESS   read-only
    STATUS       current
    DESCRIPTION
        "Cisco Firepower fabric:LanCloud:fsmRmtInvErrCode
        managed object property"
    ::= { cfprApFabricLanCloudEntry 7 }

cfprApFabricLanCloudFsmRmtInvErrDescr OBJECT-TYPE
    SYNTAX       SnmpAdminString
    MAX-ACCESS   read-only
    STATUS       current
    DESCRIPTION
        "Cisco Firepower fabric:LanCloud:fsmRmtInvErrDescr
        managed object property"
    ::= { cfprApFabricLanCloudEntry 8 }

cfprApFabricLanCloudFsmRmtInvRslt OBJECT-TYPE
    SYNTAX       CfprApConditionRemoteInvRslt
    MAX-ACCESS   read-only
    STATUS       current
    DESCRIPTION
        "Cisco Firepower fabric:LanCloud:fsmRmtInvRslt
        managed object property"
    ::= { cfprApFabricLanCloudEntry 9 }

cfprApFabricLanCloudFsmStageDescr OBJECT-TYPE
    SYNTAX       SnmpAdminString
    MAX-ACCESS   read-only
    STATUS       current
    DESCRIPTION
        "Cisco Firepower fabric:LanCloud:fsmStageDescr
        managed object property"
    ::= { cfprApFabricLanCloudEntry 10 }

cfprApFabricLanCloudFsmStamp OBJECT-TYPE
    SYNTAX       DateAndTime
    MAX-ACCESS   read-only
    STATUS       current
    DESCRIPTION
        "Cisco Firepower fabric:LanCloud:fsmStamp managed object property"
    ::= { cfprApFabricLanCloudEntry 11 }

cfprApFabricLanCloudFsmStatus OBJECT-TYPE
    SYNTAX       SnmpAdminString
    MAX-ACCESS   read-only
    STATUS       current
    DESCRIPTION
        "Cisco Firepower fabric:LanCloud:fsmStatus managed
        object property"
    ::= { cfprApFabricLanCloudEntry 12 }

cfprApFabricLanCloudFsmTry OBJECT-TYPE
    SYNTAX       Gauge32
    MAX-ACCESS   read-only
    STATUS       current
    DESCRIPTION
        "Cisco Firepower fabric:LanCloud:fsmTry managed object property"
    ::= { cfprApFabricLanCloudEntry 13 }

cfprApFabricLanCloudMacAging OBJECT-TYPE
    SYNTAX       TimeIntervalSec
    MAX-ACCESS   read-only
    STATUS       current
    DESCRIPTION
        "Cisco Firepower fabric:LanCloud:macAging managed object property"
    ::= { cfprApFabricLanCloudEntry 14 }

cfprApFabricLanCloudMode OBJECT-TYPE
    SYNTAX       CfprApFabricSwitchingMode
    MAX-ACCESS   read-only
    STATUS       current
    DESCRIPTION
        "Cisco Firepower fabric:LanCloud:mode managed object property"
    ::= { cfprApFabricLanCloudEntry 15 }

cfprApFabricLanCloudVlanCompression OBJECT-TYPE
    SYNTAX       CfprApFabricLanCloudVlanCompression
    MAX-ACCESS   read-only
    STATUS       current
    DESCRIPTION
        "Cisco Firepower fabric:LanCloud:vlanCompression
        managed object property"
    ::= { cfprApFabricLanCloudEntry 16 }

cfprApFabricLanCloudFsmTable OBJECT-TYPE
    SYNTAX           SEQUENCE OF CfprApFabricLanCloudFsmEntry
    MAX-ACCESS       not-accessible
    STATUS           current
    DESCRIPTION
        "Cisco Firepower fabric:LanCloudFsm managed object table"
    ::= { cfprApFabricObjects 70 }

cfprApFabricLanCloudFsmEntry OBJECT-TYPE
    SYNTAX           CfprApFabricLanCloudFsmEntry
    MAX-ACCESS       not-accessible
    STATUS           current
    DESCRIPTION
        "Entry for the cfprApFabricLanCloudFsmTable table."
    INDEX { cfprApFabricLanCloudFsmInstanceId }
    ::= { cfprApFabricLanCloudFsmTable 1 }

CfprApFabricLanCloudFsmEntry ::= SEQUENCE {
    cfprApFabricLanCloudFsmInstanceId                                CfprApManagedObjectId,
    cfprApFabricLanCloudFsmDn                                        CfprApManagedObjectDn,
    cfprApFabricLanCloudFsmRn                                        SnmpAdminString,
    cfprApFabricLanCloudFsmCompletionTime                            DateAndTime,
    cfprApFabricLanCloudFsmCurrentFsm                                CfprApFabricLanCloudFsmCurrentFsm,
    cfprApFabricLanCloudFsmDescrData                                 SnmpAdminString,
    cfprApFabricLanCloudFsmFsmStatus                                 CfprApFsmFsmStageStatus,
    cfprApFabricLanCloudFsmProgress                                  Gauge32,
    cfprApFabricLanCloudFsmRmtErrCode                                Gauge32,
    cfprApFabricLanCloudFsmRmtErrDescr                               SnmpAdminString,
    cfprApFabricLanCloudFsmRmtRslt                                   CfprApConditionRemoteInvRslt
}

cfprApFabricLanCloudFsmInstanceId OBJECT-TYPE
    SYNTAX       CfprApManagedObjectId
    MAX-ACCESS   not-accessible
    STATUS       current
    DESCRIPTION
        "Instance identifier of the managed object."
    ::= { cfprApFabricLanCloudFsmEntry 1 }

cfprApFabricLanCloudFsmDn OBJECT-TYPE
    SYNTAX       CfprApManagedObjectDn
    MAX-ACCESS   read-only
    STATUS       current
    DESCRIPTION
        "Cisco Firepower fabric:LanCloudFsm:dn managed object property"
    ::= { cfprApFabricLanCloudFsmEntry 2 }

cfprApFabricLanCloudFsmRn OBJECT-TYPE
    SYNTAX       SnmpAdminString
    MAX-ACCESS   read-only
    STATUS       current
    DESCRIPTION
        "Cisco Firepower fabric:LanCloudFsm:rn managed object property"
    ::= { cfprApFabricLanCloudFsmEntry 3 }

cfprApFabricLanCloudFsmCompletionTime OBJECT-TYPE
    SYNTAX       DateAndTime
    MAX-ACCESS   read-only
    STATUS       current
    DESCRIPTION
        "Cisco Firepower fabric:LanCloudFsm:completionTime
        managed object property"
    ::= { cfprApFabricLanCloudFsmEntry 4 }

cfprApFabricLanCloudFsmCurrentFsm OBJECT-TYPE
    SYNTAX       CfprApFabricLanCloudFsmCurrentFsm
    MAX-ACCESS   read-only
    STATUS       current
    DESCRIPTION
        "Cisco Firepower fabric:LanCloudFsm:currentFsm
        managed object property"
    ::= { cfprApFabricLanCloudFsmEntry 5 }

cfprApFabricLanCloudFsmDescrData OBJECT-TYPE
    SYNTAX       SnmpAdminString
    MAX-ACCESS   read-only
    STATUS       current
    DESCRIPTION
        "Cisco Firepower fabric:LanCloudFsm:descr managed object property"
    ::= { cfprApFabricLanCloudFsmEntry 6 }

cfprApFabricLanCloudFsmFsmStatus OBJECT-TYPE
    SYNTAX       CfprApFsmFsmStageStatus
    MAX-ACCESS   read-only
    STATUS       current
    DESCRIPTION
        "Cisco Firepower fabric:LanCloudFsm:fsmStatus managed
        object property"
    ::= { cfprApFabricLanCloudFsmEntry 7 }

cfprApFabricLanCloudFsmProgress OBJECT-TYPE
    SYNTAX       Gauge32
    MAX-ACCESS   read-only
    STATUS       current
    DESCRIPTION
        "Cisco Firepower fabric:LanCloudFsm:progress managed
        object property"
    ::= { cfprApFabricLanCloudFsmEntry 8 }

cfprApFabricLanCloudFsmRmtErrCode OBJECT-TYPE
    SYNTAX       Gauge32
    MAX-ACCESS   read-only
    STATUS       current
    DESCRIPTION
        "Cisco Firepower fabric:LanCloudFsm:rmtErrCode
        managed object property"
    ::= { cfprApFabricLanCloudFsmEntry 9 }

cfprApFabricLanCloudFsmRmtErrDescr OBJECT-TYPE
    SYNTAX       SnmpAdminString
    MAX-ACCESS   read-only
    STATUS       current
    DESCRIPTION
        "Cisco Firepower fabric:LanCloudFsm:rmtErrDescr
        managed object property"
    ::= { cfprApFabricLanCloudFsmEntry 10 }

cfprApFabricLanCloudFsmRmtRslt OBJECT-TYPE
    SYNTAX       CfprApConditionRemoteInvRslt
    MAX-ACCESS   read-only
    STATUS       current
    DESCRIPTION
        "Cisco Firepower fabric:LanCloudFsm:rmtRslt managed
        object property"
    ::= { cfprApFabricLanCloudFsmEntry 11 }

cfprApFabricLanCloudFsmStageTable OBJECT-TYPE
    SYNTAX           SEQUENCE OF CfprApFabricLanCloudFsmStageEntry
    MAX-ACCESS       not-accessible
    STATUS           current
    DESCRIPTION
        "Cisco Firepower fabric:LanCloudFsmStage managed object table"
    ::= { cfprApFabricObjects 71 }

cfprApFabricLanCloudFsmStageEntry OBJECT-TYPE
    SYNTAX           CfprApFabricLanCloudFsmStageEntry
    MAX-ACCESS       not-accessible
    STATUS           current
    DESCRIPTION
        "Entry for the cfprApFabricLanCloudFsmStageTable table."
    INDEX { cfprApFabricLanCloudFsmStageInstanceId }
    ::= { cfprApFabricLanCloudFsmStageTable 1 }

CfprApFabricLanCloudFsmStageEntry ::= SEQUENCE {
    cfprApFabricLanCloudFsmStageInstanceId                           CfprApManagedObjectId,
    cfprApFabricLanCloudFsmStageDn                                   CfprApManagedObjectDn,
    cfprApFabricLanCloudFsmStageRn                                   SnmpAdminString,
    cfprApFabricLanCloudFsmStageDescrData                            SnmpAdminString,
    cfprApFabricLanCloudFsmStageLastUpdateTime                       DateAndTime,
    cfprApFabricLanCloudFsmStageName                                 CfprApFabricLanCloudFsmStageName,
    cfprApFabricLanCloudFsmStageOrder                                Gauge32,
    cfprApFabricLanCloudFsmStageRetry                                Gauge32,
    cfprApFabricLanCloudFsmStageStageStatus                          CfprApFsmFsmStageStatus
}

cfprApFabricLanCloudFsmStageInstanceId OBJECT-TYPE
    SYNTAX       CfprApManagedObjectId
    MAX-ACCESS   not-accessible
    STATUS       current
    DESCRIPTION
        "Instance identifier of the managed object."
    ::= { cfprApFabricLanCloudFsmStageEntry 1 }

cfprApFabricLanCloudFsmStageDn OBJECT-TYPE
    SYNTAX       CfprApManagedObjectDn
    MAX-ACCESS   read-only
    STATUS       current
    DESCRIPTION
        "Cisco Firepower fabric:LanCloudFsmStage:dn managed
        object property"
    ::= { cfprApFabricLanCloudFsmStageEntry 2 }

cfprApFabricLanCloudFsmStageRn OBJECT-TYPE
    SYNTAX       SnmpAdminString
    MAX-ACCESS   read-only
    STATUS       current
    DESCRIPTION
        "Cisco Firepower fabric:LanCloudFsmStage:rn managed
        object property"
    ::= { cfprApFabricLanCloudFsmStageEntry 3 }

cfprApFabricLanCloudFsmStageDescrData OBJECT-TYPE
    SYNTAX       SnmpAdminString
    MAX-ACCESS   read-only
    STATUS       current
    DESCRIPTION
        "Cisco Firepower fabric:LanCloudFsmStage:descr
        managed object property"
    ::= { cfprApFabricLanCloudFsmStageEntry 4 }

cfprApFabricLanCloudFsmStageLastUpdateTime OBJECT-TYPE
    SYNTAX       DateAndTime
    MAX-ACCESS   read-only
    STATUS       current
    DESCRIPTION
        "Cisco Firepower fabric:LanCloudFsmStage:lastUpdateTime
        managed object property"
    ::= { cfprApFabricLanCloudFsmStageEntry 5 }

cfprApFabricLanCloudFsmStageName OBJECT-TYPE
    SYNTAX       CfprApFabricLanCloudFsmStageName
    MAX-ACCESS   read-only
    STATUS       current
    DESCRIPTION
        "Cisco Firepower fabric:LanCloudFsmStage:name managed
        object property"
    ::= { cfprApFabricLanCloudFsmStageEntry 6 }

cfprApFabricLanCloudFsmStageOrder OBJECT-TYPE
    SYNTAX       Gauge32
    MAX-ACCESS   read-only
    STATUS       current
    DESCRIPTION
        "Cisco Firepower fabric:LanCloudFsmStage:order
        managed object property"
    ::= { cfprApFabricLanCloudFsmStageEntry 7 }

cfprApFabricLanCloudFsmStageRetry OBJECT-TYPE
    SYNTAX       Gauge32
    MAX-ACCESS   read-only
    STATUS       current
    DESCRIPTION
        "Cisco Firepower fabric:LanCloudFsmStage:retry
        managed object property"
    ::= { cfprApFabricLanCloudFsmStageEntry 8 }

cfprApFabricLanCloudFsmStageStageStatus OBJECT-TYPE
    SYNTAX       CfprApFsmFsmStageStatus
    MAX-ACCESS   read-only
    STATUS       current
    DESCRIPTION
        "Cisco Firepower fabric:LanCloudFsmStage:stageStatus
        managed object property"
    ::= { cfprApFabricLanCloudFsmStageEntry 9 }

cfprApFabricLanCloudFsmTaskTable OBJECT-TYPE
    SYNTAX           SEQUENCE OF CfprApFabricLanCloudFsmTaskEntry
    MAX-ACCESS       not-accessible
    STATUS           current
    DESCRIPTION
        "Cisco Firepower fabric:LanCloudFsmTask managed object table"
    ::= { cfprApFabricObjects 72 }

cfprApFabricLanCloudFsmTaskEntry OBJECT-TYPE
    SYNTAX           CfprApFabricLanCloudFsmTaskEntry
    MAX-ACCESS       not-accessible
    STATUS           current
    DESCRIPTION
        "Entry for the cfprApFabricLanCloudFsmTaskTable table."
    INDEX { cfprApFabricLanCloudFsmTaskInstanceId }
    ::= { cfprApFabricLanCloudFsmTaskTable 1 }

CfprApFabricLanCloudFsmTaskEntry ::= SEQUENCE {
    cfprApFabricLanCloudFsmTaskInstanceId                            CfprApManagedObjectId,
    cfprApFabricLanCloudFsmTaskDn                                    CfprApManagedObjectDn,
    cfprApFabricLanCloudFsmTaskRn                                    SnmpAdminString,
    cfprApFabricLanCloudFsmTaskCompletion                            CfprApFsmCompletion,
    cfprApFabricLanCloudFsmTaskFlags                                 CfprApFsmFlags,
    cfprApFabricLanCloudFsmTaskItem                                  CfprApFabricLanCloudFsmTaskItem,
    cfprApFabricLanCloudFsmTaskSeqId                                 Gauge32
}

cfprApFabricLanCloudFsmTaskInstanceId OBJECT-TYPE
    SYNTAX       CfprApManagedObjectId
    MAX-ACCESS   not-accessible
    STATUS       current
    DESCRIPTION
        "Instance identifier of the managed object."
    ::= { cfprApFabricLanCloudFsmTaskEntry 1 }

cfprApFabricLanCloudFsmTaskDn OBJECT-TYPE
    SYNTAX       CfprApManagedObjectDn
    MAX-ACCESS   read-only
    STATUS       current
    DESCRIPTION
        "Cisco Firepower fabric:LanCloudFsmTask:dn managed
        object property"
    ::= { cfprApFabricLanCloudFsmTaskEntry 2 }

cfprApFabricLanCloudFsmTaskRn OBJECT-TYPE
    SYNTAX       SnmpAdminString
    MAX-ACCESS   read-only
    STATUS       current
    DESCRIPTION
        "Cisco Firepower fabric:LanCloudFsmTask:rn managed
        object property"
    ::= { cfprApFabricLanCloudFsmTaskEntry 3 }

cfprApFabricLanCloudFsmTaskCompletion OBJECT-TYPE
    SYNTAX       CfprApFsmCompletion
    MAX-ACCESS   read-only
    STATUS       current
    DESCRIPTION
        "Cisco Firepower fabric:LanCloudFsmTask:completion
        managed object property"
    ::= { cfprApFabricLanCloudFsmTaskEntry 4 }

cfprApFabricLanCloudFsmTaskFlags OBJECT-TYPE
    SYNTAX       CfprApFsmFlags
    MAX-ACCESS   read-only
    STATUS       current
    DESCRIPTION
        "Cisco Firepower fabric:LanCloudFsmTask:flags managed
        object property"
    ::= { cfprApFabricLanCloudFsmTaskEntry 5 }

cfprApFabricLanCloudFsmTaskItem OBJECT-TYPE
    SYNTAX       CfprApFabricLanCloudFsmTaskItem
    MAX-ACCESS   read-only
    STATUS       current
    DESCRIPTION
        "Cisco Firepower fabric:LanCloudFsmTask:item managed
        object property"
    ::= { cfprApFabricLanCloudFsmTaskEntry 6 }

cfprApFabricLanCloudFsmTaskSeqId OBJECT-TYPE
    SYNTAX       Gauge32
    MAX-ACCESS   read-only
    STATUS       current
    DESCRIPTION
        "Cisco Firepower fabric:LanCloudFsmTask:seqId managed
        object property"
    ::= { cfprApFabricLanCloudFsmTaskEntry 7 }

cfprApFabricLanMonCloudTable OBJECT-TYPE
    SYNTAX           SEQUENCE OF CfprApFabricLanMonCloudEntry
    MAX-ACCESS       not-accessible
    STATUS           current
    DESCRIPTION
        "Cisco Firepower fabric:LanMonCloud managed object table"
    ::= { cfprApFabricObjects 73 }

cfprApFabricLanMonCloudEntry OBJECT-TYPE
    SYNTAX           CfprApFabricLanMonCloudEntry
    MAX-ACCESS       not-accessible
    STATUS           current
    DESCRIPTION
        "Entry for the cfprApFabricLanMonCloudTable table."
    INDEX { cfprApFabricLanMonCloudInstanceId }
    ::= { cfprApFabricLanMonCloudTable 1 }

CfprApFabricLanMonCloudEntry ::= SEQUENCE {
    cfprApFabricLanMonCloudInstanceId                                CfprApManagedObjectId,
    cfprApFabricLanMonCloudDn                                        CfprApManagedObjectDn,
    cfprApFabricLanMonCloudRn                                        SnmpAdminString,
    cfprApFabricLanMonCloudMode                                      CfprApFabricSwitchingMode
}

cfprApFabricLanMonCloudInstanceId OBJECT-TYPE
    SYNTAX       CfprApManagedObjectId
    MAX-ACCESS   not-accessible
    STATUS       current
    DESCRIPTION
        "Instance identifier of the managed object."
    ::= { cfprApFabricLanMonCloudEntry 1 }

cfprApFabricLanMonCloudDn OBJECT-TYPE
    SYNTAX       CfprApManagedObjectDn
    MAX-ACCESS   read-only
    STATUS       current
    DESCRIPTION
        "Cisco Firepower fabric:LanMonCloud:dn managed object property"
    ::= { cfprApFabricLanMonCloudEntry 2 }

cfprApFabricLanMonCloudRn OBJECT-TYPE
    SYNTAX       SnmpAdminString
    MAX-ACCESS   read-only
    STATUS       current
    DESCRIPTION
        "Cisco Firepower fabric:LanMonCloud:rn managed object property"
    ::= { cfprApFabricLanMonCloudEntry 3 }

cfprApFabricLanMonCloudMode OBJECT-TYPE
    SYNTAX       CfprApFabricSwitchingMode
    MAX-ACCESS   read-only
    STATUS       current
    DESCRIPTION
        "Cisco Firepower fabric:LanMonCloud:mode managed object property"
    ::= { cfprApFabricLanMonCloudEntry 4 }

cfprApFabricLanPinGroupTable OBJECT-TYPE
    SYNTAX           SEQUENCE OF CfprApFabricLanPinGroupEntry
    MAX-ACCESS       not-accessible
    STATUS           current
    DESCRIPTION
        "Cisco Firepower fabric:LanPinGroup managed object table"
    ::= { cfprApFabricObjects 74 }

cfprApFabricLanPinGroupEntry OBJECT-TYPE
    SYNTAX           CfprApFabricLanPinGroupEntry
    MAX-ACCESS       not-accessible
    STATUS           current
    DESCRIPTION
        "Entry for the cfprApFabricLanPinGroupTable table."
    INDEX { cfprApFabricLanPinGroupInstanceId }
    ::= { cfprApFabricLanPinGroupTable 1 }

CfprApFabricLanPinGroupEntry ::= SEQUENCE {
    cfprApFabricLanPinGroupInstanceId                                CfprApManagedObjectId,
    cfprApFabricLanPinGroupDn                                        CfprApManagedObjectDn,
    cfprApFabricLanPinGroupRn                                        SnmpAdminString,
    cfprApFabricLanPinGroupDescr                                     SnmpAdminString,
    cfprApFabricLanPinGroupIntId                                     SnmpAdminString,
    cfprApFabricLanPinGroupName                                      SnmpAdminString,
    cfprApFabricLanPinGroupPolicyLevel                               Gauge32,
    cfprApFabricLanPinGroupPolicyOwner                               CfprApPolicyPolicyOwner,
    cfprApFabricLanPinGroupSize                                      Gauge32
}

cfprApFabricLanPinGroupInstanceId OBJECT-TYPE
    SYNTAX       CfprApManagedObjectId
    MAX-ACCESS   not-accessible
    STATUS       current
    DESCRIPTION
        "Instance identifier of the managed object."
    ::= { cfprApFabricLanPinGroupEntry 1 }

cfprApFabricLanPinGroupDn OBJECT-TYPE
    SYNTAX       CfprApManagedObjectDn
    MAX-ACCESS   read-only
    STATUS       current
    DESCRIPTION
        "Cisco Firepower fabric:LanPinGroup:dn managed object property"
    ::= { cfprApFabricLanPinGroupEntry 2 }

cfprApFabricLanPinGroupRn OBJECT-TYPE
    SYNTAX       SnmpAdminString
    MAX-ACCESS   read-only
    STATUS       current
    DESCRIPTION
        "Cisco Firepower fabric:LanPinGroup:rn managed object property"
    ::= { cfprApFabricLanPinGroupEntry 3 }

cfprApFabricLanPinGroupDescr OBJECT-TYPE
    SYNTAX       SnmpAdminString
    MAX-ACCESS   read-only
    STATUS       current
    DESCRIPTION
        "Cisco Firepower fabric:LanPinGroup:descr managed object property"
    ::= { cfprApFabricLanPinGroupEntry 4 }

cfprApFabricLanPinGroupIntId OBJECT-TYPE
    SYNTAX       SnmpAdminString
    MAX-ACCESS   read-only
    STATUS       current
    DESCRIPTION
        "Cisco Firepower fabric:LanPinGroup:intId managed object property"
    ::= { cfprApFabricLanPinGroupEntry 5 }

cfprApFabricLanPinGroupName OBJECT-TYPE
    SYNTAX       SnmpAdminString
    MAX-ACCESS   read-only
    STATUS       current
    DESCRIPTION
        "Cisco Firepower fabric:LanPinGroup:name managed object property"
    ::= { cfprApFabricLanPinGroupEntry 6 }

cfprApFabricLanPinGroupPolicyLevel OBJECT-TYPE
    SYNTAX       Gauge32
    MAX-ACCESS   read-only
    STATUS       current
    DESCRIPTION
        "Cisco Firepower fabric:LanPinGroup:policyLevel
        managed object property"
    ::= { cfprApFabricLanPinGroupEntry 7 }

cfprApFabricLanPinGroupPolicyOwner OBJECT-TYPE
    SYNTAX       CfprApPolicyPolicyOwner
    MAX-ACCESS   read-only
    STATUS       current
    DESCRIPTION
        "Cisco Firepower fabric:LanPinGroup:policyOwner
        managed object property"
    ::= { cfprApFabricLanPinGroupEntry 8 }

cfprApFabricLanPinGroupSize OBJECT-TYPE
    SYNTAX       Gauge32
    MAX-ACCESS   read-only
    STATUS       current
    DESCRIPTION
        "Cisco Firepower fabric:LanPinGroup:size managed object property"
    ::= { cfprApFabricLanPinGroupEntry 9 }

cfprApFabricLanPinTargetTable OBJECT-TYPE
    SYNTAX           SEQUENCE OF CfprApFabricLanPinTargetEntry
    MAX-ACCESS       not-accessible
    STATUS           current
    DESCRIPTION
        "Cisco Firepower fabric:LanPinTarget managed object table"
    ::= { cfprApFabricObjects 75 }

cfprApFabricLanPinTargetEntry OBJECT-TYPE
    SYNTAX           CfprApFabricLanPinTargetEntry
    MAX-ACCESS       not-accessible
    STATUS           current
    DESCRIPTION
        "Entry for the cfprApFabricLanPinTargetTable table."
    INDEX { cfprApFabricLanPinTargetInstanceId }
    ::= { cfprApFabricLanPinTargetTable 1 }

CfprApFabricLanPinTargetEntry ::= SEQUENCE {
    cfprApFabricLanPinTargetInstanceId                               CfprApManagedObjectId,
    cfprApFabricLanPinTargetDn                                       CfprApManagedObjectDn,
    cfprApFabricLanPinTargetRn                                       SnmpAdminString,
    cfprApFabricLanPinTargetEpDn                                     SnmpAdminString,
    cfprApFabricLanPinTargetFabricId                                 SnmpAdminString,
    cfprApFabricLanPinTargetTargetStatus                             CfprApFabricTargetStatus
}

cfprApFabricLanPinTargetInstanceId OBJECT-TYPE
    SYNTAX       CfprApManagedObjectId
    MAX-ACCESS   not-accessible
    STATUS       current
    DESCRIPTION
        "Instance identifier of the managed object."
    ::= { cfprApFabricLanPinTargetEntry 1 }

cfprApFabricLanPinTargetDn OBJECT-TYPE
    SYNTAX       CfprApManagedObjectDn
    MAX-ACCESS   read-only
    STATUS       current
    DESCRIPTION
        "Cisco Firepower fabric:LanPinTarget:dn managed object property"
    ::= { cfprApFabricLanPinTargetEntry 2 }

cfprApFabricLanPinTargetRn OBJECT-TYPE
    SYNTAX       SnmpAdminString
    MAX-ACCESS   read-only
    STATUS       current
    DESCRIPTION
        "Cisco Firepower fabric:LanPinTarget:rn managed object property"
    ::= { cfprApFabricLanPinTargetEntry 3 }

cfprApFabricLanPinTargetEpDn OBJECT-TYPE
    SYNTAX       SnmpAdminString
    MAX-ACCESS   read-only
    STATUS       current
    DESCRIPTION
        "Cisco Firepower fabric:LanPinTarget:epDn managed object property"
    ::= { cfprApFabricLanPinTargetEntry 4 }

cfprApFabricLanPinTargetFabricId OBJECT-TYPE
    SYNTAX       SnmpAdminString
    MAX-ACCESS   read-only
    STATUS       current
    DESCRIPTION
        "Cisco Firepower fabric:LanPinTarget:fabricId managed
        object property"
    ::= { cfprApFabricLanPinTargetEntry 5 }

cfprApFabricLanPinTargetTargetStatus OBJECT-TYPE
    SYNTAX       CfprApFabricTargetStatus
    MAX-ACCESS   read-only
    STATUS       current
    DESCRIPTION
        "Cisco Firepower fabric:LanPinTarget:targetStatus
        managed object property"
    ::= { cfprApFabricLanPinTargetEntry 6 }

cfprApFabricLastAckedSlotTable OBJECT-TYPE
    SYNTAX           SEQUENCE OF CfprApFabricLastAckedSlotEntry
    MAX-ACCESS       not-accessible
    STATUS           current
    DESCRIPTION
        "Cisco Firepower fabric:LastAckedSlot managed object table"
    ::= { cfprApFabricObjects 76 }

cfprApFabricLastAckedSlotEntry OBJECT-TYPE
    SYNTAX           CfprApFabricLastAckedSlotEntry
    MAX-ACCESS       not-accessible
    STATUS           current
    DESCRIPTION
        "Entry for the cfprApFabricLastAckedSlotTable table."
    INDEX { cfprApFabricLastAckedSlotInstanceId }
    ::= { cfprApFabricLastAckedSlotTable 1 }

CfprApFabricLastAckedSlotEntry ::= SEQUENCE {
    cfprApFabricLastAckedSlotInstanceId                              CfprApManagedObjectId,
    cfprApFabricLastAckedSlotDn                                      CfprApManagedObjectDn,
    cfprApFabricLastAckedSlotRn                                      SnmpAdminString,
    cfprApFabricLastAckedSlotBoardAggregationRole                    CfprApEquipmentBoardAggregationRole,
    cfprApFabricLastAckedSlotChassisId                               Gauge32,
    cfprApFabricLastAckedSlotSlotId                                  Gauge32,
    cfprApFabricLastAckedSlotSwitchId                                CfprApNetworkSwitchId
}

cfprApFabricLastAckedSlotInstanceId OBJECT-TYPE
    SYNTAX       CfprApManagedObjectId
    MAX-ACCESS   not-accessible
    STATUS       current
    DESCRIPTION
        "Instance identifier of the managed object."
    ::= { cfprApFabricLastAckedSlotEntry 1 }

cfprApFabricLastAckedSlotDn OBJECT-TYPE
    SYNTAX       CfprApManagedObjectDn
    MAX-ACCESS   read-only
    STATUS       current
    DESCRIPTION
        "Cisco Firepower fabric:LastAckedSlot:dn managed object property"
    ::= { cfprApFabricLastAckedSlotEntry 2 }

cfprApFabricLastAckedSlotRn OBJECT-TYPE
    SYNTAX       SnmpAdminString
    MAX-ACCESS   read-only
    STATUS       current
    DESCRIPTION
        "Cisco Firepower fabric:LastAckedSlot:rn managed object property"
    ::= { cfprApFabricLastAckedSlotEntry 3 }

cfprApFabricLastAckedSlotBoardAggregationRole OBJECT-TYPE
    SYNTAX       CfprApEquipmentBoardAggregationRole
    MAX-ACCESS   read-only
    STATUS       current
    DESCRIPTION
        "Cisco Firepower fabric:LastAckedSlot:boardAggregationRole
        managed object property"
    ::= { cfprApFabricLastAckedSlotEntry 4 }

cfprApFabricLastAckedSlotChassisId OBJECT-TYPE
    SYNTAX       Gauge32
    MAX-ACCESS   read-only
    STATUS       current
    DESCRIPTION
        "Cisco Firepower fabric:LastAckedSlot:chassisId
        managed object property"
    ::= { cfprApFabricLastAckedSlotEntry 5 }

cfprApFabricLastAckedSlotSlotId OBJECT-TYPE
    SYNTAX       Gauge32
    MAX-ACCESS   read-only
    STATUS       current
    DESCRIPTION
        "Cisco Firepower fabric:LastAckedSlot:slotId managed
        object property"
    ::= { cfprApFabricLastAckedSlotEntry 6 }

cfprApFabricLastAckedSlotSwitchId OBJECT-TYPE
    SYNTAX       CfprApNetworkSwitchId
    MAX-ACCESS   read-only
    STATUS       current
    DESCRIPTION
        "Cisco Firepower fabric:LastAckedSlot:switchId
        managed object property"
    ::= { cfprApFabricLastAckedSlotEntry 7 }

cfprApFabricLocaleTable OBJECT-TYPE
    SYNTAX           SEQUENCE OF CfprApFabricLocaleEntry
    MAX-ACCESS       not-accessible
    STATUS           current
    DESCRIPTION
        "Cisco Firepower fabric:Locale managed object table"
    ::= { cfprApFabricObjects 77 }

cfprApFabricLocaleEntry OBJECT-TYPE
    SYNTAX           CfprApFabricLocaleEntry
    MAX-ACCESS       not-accessible
    STATUS           current
    DESCRIPTION
        "Entry for the cfprApFabricLocaleTable table."
    INDEX { cfprApFabricLocaleInstanceId }
    ::= { cfprApFabricLocaleTable 1 }

CfprApFabricLocaleEntry ::= SEQUENCE {
    cfprApFabricLocaleInstanceId                                     CfprApManagedObjectId,
    cfprApFabricLocaleDn                                             CfprApManagedObjectDn,
    cfprApFabricLocaleRn                                             SnmpAdminString,
    cfprApFabricLocaleCType                                          Gauge32,
    cfprApFabricLocaleChassisId                                      Gauge32,
    cfprApFabricLocaleLocale                                         CfprApNetworkLocale,
    cfprApFabricLocaleName                                           SnmpAdminString,
    cfprApFabricLocaleSide                                           CfprApNetworkSide,
    cfprApFabricLocaleSlotId                                         Gauge32,
    cfprApFabricLocaleSwitchId                                       CfprApNetworkSwitchId,
    cfprApFabricLocaleTransport                                      CfprApNetworkTransport,
    cfprApFabricLocaleType                                           CfprApNetworkConnectionType
}

cfprApFabricLocaleInstanceId OBJECT-TYPE
    SYNTAX       CfprApManagedObjectId
    MAX-ACCESS   not-accessible
    STATUS       current
    DESCRIPTION
        "Instance identifier of the managed object."
    ::= { cfprApFabricLocaleEntry 1 }

cfprApFabricLocaleDn OBJECT-TYPE
    SYNTAX       CfprApManagedObjectDn
    MAX-ACCESS   read-only
    STATUS       current
    DESCRIPTION
        "Cisco Firepower fabric:Locale:dn managed object property"
    ::= { cfprApFabricLocaleEntry 2 }

cfprApFabricLocaleRn OBJECT-TYPE
    SYNTAX       SnmpAdminString
    MAX-ACCESS   read-only
    STATUS       current
    DESCRIPTION
        "Cisco Firepower fabric:Locale:rn managed object property"
    ::= { cfprApFabricLocaleEntry 3 }

cfprApFabricLocaleCType OBJECT-TYPE
    SYNTAX       Gauge32
    MAX-ACCESS   read-only
    STATUS       current
    DESCRIPTION
        "Cisco Firepower fabric:Locale:cType managed object property"
    ::= { cfprApFabricLocaleEntry 4 }

cfprApFabricLocaleChassisId OBJECT-TYPE
    SYNTAX       Gauge32
    MAX-ACCESS   read-only
    STATUS       current
    DESCRIPTION
        "Cisco Firepower fabric:Locale:chassisId managed object property"
    ::= { cfprApFabricLocaleEntry 5 }

cfprApFabricLocaleLocale OBJECT-TYPE
    SYNTAX       CfprApNetworkLocale
    MAX-ACCESS   read-only
    STATUS       current
    DESCRIPTION
        "Cisco Firepower fabric:Locale:locale managed object property"
    ::= { cfprApFabricLocaleEntry 6 }

cfprApFabricLocaleName OBJECT-TYPE
    SYNTAX       SnmpAdminString
    MAX-ACCESS   read-only
    STATUS       current
    DESCRIPTION
        "Cisco Firepower fabric:Locale:name managed object property"
    ::= { cfprApFabricLocaleEntry 7 }

cfprApFabricLocaleSide OBJECT-TYPE
    SYNTAX       CfprApNetworkSide
    MAX-ACCESS   read-only
    STATUS       current
    DESCRIPTION
        "Cisco Firepower fabric:Locale:side managed object property"
    ::= { cfprApFabricLocaleEntry 8 }

cfprApFabricLocaleSlotId OBJECT-TYPE
    SYNTAX       Gauge32
    MAX-ACCESS   read-only
    STATUS       current
    DESCRIPTION
        "Cisco Firepower fabric:Locale:slotId managed object property"
    ::= { cfprApFabricLocaleEntry 9 }

cfprApFabricLocaleSwitchId OBJECT-TYPE
    SYNTAX       CfprApNetworkSwitchId
    MAX-ACCESS   read-only
    STATUS       current
    DESCRIPTION
        "Cisco Firepower fabric:Locale:switchId managed object property"
    ::= { cfprApFabricLocaleEntry 10 }

cfprApFabricLocaleTransport OBJECT-TYPE
    SYNTAX       CfprApNetworkTransport
    MAX-ACCESS   read-only
    STATUS       current
    DESCRIPTION
        "Cisco Firepower fabric:Locale:transport managed object property"
    ::= { cfprApFabricLocaleEntry 11 }

cfprApFabricLocaleType OBJECT-TYPE
    SYNTAX       CfprApNetworkConnectionType
    MAX-ACCESS   read-only
    STATUS       current
    DESCRIPTION
        "Cisco Firepower fabric:Locale:type managed object property"
    ::= { cfprApFabricLocaleEntry 12 }

cfprApFabricMulticastPolicyTable OBJECT-TYPE
    SYNTAX           SEQUENCE OF CfprApFabricMulticastPolicyEntry
    MAX-ACCESS       not-accessible
    STATUS           current
    DESCRIPTION
        "Cisco Firepower fabric:MulticastPolicy managed object table"
    ::= { cfprApFabricObjects 78 }

cfprApFabricMulticastPolicyEntry OBJECT-TYPE
    SYNTAX           CfprApFabricMulticastPolicyEntry
    MAX-ACCESS       not-accessible
    STATUS           current
    DESCRIPTION
        "Entry for the cfprApFabricMulticastPolicyTable table."
    INDEX { cfprApFabricMulticastPolicyInstanceId }
    ::= { cfprApFabricMulticastPolicyTable 1 }

CfprApFabricMulticastPolicyEntry ::= SEQUENCE {
    cfprApFabricMulticastPolicyInstanceId                            CfprApManagedObjectId,
    cfprApFabricMulticastPolicyDn                                    CfprApManagedObjectDn,
    cfprApFabricMulticastPolicyRn                                    SnmpAdminString,
    cfprApFabricMulticastPolicyDescr                                 SnmpAdminString,
    cfprApFabricMulticastPolicyIntId                                 SnmpAdminString,
    cfprApFabricMulticastPolicyName                                  SnmpAdminString,
    cfprApFabricMulticastPolicyPolicyLevel                           Gauge32,
    cfprApFabricMulticastPolicyPolicyOwner                           CfprApPolicyPolicyOwner,
    cfprApFabricMulticastPolicyQuerierIpAddr                         InetAddressIPv4,
    cfprApFabricMulticastPolicyQuerierState                          CfprApFabricQuerierType,
    cfprApFabricMulticastPolicySnoopingState                         CfprApFabricSnoopingType
}

cfprApFabricMulticastPolicyInstanceId OBJECT-TYPE
    SYNTAX       CfprApManagedObjectId
    MAX-ACCESS   not-accessible
    STATUS       current
    DESCRIPTION
        "Instance identifier of the managed object."
    ::= { cfprApFabricMulticastPolicyEntry 1 }

cfprApFabricMulticastPolicyDn OBJECT-TYPE
    SYNTAX       CfprApManagedObjectDn
    MAX-ACCESS   read-only
    STATUS       current
    DESCRIPTION
        "Cisco Firepower fabric:MulticastPolicy:dn managed
        object property"
    ::= { cfprApFabricMulticastPolicyEntry 2 }

cfprApFabricMulticastPolicyRn OBJECT-TYPE
    SYNTAX       SnmpAdminString
    MAX-ACCESS   read-only
    STATUS       current
    DESCRIPTION
        "Cisco Firepower fabric:MulticastPolicy:rn managed
        object property"
    ::= { cfprApFabricMulticastPolicyEntry 3 }

cfprApFabricMulticastPolicyDescr OBJECT-TYPE
    SYNTAX       SnmpAdminString
    MAX-ACCESS   read-only
    STATUS       current
    DESCRIPTION
        "Cisco Firepower fabric:MulticastPolicy:descr managed
        object property"
    ::= { cfprApFabricMulticastPolicyEntry 4 }

cfprApFabricMulticastPolicyIntId OBJECT-TYPE
    SYNTAX       SnmpAdminString
    MAX-ACCESS   read-only
    STATUS       current
    DESCRIPTION
        "Cisco Firepower fabric:MulticastPolicy:intId managed
        object property"
    ::= { cfprApFabricMulticastPolicyEntry 5 }

cfprApFabricMulticastPolicyName OBJECT-TYPE
    SYNTAX       SnmpAdminString
    MAX-ACCESS   read-only
    STATUS       current
    DESCRIPTION
        "Cisco Firepower fabric:MulticastPolicy:name managed
        object property"
    ::= { cfprApFabricMulticastPolicyEntry 6 }

cfprApFabricMulticastPolicyPolicyLevel OBJECT-TYPE
    SYNTAX       Gauge32
    MAX-ACCESS   read-only
    STATUS       current
    DESCRIPTION
        "Cisco Firepower fabric:MulticastPolicy:policyLevel
        managed object property"
    ::= { cfprApFabricMulticastPolicyEntry 7 }

cfprApFabricMulticastPolicyPolicyOwner OBJECT-TYPE
    SYNTAX       CfprApPolicyPolicyOwner
    MAX-ACCESS   read-only
    STATUS       current
    DESCRIPTION
        "Cisco Firepower fabric:MulticastPolicy:policyOwner
        managed object property"
    ::= { cfprApFabricMulticastPolicyEntry 8 }

cfprApFabricMulticastPolicyQuerierIpAddr OBJECT-TYPE
    SYNTAX       InetAddressIPv4
    MAX-ACCESS   read-only
    STATUS       current
    DESCRIPTION
        "Cisco Firepower fabric:MulticastPolicy:querierIpAddr
        managed object property"
    ::= { cfprApFabricMulticastPolicyEntry 9 }

cfprApFabricMulticastPolicyQuerierState OBJECT-TYPE
    SYNTAX       CfprApFabricQuerierType
    MAX-ACCESS   read-only
    STATUS       current
    DESCRIPTION
        "Cisco Firepower fabric:MulticastPolicy:querierState
        managed object property"
    ::= { cfprApFabricMulticastPolicyEntry 10 }

cfprApFabricMulticastPolicySnoopingState OBJECT-TYPE
    SYNTAX       CfprApFabricSnoopingType
    MAX-ACCESS   read-only
    STATUS       current
    DESCRIPTION
        "Cisco Firepower fabric:MulticastPolicy:snoopingState
        managed object property"
    ::= { cfprApFabricMulticastPolicyEntry 11 }

cfprApFabricNetGroupTable OBJECT-TYPE
    SYNTAX           SEQUENCE OF CfprApFabricNetGroupEntry
    MAX-ACCESS       not-accessible
    STATUS           current
    DESCRIPTION
        "Cisco Firepower fabric:NetGroup managed object table"
    ::= { cfprApFabricObjects 79 }

cfprApFabricNetGroupEntry OBJECT-TYPE
    SYNTAX           CfprApFabricNetGroupEntry
    MAX-ACCESS       not-accessible
    STATUS           current
    DESCRIPTION
        "Entry for the cfprApFabricNetGroupTable table."
    INDEX { cfprApFabricNetGroupInstanceId }
    ::= { cfprApFabricNetGroupTable 1 }

CfprApFabricNetGroupEntry ::= SEQUENCE {
    cfprApFabricNetGroupInstanceId                                   CfprApManagedObjectId,
    cfprApFabricNetGroupDn                                           CfprApManagedObjectDn,
    cfprApFabricNetGroupRn                                           SnmpAdminString,
    cfprApFabricNetGroupAssigned                                     Gauge32,
    cfprApFabricNetGroupAssignmentOrder                              CfprApPoolPoolAssignmentOrder,
    cfprApFabricNetGroupDescr                                        SnmpAdminString,
    cfprApFabricNetGroupId                                           Gauge32,
    cfprApFabricNetGroupIntId                                        SnmpAdminString,
    cfprApFabricNetGroupName                                         SnmpAdminString,
    cfprApFabricNetGroupNativeNet                                    SnmpAdminString,
    cfprApFabricNetGroupNativeNetDn                                  SnmpAdminString,
    cfprApFabricNetGroupOwner                                        CfprApFabricOwner,
    cfprApFabricNetGroupPeerDn                                       SnmpAdminString,
    cfprApFabricNetGroupPolicyLevel                                  Gauge32,
    cfprApFabricNetGroupPolicyOwner                                  CfprApPolicyPolicyOwner,
    cfprApFabricNetGroupSize                                         Gauge32,
    cfprApFabricNetGroupSwitchId                                     CfprApFabricNetGroupSwitchId,
    cfprApFabricNetGroupType                                         CfprApFabricNetGroupType
}

cfprApFabricNetGroupInstanceId OBJECT-TYPE
    SYNTAX       CfprApManagedObjectId
    MAX-ACCESS   not-accessible
    STATUS       current
    DESCRIPTION
        "Instance identifier of the managed object."
    ::= { cfprApFabricNetGroupEntry 1 }

cfprApFabricNetGroupDn OBJECT-TYPE
    SYNTAX       CfprApManagedObjectDn
    MAX-ACCESS   read-only
    STATUS       current
    DESCRIPTION
        "Cisco Firepower fabric:NetGroup:dn managed object property"
    ::= { cfprApFabricNetGroupEntry 2 }

cfprApFabricNetGroupRn OBJECT-TYPE
    SYNTAX       SnmpAdminString
    MAX-ACCESS   read-only
    STATUS       current
    DESCRIPTION
        "Cisco Firepower fabric:NetGroup:rn managed object property"
    ::= { cfprApFabricNetGroupEntry 3 }

cfprApFabricNetGroupAssigned OBJECT-TYPE
    SYNTAX       Gauge32
    MAX-ACCESS   read-only
    STATUS       current
    DESCRIPTION
        "Cisco Firepower fabric:NetGroup:assigned managed object property"
    ::= { cfprApFabricNetGroupEntry 4 }

cfprApFabricNetGroupAssignmentOrder OBJECT-TYPE
    SYNTAX       CfprApPoolPoolAssignmentOrder
    MAX-ACCESS   read-only
    STATUS       current
    DESCRIPTION
        "Cisco Firepower fabric:NetGroup:assignmentOrder
        managed object property"
    ::= { cfprApFabricNetGroupEntry 5 }

cfprApFabricNetGroupDescr OBJECT-TYPE
    SYNTAX       SnmpAdminString
    MAX-ACCESS   read-only
    STATUS       current
    DESCRIPTION
        "Cisco Firepower fabric:NetGroup:descr managed object property"
    ::= { cfprApFabricNetGroupEntry 6 }

cfprApFabricNetGroupId OBJECT-TYPE
    SYNTAX       Gauge32
    MAX-ACCESS   read-only
    STATUS       current
    DESCRIPTION
        "Cisco Firepower fabric:NetGroup:id managed object property"
    ::= { cfprApFabricNetGroupEntry 7 }

cfprApFabricNetGroupIntId OBJECT-TYPE
    SYNTAX       SnmpAdminString
    MAX-ACCESS   read-only
    STATUS       current
    DESCRIPTION
        "Cisco Firepower fabric:NetGroup:intId managed object property"
    ::= { cfprApFabricNetGroupEntry 8 }

cfprApFabricNetGroupName OBJECT-TYPE
    SYNTAX       SnmpAdminString
    MAX-ACCESS   read-only
    STATUS       current
    DESCRIPTION
        "Cisco Firepower fabric:NetGroup:name managed object property"
    ::= { cfprApFabricNetGroupEntry 9 }

cfprApFabricNetGroupNativeNet OBJECT-TYPE
    SYNTAX       SnmpAdminString
    MAX-ACCESS   read-only
    STATUS       current
    DESCRIPTION
        "Cisco Firepower fabric:NetGroup:nativeNet managed
        object property"
    ::= { cfprApFabricNetGroupEntry 10 }

cfprApFabricNetGroupNativeNetDn OBJECT-TYPE
    SYNTAX       SnmpAdminString
    MAX-ACCESS   read-only
    STATUS       current
    DESCRIPTION
        "Cisco Firepower fabric:NetGroup:nativeNetDn managed
        object property"
    ::= { cfprApFabricNetGroupEntry 11 }

cfprApFabricNetGroupOwner OBJECT-TYPE
    SYNTAX       CfprApFabricOwner
    MAX-ACCESS   read-only
    STATUS       current
    DESCRIPTION
        "Cisco Firepower fabric:NetGroup:owner managed object property"
    ::= { cfprApFabricNetGroupEntry 12 }

cfprApFabricNetGroupPeerDn OBJECT-TYPE
    SYNTAX       SnmpAdminString
    MAX-ACCESS   read-only
    STATUS       current
    DESCRIPTION
        "Cisco Firepower fabric:NetGroup:peerDn managed object property"
    ::= { cfprApFabricNetGroupEntry 13 }

cfprApFabricNetGroupPolicyLevel OBJECT-TYPE
    SYNTAX       Gauge32
    MAX-ACCESS   read-only
    STATUS       current
    DESCRIPTION
        "Cisco Firepower fabric:NetGroup:policyLevel managed
        object property"
    ::= { cfprApFabricNetGroupEntry 14 }

cfprApFabricNetGroupPolicyOwner OBJECT-TYPE
    SYNTAX       CfprApPolicyPolicyOwner
    MAX-ACCESS   read-only
    STATUS       current
    DESCRIPTION
        "Cisco Firepower fabric:NetGroup:policyOwner managed
        object property"
    ::= { cfprApFabricNetGroupEntry 15 }

cfprApFabricNetGroupSize OBJECT-TYPE
    SYNTAX       Gauge32
    MAX-ACCESS   read-only
    STATUS       current
    DESCRIPTION
        "Cisco Firepower fabric:NetGroup:size managed object property"
    ::= { cfprApFabricNetGroupEntry 16 }

cfprApFabricNetGroupSwitchId OBJECT-TYPE
    SYNTAX       CfprApFabricNetGroupSwitchId
    MAX-ACCESS   read-only
    STATUS       current
    DESCRIPTION
        "Cisco Firepower fabric:NetGroup:switchId managed object property"
    ::= { cfprApFabricNetGroupEntry 17 }

cfprApFabricNetGroupType OBJECT-TYPE
    SYNTAX       CfprApFabricNetGroupType
    MAX-ACCESS   read-only
    STATUS       current
    DESCRIPTION
        "Cisco Firepower fabric:NetGroup:type managed object property"
    ::= { cfprApFabricNetGroupEntry 18 }

cfprApFabricOrgVlanPolicyTable OBJECT-TYPE
    SYNTAX           SEQUENCE OF CfprApFabricOrgVlanPolicyEntry
    MAX-ACCESS       not-accessible
    STATUS           current
    DESCRIPTION
        "Cisco Firepower fabric:OrgVlanPolicy managed object table"
    ::= { cfprApFabricObjects 90 }

cfprApFabricOrgVlanPolicyEntry OBJECT-TYPE
    SYNTAX           CfprApFabricOrgVlanPolicyEntry
    MAX-ACCESS       not-accessible
    STATUS           current
    DESCRIPTION
        "Entry for the cfprApFabricOrgVlanPolicyTable table."
    INDEX { cfprApFabricOrgVlanPolicyInstanceId }
    ::= { cfprApFabricOrgVlanPolicyTable 1 }

CfprApFabricOrgVlanPolicyEntry ::= SEQUENCE {
    cfprApFabricOrgVlanPolicyInstanceId                              CfprApManagedObjectId,
    cfprApFabricOrgVlanPolicyDn                                      CfprApManagedObjectDn,
    cfprApFabricOrgVlanPolicyRn                                      SnmpAdminString,
    cfprApFabricOrgVlanPolicyAdminState                              CfprApFabricAdminState,
    cfprApFabricOrgVlanPolicyName                                    SnmpAdminString
}

cfprApFabricOrgVlanPolicyInstanceId OBJECT-TYPE
    SYNTAX       CfprApManagedObjectId
    MAX-ACCESS   not-accessible
    STATUS       current
    DESCRIPTION
        "Instance identifier of the managed object."
    ::= { cfprApFabricOrgVlanPolicyEntry 1 }

cfprApFabricOrgVlanPolicyDn OBJECT-TYPE
    SYNTAX       CfprApManagedObjectDn
    MAX-ACCESS   read-only
    STATUS       current
    DESCRIPTION
        "Cisco Firepower fabric:OrgVlanPolicy:dn managed object property"
    ::= { cfprApFabricOrgVlanPolicyEntry 2 }

cfprApFabricOrgVlanPolicyRn OBJECT-TYPE
    SYNTAX       SnmpAdminString
    MAX-ACCESS   read-only
    STATUS       current
    DESCRIPTION
        "Cisco Firepower fabric:OrgVlanPolicy:rn managed object property"
    ::= { cfprApFabricOrgVlanPolicyEntry 3 }

cfprApFabricOrgVlanPolicyAdminState OBJECT-TYPE
    SYNTAX       CfprApFabricAdminState
    MAX-ACCESS   read-only
    STATUS       current
    DESCRIPTION
        "Cisco Firepower fabric:OrgVlanPolicy:adminState
        managed object property"
    ::= { cfprApFabricOrgVlanPolicyEntry 4 }

cfprApFabricOrgVlanPolicyName OBJECT-TYPE
    SYNTAX       SnmpAdminString
    MAX-ACCESS   read-only
    STATUS       current
    DESCRIPTION
        "Cisco Firepower fabric:OrgVlanPolicy:name managed
        object property"
    ::= { cfprApFabricOrgVlanPolicyEntry 5 }

cfprApFabricPathTable OBJECT-TYPE
    SYNTAX           SEQUENCE OF CfprApFabricPathEntry
    MAX-ACCESS       not-accessible
    STATUS           current
    DESCRIPTION
        "Cisco Firepower fabric:Path managed object table"
    ::= { cfprApFabricObjects 91 }

cfprApFabricPathEntry OBJECT-TYPE
    SYNTAX           CfprApFabricPathEntry
    MAX-ACCESS       not-accessible
    STATUS           current
    DESCRIPTION
        "Entry for the cfprApFabricPathTable table."
    INDEX { cfprApFabricPathInstanceId }
    ::= { cfprApFabricPathTable 1 }

CfprApFabricPathEntry ::= SEQUENCE {
    cfprApFabricPathInstanceId                                       CfprApManagedObjectId,
    cfprApFabricPathDn                                               CfprApManagedObjectDn,
    cfprApFabricPathRn                                               SnmpAdminString,
    cfprApFabricPathCType                                            Gauge32,
    cfprApFabricPathChassisId                                        Gauge32,
    cfprApFabricPathEnacp                                            Gauge32,
    cfprApFabricPathId                                               Gauge32,
    cfprApFabricPathLocale                                           CfprApNetworkLocale,
    cfprApFabricPathName                                             SnmpAdminString,
    cfprApFabricPathNsSize                                           Gauge32,
    cfprApFabricPathSide                                             CfprApNetworkSide,
    cfprApFabricPathSwitchId                                         CfprApNetworkSwitchId,
    cfprApFabricPathTransport                                        CfprApNetworkTransport,
    cfprApFabricPathType                                             CfprApNetworkConnectionType
}

cfprApFabricPathInstanceId OBJECT-TYPE
    SYNTAX       CfprApManagedObjectId
    MAX-ACCESS   not-accessible
    STATUS       current
    DESCRIPTION
        "Instance identifier of the managed object."
    ::= { cfprApFabricPathEntry 1 }

cfprApFabricPathDn OBJECT-TYPE
    SYNTAX       CfprApManagedObjectDn
    MAX-ACCESS   read-only
    STATUS       current
    DESCRIPTION
        "Cisco Firepower fabric:Path:dn managed object property"
    ::= { cfprApFabricPathEntry 2 }

cfprApFabricPathRn OBJECT-TYPE
    SYNTAX       SnmpAdminString
    MAX-ACCESS   read-only
    STATUS       current
    DESCRIPTION
        "Cisco Firepower fabric:Path:rn managed object property"
    ::= { cfprApFabricPathEntry 3 }

cfprApFabricPathCType OBJECT-TYPE
    SYNTAX       Gauge32
    MAX-ACCESS   read-only
    STATUS       current
    DESCRIPTION
        "Cisco Firepower fabric:Path:cType managed object property"
    ::= { cfprApFabricPathEntry 4 }

cfprApFabricPathChassisId OBJECT-TYPE
    SYNTAX       Gauge32
    MAX-ACCESS   read-only
    STATUS       current
    DESCRIPTION
        "Cisco Firepower fabric:Path:chassisId managed object property"
    ::= { cfprApFabricPathEntry 5 }

cfprApFabricPathEnacp OBJECT-TYPE
    SYNTAX       Gauge32
    MAX-ACCESS   read-only
    STATUS       current
    DESCRIPTION
        "Cisco Firepower fabric:Path:enacp managed object property"
    ::= { cfprApFabricPathEntry 6 }

cfprApFabricPathId OBJECT-TYPE
    SYNTAX       Gauge32
    MAX-ACCESS   read-only
    STATUS       current
    DESCRIPTION
        "Cisco Firepower fabric:Path:id managed object property"
    ::= { cfprApFabricPathEntry 7 }

cfprApFabricPathLocale OBJECT-TYPE
    SYNTAX       CfprApNetworkLocale
    MAX-ACCESS   read-only
    STATUS       current
    DESCRIPTION
        "Cisco Firepower fabric:Path:locale managed object property"
    ::= { cfprApFabricPathEntry 8 }

cfprApFabricPathName OBJECT-TYPE
    SYNTAX       SnmpAdminString
    MAX-ACCESS   read-only
    STATUS       current
    DESCRIPTION
        "Cisco Firepower fabric:Path:name managed object property"
    ::= { cfprApFabricPathEntry 9 }

cfprApFabricPathNsSize OBJECT-TYPE
    SYNTAX       Gauge32
    MAX-ACCESS   read-only
    STATUS       current
    DESCRIPTION
        "Cisco Firepower fabric:Path:nsSize managed object property"
    ::= { cfprApFabricPathEntry 10 }

cfprApFabricPathSide OBJECT-TYPE
    SYNTAX       CfprApNetworkSide
    MAX-ACCESS   read-only
    STATUS       current
    DESCRIPTION
        "Cisco Firepower fabric:Path:side managed object property"
    ::= { cfprApFabricPathEntry 11 }

cfprApFabricPathSwitchId OBJECT-TYPE
    SYNTAX       CfprApNetworkSwitchId
    MAX-ACCESS   read-only
    STATUS       current
    DESCRIPTION
        "Cisco Firepower fabric:Path:switchId managed object property"
    ::= { cfprApFabricPathEntry 12 }

cfprApFabricPathTransport OBJECT-TYPE
    SYNTAX       CfprApNetworkTransport
    MAX-ACCESS   read-only
    STATUS       current
    DESCRIPTION
        "Cisco Firepower fabric:Path:transport managed object property"
    ::= { cfprApFabricPathEntry 13 }

cfprApFabricPathType OBJECT-TYPE
    SYNTAX       CfprApNetworkConnectionType
    MAX-ACCESS   read-only
    STATUS       current
    DESCRIPTION
        "Cisco Firepower fabric:Path:type managed object property"
    ::= { cfprApFabricPathEntry 14 }

cfprApFabricPathConnTable OBJECT-TYPE
    SYNTAX           SEQUENCE OF CfprApFabricPathConnEntry
    MAX-ACCESS       not-accessible
    STATUS           current
    DESCRIPTION
        "Cisco Firepower fabric:PathConn managed object table"
    ::= { cfprApFabricObjects 92 }

cfprApFabricPathConnEntry OBJECT-TYPE
    SYNTAX           CfprApFabricPathConnEntry
    MAX-ACCESS       not-accessible
    STATUS           current
    DESCRIPTION
        "Entry for the cfprApFabricPathConnTable table."
    INDEX { cfprApFabricPathConnInstanceId }
    ::= { cfprApFabricPathConnTable 1 }

CfprApFabricPathConnEntry ::= SEQUENCE {
    cfprApFabricPathConnInstanceId                                   CfprApManagedObjectId,
    cfprApFabricPathConnDn                                           CfprApManagedObjectDn,
    cfprApFabricPathConnRn                                           SnmpAdminString,
    cfprApFabricPathConnCType                                        Gauge32,
    cfprApFabricPathConnLocale                                       CfprApNetworkLocale,
    cfprApFabricPathConnName                                         SnmpAdminString,
    cfprApFabricPathConnTransport                                    CfprApNetworkTransport,
    cfprApFabricPathConnType                                         CfprApNetworkConnectionType
}

cfprApFabricPathConnInstanceId OBJECT-TYPE
    SYNTAX       CfprApManagedObjectId
    MAX-ACCESS   not-accessible
    STATUS       current
    DESCRIPTION
        "Instance identifier of the managed object."
    ::= { cfprApFabricPathConnEntry 1 }

cfprApFabricPathConnDn OBJECT-TYPE
    SYNTAX       CfprApManagedObjectDn
    MAX-ACCESS   read-only
    STATUS       current
    DESCRIPTION
        "Cisco Firepower fabric:PathConn:dn managed object property"
    ::= { cfprApFabricPathConnEntry 2 }

cfprApFabricPathConnRn OBJECT-TYPE
    SYNTAX       SnmpAdminString
    MAX-ACCESS   read-only
    STATUS       current
    DESCRIPTION
        "Cisco Firepower fabric:PathConn:rn managed object property"
    ::= { cfprApFabricPathConnEntry 3 }

cfprApFabricPathConnCType OBJECT-TYPE
    SYNTAX       Gauge32
    MAX-ACCESS   read-only
    STATUS       current
    DESCRIPTION
        "Cisco Firepower fabric:PathConn:cType managed object property"
    ::= { cfprApFabricPathConnEntry 4 }

cfprApFabricPathConnLocale OBJECT-TYPE
    SYNTAX       CfprApNetworkLocale
    MAX-ACCESS   read-only
    STATUS       current
    DESCRIPTION
        "Cisco Firepower fabric:PathConn:locale managed object property"
    ::= { cfprApFabricPathConnEntry 5 }

cfprApFabricPathConnName OBJECT-TYPE
    SYNTAX       SnmpAdminString
    MAX-ACCESS   read-only
    STATUS       current
    DESCRIPTION
        "Cisco Firepower fabric:PathConn:name managed object property"
    ::= { cfprApFabricPathConnEntry 6 }

cfprApFabricPathConnTransport OBJECT-TYPE
    SYNTAX       CfprApNetworkTransport
    MAX-ACCESS   read-only
    STATUS       current
    DESCRIPTION
        "Cisco Firepower fabric:PathConn:transport managed
        object property"
    ::= { cfprApFabricPathConnEntry 7 }

cfprApFabricPathConnType OBJECT-TYPE
    SYNTAX       CfprApNetworkConnectionType
    MAX-ACCESS   read-only
    STATUS       current
    DESCRIPTION
        "Cisco Firepower fabric:PathConn:type managed object property"
    ::= { cfprApFabricPathConnEntry 8 }

cfprApFabricPathEpTable OBJECT-TYPE
    SYNTAX           SEQUENCE OF CfprApFabricPathEpEntry
    MAX-ACCESS       not-accessible
    STATUS           current
    DESCRIPTION
        "Cisco Firepower fabric:PathEp managed object table"
    ::= { cfprApFabricObjects 93 }

cfprApFabricPathEpEntry OBJECT-TYPE
    SYNTAX           CfprApFabricPathEpEntry
    MAX-ACCESS       not-accessible
    STATUS           current
    DESCRIPTION
        "Entry for the cfprApFabricPathEpTable table."
    INDEX { cfprApFabricPathEpInstanceId }
    ::= { cfprApFabricPathEpTable 1 }

CfprApFabricPathEpEntry ::= SEQUENCE {
    cfprApFabricPathEpInstanceId                                     CfprApManagedObjectId,
    cfprApFabricPathEpDn                                             CfprApManagedObjectDn,
    cfprApFabricPathEpRn                                             SnmpAdminString,
    cfprApFabricPathEpAggrPortId                                     Gauge32,
    cfprApFabricPathEpCType                                          Gauge32,
    cfprApFabricPathEpChassisId                                      Gauge32,
    cfprApFabricPathEpDiagLldpTransmit                               TruthValue,
    cfprApFabricPathEpEpDn                                           SnmpAdminString,
    cfprApFabricPathEpIfRole                                         CfprApNetworkPortRole,
    cfprApFabricPathEpIfType                                         CfprApFabricPathEpIfType,
    cfprApFabricPathEpLocale                                         CfprApFabricPathEpLocale,
    cfprApFabricPathEpName                                           SnmpAdminString,
    cfprApFabricPathEpPeerAggrPortId                                 Gauge32,
    cfprApFabricPathEpPeerChassisId                                  Gauge32,
    cfprApFabricPathEpPeerDn                                         SnmpAdminString,
    cfprApFabricPathEpPeerMac                                        MacAddress,
    cfprApFabricPathEpPeerPortId                                     Gauge32,
    cfprApFabricPathEpPeerSlotId                                     Gauge32,
    cfprApFabricPathEpPortId                                         Gauge32,
    cfprApFabricPathEpSide                                           CfprApNetworkSide,
    cfprApFabricPathEpSlotId                                         Gauge32,
    cfprApFabricPathEpSwitchId                                       CfprApNetworkSwitchId,
    cfprApFabricPathEpTransport                                      CfprApNetworkTransport,
    cfprApFabricPathEpType                                           CfprApNetworkConnectionType
}

cfprApFabricPathEpInstanceId OBJECT-TYPE
    SYNTAX       CfprApManagedObjectId
    MAX-ACCESS   not-accessible
    STATUS       current
    DESCRIPTION
        "Instance identifier of the managed object."
    ::= { cfprApFabricPathEpEntry 1 }

cfprApFabricPathEpDn OBJECT-TYPE
    SYNTAX       CfprApManagedObjectDn
    MAX-ACCESS   read-only
    STATUS       current
    DESCRIPTION
        "Cisco Firepower fabric:PathEp:dn managed object property"
    ::= { cfprApFabricPathEpEntry 2 }

cfprApFabricPathEpRn OBJECT-TYPE
    SYNTAX       SnmpAdminString
    MAX-ACCESS   read-only
    STATUS       current
    DESCRIPTION
        "Cisco Firepower fabric:PathEp:rn managed object property"
    ::= { cfprApFabricPathEpEntry 3 }

cfprApFabricPathEpAggrPortId OBJECT-TYPE
    SYNTAX       Gauge32
    MAX-ACCESS   read-only
    STATUS       current
    DESCRIPTION
        "Cisco Firepower fabric:PathEp:aggrPortId managed object property"
    ::= { cfprApFabricPathEpEntry 4 }

cfprApFabricPathEpCType OBJECT-TYPE
    SYNTAX       Gauge32
    MAX-ACCESS   read-only
    STATUS       current
    DESCRIPTION
        "Cisco Firepower fabric:PathEp:cType managed object property"
    ::= { cfprApFabricPathEpEntry 5 }

cfprApFabricPathEpChassisId OBJECT-TYPE
    SYNTAX       Gauge32
    MAX-ACCESS   read-only
    STATUS       current
    DESCRIPTION
        "Cisco Firepower fabric:PathEp:chassisId managed object property"
    ::= { cfprApFabricPathEpEntry 6 }

cfprApFabricPathEpDiagLldpTransmit OBJECT-TYPE
    SYNTAX       TruthValue
    MAX-ACCESS   read-only
    STATUS       current
    DESCRIPTION
        "Cisco Firepower fabric:PathEp:diagLldpTransmit
        managed object property"
    ::= { cfprApFabricPathEpEntry 7 }

cfprApFabricPathEpEpDn OBJECT-TYPE
    SYNTAX       SnmpAdminString
    MAX-ACCESS   read-only
    STATUS       current
    DESCRIPTION
        "Cisco Firepower fabric:PathEp:epDn managed object property"
    ::= { cfprApFabricPathEpEntry 8 }

cfprApFabricPathEpIfRole OBJECT-TYPE
    SYNTAX       CfprApNetworkPortRole
    MAX-ACCESS   read-only
    STATUS       current
    DESCRIPTION
        "Cisco Firepower fabric:PathEp:ifRole managed object property"
    ::= { cfprApFabricPathEpEntry 9 }

cfprApFabricPathEpIfType OBJECT-TYPE
    SYNTAX       CfprApFabricPathEpIfType
    MAX-ACCESS   read-only
    STATUS       current
    DESCRIPTION
        "Cisco Firepower fabric:PathEp:ifType managed object property"
    ::= { cfprApFabricPathEpEntry 10 }

cfprApFabricPathEpLocale OBJECT-TYPE
    SYNTAX       CfprApFabricPathEpLocale
    MAX-ACCESS   read-only
    STATUS       current
    DESCRIPTION
        "Cisco Firepower fabric:PathEp:locale managed object property"
    ::= { cfprApFabricPathEpEntry 11 }

cfprApFabricPathEpName OBJECT-TYPE
    SYNTAX       SnmpAdminString
    MAX-ACCESS   read-only
    STATUS       current
    DESCRIPTION
        "Cisco Firepower fabric:PathEp:name managed object property"
    ::= { cfprApFabricPathEpEntry 12 }

cfprApFabricPathEpPeerAggrPortId OBJECT-TYPE
    SYNTAX       Gauge32
    MAX-ACCESS   read-only
    STATUS       current
    DESCRIPTION
        "Cisco Firepower fabric:PathEp:peerAggrPortId managed
        object property"
    ::= { cfprApFabricPathEpEntry 13 }

cfprApFabricPathEpPeerChassisId OBJECT-TYPE
    SYNTAX       Gauge32
    MAX-ACCESS   read-only
    STATUS       current
    DESCRIPTION
        "Cisco Firepower fabric:PathEp:peerChassisId managed
        object property"
    ::= { cfprApFabricPathEpEntry 14 }

cfprApFabricPathEpPeerDn OBJECT-TYPE
    SYNTAX       SnmpAdminString
    MAX-ACCESS   read-only
    STATUS       current
    DESCRIPTION
        "Cisco Firepower fabric:PathEp:peerDn managed object property"
    ::= { cfprApFabricPathEpEntry 15 }

cfprApFabricPathEpPeerMac OBJECT-TYPE
    SYNTAX       MacAddress
    MAX-ACCESS   read-only
    STATUS       current
    DESCRIPTION
        "Cisco Firepower fabric:PathEp:peerMac managed object property"
    ::= { cfprApFabricPathEpEntry 16 }

cfprApFabricPathEpPeerPortId OBJECT-TYPE
    SYNTAX       Gauge32
    MAX-ACCESS   read-only
    STATUS       current
    DESCRIPTION
        "Cisco Firepower fabric:PathEp:peerPortId managed object property"
    ::= { cfprApFabricPathEpEntry 17 }

cfprApFabricPathEpPeerSlotId OBJECT-TYPE
    SYNTAX       Gauge32
    MAX-ACCESS   read-only
    STATUS       current
    DESCRIPTION
        "Cisco Firepower fabric:PathEp:peerSlotId managed object property"
    ::= { cfprApFabricPathEpEntry 18 }

cfprApFabricPathEpPortId OBJECT-TYPE
    SYNTAX       Gauge32
    MAX-ACCESS   read-only
    STATUS       current
    DESCRIPTION
        "Cisco Firepower fabric:PathEp:portId managed object property"
    ::= { cfprApFabricPathEpEntry 19 }

cfprApFabricPathEpSide OBJECT-TYPE
    SYNTAX       CfprApNetworkSide
    MAX-ACCESS   read-only
    STATUS       current
    DESCRIPTION
        "Cisco Firepower fabric:PathEp:side managed object property"
    ::= { cfprApFabricPathEpEntry 20 }

cfprApFabricPathEpSlotId OBJECT-TYPE
    SYNTAX       Gauge32
    MAX-ACCESS   read-only
    STATUS       current
    DESCRIPTION
        "Cisco Firepower fabric:PathEp:slotId managed object property"
    ::= { cfprApFabricPathEpEntry 21 }

cfprApFabricPathEpSwitchId OBJECT-TYPE
    SYNTAX       CfprApNetworkSwitchId
    MAX-ACCESS   read-only
    STATUS       current
    DESCRIPTION
        "Cisco Firepower fabric:PathEp:switchId managed object property"
    ::= { cfprApFabricPathEpEntry 22 }

cfprApFabricPathEpTransport OBJECT-TYPE
    SYNTAX       CfprApNetworkTransport
    MAX-ACCESS   read-only
    STATUS       current
    DESCRIPTION
        "Cisco Firepower fabric:PathEp:transport managed object property"
    ::= { cfprApFabricPathEpEntry 23 }

cfprApFabricPathEpType OBJECT-TYPE
    SYNTAX       CfprApNetworkConnectionType
    MAX-ACCESS   read-only
    STATUS       current
    DESCRIPTION
        "Cisco Firepower fabric:PathEp:type managed object property"
    ::= { cfprApFabricPathEpEntry 24 }

cfprApFabricPoolableVlanTable OBJECT-TYPE
    SYNTAX           SEQUENCE OF CfprApFabricPoolableVlanEntry
    MAX-ACCESS       not-accessible
    STATUS           current
    DESCRIPTION
        "Cisco Firepower fabric:PoolableVlan managed object table"
    ::= { cfprApFabricObjects 94 }

cfprApFabricPoolableVlanEntry OBJECT-TYPE
    SYNTAX           CfprApFabricPoolableVlanEntry
    MAX-ACCESS       not-accessible
    STATUS           current
    DESCRIPTION
        "Entry for the cfprApFabricPoolableVlanTable table."
    INDEX { cfprApFabricPoolableVlanInstanceId }
    ::= { cfprApFabricPoolableVlanTable 1 }

CfprApFabricPoolableVlanEntry ::= SEQUENCE {
    cfprApFabricPoolableVlanInstanceId                               CfprApManagedObjectId,
    cfprApFabricPoolableVlanDn                                       CfprApManagedObjectDn,
    cfprApFabricPoolableVlanRn                                       SnmpAdminString,
    cfprApFabricPoolableVlanId                                       Unsigned64,
    cfprApFabricPoolableVlanPoolDn                                   SnmpAdminString
}

cfprApFabricPoolableVlanInstanceId OBJECT-TYPE
    SYNTAX       CfprApManagedObjectId
    MAX-ACCESS   not-accessible
    STATUS       current
    DESCRIPTION
        "Instance identifier of the managed object."
    ::= { cfprApFabricPoolableVlanEntry 1 }

cfprApFabricPoolableVlanDn OBJECT-TYPE
    SYNTAX       CfprApManagedObjectDn
    MAX-ACCESS   read-only
    STATUS       current
    DESCRIPTION
        "Cisco Firepower fabric:PoolableVlan:dn managed object property"
    ::= { cfprApFabricPoolableVlanEntry 2 }

cfprApFabricPoolableVlanRn OBJECT-TYPE
    SYNTAX       SnmpAdminString
    MAX-ACCESS   read-only
    STATUS       current
    DESCRIPTION
        "Cisco Firepower fabric:PoolableVlan:rn managed object property"
    ::= { cfprApFabricPoolableVlanEntry 3 }

cfprApFabricPoolableVlanId OBJECT-TYPE
    SYNTAX       Unsigned64
    MAX-ACCESS   read-only
    STATUS       current
    DESCRIPTION
        "Cisco Firepower fabric:PoolableVlan:id managed object property"
    ::= { cfprApFabricPoolableVlanEntry 4 }

cfprApFabricPoolableVlanPoolDn OBJECT-TYPE
    SYNTAX       SnmpAdminString
    MAX-ACCESS   read-only
    STATUS       current
    DESCRIPTION
        "Cisco Firepower fabric:PoolableVlan:poolDn managed
        object property"
    ::= { cfprApFabricPoolableVlanEntry 5 }

cfprApFabricPooledVlanTable OBJECT-TYPE
    SYNTAX           SEQUENCE OF CfprApFabricPooledVlanEntry
    MAX-ACCESS       not-accessible
    STATUS           current
    DESCRIPTION
        "Cisco Firepower fabric:PooledVlan managed object table"
    ::= { cfprApFabricObjects 95 }

cfprApFabricPooledVlanEntry OBJECT-TYPE
    SYNTAX           CfprApFabricPooledVlanEntry
    MAX-ACCESS       not-accessible
    STATUS           current
    DESCRIPTION
        "Entry for the cfprApFabricPooledVlanTable table."
    INDEX { cfprApFabricPooledVlanInstanceId }
    ::= { cfprApFabricPooledVlanTable 1 }

CfprApFabricPooledVlanEntry ::= SEQUENCE {
    cfprApFabricPooledVlanInstanceId                                 CfprApManagedObjectId,
    cfprApFabricPooledVlanDn                                         CfprApManagedObjectDn,
    cfprApFabricPooledVlanRn                                         SnmpAdminString,
    cfprApFabricPooledVlanAssigned                                   TruthValue,
    cfprApFabricPooledVlanAssignedToDn                               SnmpAdminString,
    cfprApFabricPooledVlanConfigIssues                               CfprApFabricPoolMemberConfigIssues,
    cfprApFabricPooledVlanName                                       SnmpAdminString,
    cfprApFabricPooledVlanPeerDn                                     SnmpAdminString,
    cfprApFabricPooledVlanPoolableDn                                 SnmpAdminString,
    cfprApFabricPooledVlanPrevAssignedToDn                           SnmpAdminString
}

cfprApFabricPooledVlanInstanceId OBJECT-TYPE
    SYNTAX       CfprApManagedObjectId
    MAX-ACCESS   not-accessible
    STATUS       current
    DESCRIPTION
        "Instance identifier of the managed object."
    ::= { cfprApFabricPooledVlanEntry 1 }

cfprApFabricPooledVlanDn OBJECT-TYPE
    SYNTAX       CfprApManagedObjectDn
    MAX-ACCESS   read-only
    STATUS       current
    DESCRIPTION
        "Cisco Firepower fabric:PooledVlan:dn managed object property"
    ::= { cfprApFabricPooledVlanEntry 2 }

cfprApFabricPooledVlanRn OBJECT-TYPE
    SYNTAX       SnmpAdminString
    MAX-ACCESS   read-only
    STATUS       current
    DESCRIPTION
        "Cisco Firepower fabric:PooledVlan:rn managed object property"
    ::= { cfprApFabricPooledVlanEntry 3 }

cfprApFabricPooledVlanAssigned OBJECT-TYPE
    SYNTAX       TruthValue
    MAX-ACCESS   read-only
    STATUS       current
    DESCRIPTION
        "Cisco Firepower fabric:PooledVlan:assigned managed
        object property"
    ::= { cfprApFabricPooledVlanEntry 4 }

cfprApFabricPooledVlanAssignedToDn OBJECT-TYPE
    SYNTAX       SnmpAdminString
    MAX-ACCESS   read-only
    STATUS       current
    DESCRIPTION
        "Cisco Firepower fabric:PooledVlan:assignedToDn
        managed object property"
    ::= { cfprApFabricPooledVlanEntry 5 }

cfprApFabricPooledVlanConfigIssues OBJECT-TYPE
    SYNTAX       CfprApFabricPoolMemberConfigIssues
    MAX-ACCESS   read-only
    STATUS       current
    DESCRIPTION
        "Cisco Firepower fabric:PooledVlan:configIssues
        managed object property"
    ::= { cfprApFabricPooledVlanEntry 6 }

cfprApFabricPooledVlanName OBJECT-TYPE
    SYNTAX       SnmpAdminString
    MAX-ACCESS   read-only
    STATUS       current
    DESCRIPTION
        "Cisco Firepower fabric:PooledVlan:name managed object property"
    ::= { cfprApFabricPooledVlanEntry 7 }

cfprApFabricPooledVlanPeerDn OBJECT-TYPE
    SYNTAX       SnmpAdminString
    MAX-ACCESS   read-only
    STATUS       current
    DESCRIPTION
        "Cisco Firepower fabric:PooledVlan:peerDn managed object property"
    ::= { cfprApFabricPooledVlanEntry 8 }

cfprApFabricPooledVlanPoolableDn OBJECT-TYPE
    SYNTAX       SnmpAdminString
    MAX-ACCESS   read-only
    STATUS       current
    DESCRIPTION
        "Cisco Firepower fabric:PooledVlan:poolableDn managed
        object property"
    ::= { cfprApFabricPooledVlanEntry 9 }

cfprApFabricPooledVlanPrevAssignedToDn OBJECT-TYPE
    SYNTAX       SnmpAdminString
    MAX-ACCESS   read-only
    STATUS       current
    DESCRIPTION
        "Cisco Firepower fabric:PooledVlan:prevAssignedToDn
        managed object property"
    ::= { cfprApFabricPooledVlanEntry 10 }

cfprApFabricSanCloudTable OBJECT-TYPE
    SYNTAX           SEQUENCE OF CfprApFabricSanCloudEntry
    MAX-ACCESS       not-accessible
    STATUS           current
    DESCRIPTION
        "Cisco Firepower fabric:SanCloud managed object table"
    ::= { cfprApFabricObjects 96 }

cfprApFabricSanCloudEntry OBJECT-TYPE
    SYNTAX           CfprApFabricSanCloudEntry
    MAX-ACCESS       not-accessible
    STATUS           current
    DESCRIPTION
        "Entry for the cfprApFabricSanCloudTable table."
    INDEX { cfprApFabricSanCloudInstanceId }
    ::= { cfprApFabricSanCloudTable 1 }

CfprApFabricSanCloudEntry ::= SEQUENCE {
    cfprApFabricSanCloudInstanceId                                   CfprApManagedObjectId,
    cfprApFabricSanCloudDn                                           CfprApManagedObjectDn,
    cfprApFabricSanCloudRn                                           SnmpAdminString,
    cfprApFabricSanCloudFsmDescr                                     SnmpAdminString,
    cfprApFabricSanCloudFsmPrev                                      SnmpAdminString,
    cfprApFabricSanCloudFsmProgr                                     Gauge32,
    cfprApFabricSanCloudFsmRmtInvErrCode                             Gauge32,
    cfprApFabricSanCloudFsmRmtInvErrDescr                            SnmpAdminString,
    cfprApFabricSanCloudFsmRmtInvRslt                                CfprApConditionRemoteInvRslt,
    cfprApFabricSanCloudFsmStageDescr                                SnmpAdminString,
    cfprApFabricSanCloudFsmStamp                                     DateAndTime,
    cfprApFabricSanCloudFsmStatus                                    SnmpAdminString,
    cfprApFabricSanCloudFsmTry                                       Gauge32,
    cfprApFabricSanCloudMode                                         CfprApFabricSwitchingMode
}

cfprApFabricSanCloudInstanceId OBJECT-TYPE
    SYNTAX       CfprApManagedObjectId
    MAX-ACCESS   not-accessible
    STATUS       current
    DESCRIPTION
        "Instance identifier of the managed object."
    ::= { cfprApFabricSanCloudEntry 1 }

cfprApFabricSanCloudDn OBJECT-TYPE
    SYNTAX       CfprApManagedObjectDn
    MAX-ACCESS   read-only
    STATUS       current
    DESCRIPTION
        "Cisco Firepower fabric:SanCloud:dn managed object property"
    ::= { cfprApFabricSanCloudEntry 2 }

cfprApFabricSanCloudRn OBJECT-TYPE
    SYNTAX       SnmpAdminString
    MAX-ACCESS   read-only
    STATUS       current
    DESCRIPTION
        "Cisco Firepower fabric:SanCloud:rn managed object property"
    ::= { cfprApFabricSanCloudEntry 3 }

cfprApFabricSanCloudFsmDescr OBJECT-TYPE
    SYNTAX       SnmpAdminString
    MAX-ACCESS   read-only
    STATUS       current
    DESCRIPTION
        "Cisco Firepower fabric:SanCloud:fsmDescr managed object property"
    ::= { cfprApFabricSanCloudEntry 4 }

cfprApFabricSanCloudFsmPrev OBJECT-TYPE
    SYNTAX       SnmpAdminString
    MAX-ACCESS   read-only
    STATUS       current
    DESCRIPTION
        "Cisco Firepower fabric:SanCloud:fsmPrev managed object property"
    ::= { cfprApFabricSanCloudEntry 5 }

cfprApFabricSanCloudFsmProgr OBJECT-TYPE
    SYNTAX       Gauge32
    MAX-ACCESS   read-only
    STATUS       current
    DESCRIPTION
        "Cisco Firepower fabric:SanCloud:fsmProgr managed object property"
    ::= { cfprApFabricSanCloudEntry 6 }

cfprApFabricSanCloudFsmRmtInvErrCode OBJECT-TYPE
    SYNTAX       Gauge32
    MAX-ACCESS   read-only
    STATUS       current
    DESCRIPTION
        "Cisco Firepower fabric:SanCloud:fsmRmtInvErrCode
        managed object property"
    ::= { cfprApFabricSanCloudEntry 7 }

cfprApFabricSanCloudFsmRmtInvErrDescr OBJECT-TYPE
    SYNTAX       SnmpAdminString
    MAX-ACCESS   read-only
    STATUS       current
    DESCRIPTION
        "Cisco Firepower fabric:SanCloud:fsmRmtInvErrDescr
        managed object property"
    ::= { cfprApFabricSanCloudEntry 8 }

cfprApFabricSanCloudFsmRmtInvRslt OBJECT-TYPE
    SYNTAX       CfprApConditionRemoteInvRslt
    MAX-ACCESS   read-only
    STATUS       current
    DESCRIPTION
        "Cisco Firepower fabric:SanCloud:fsmRmtInvRslt
        managed object property"
    ::= { cfprApFabricSanCloudEntry 9 }

cfprApFabricSanCloudFsmStageDescr OBJECT-TYPE
    SYNTAX       SnmpAdminString
    MAX-ACCESS   read-only
    STATUS       current
    DESCRIPTION
        "Cisco Firepower fabric:SanCloud:fsmStageDescr
        managed object property"
    ::= { cfprApFabricSanCloudEntry 10 }

cfprApFabricSanCloudFsmStamp OBJECT-TYPE
    SYNTAX       DateAndTime
    MAX-ACCESS   read-only
    STATUS       current
    DESCRIPTION
        "Cisco Firepower fabric:SanCloud:fsmStamp managed object property"
    ::= { cfprApFabricSanCloudEntry 11 }

cfprApFabricSanCloudFsmStatus OBJECT-TYPE
    SYNTAX       SnmpAdminString
    MAX-ACCESS   read-only
    STATUS       current
    DESCRIPTION
        "Cisco Firepower fabric:SanCloud:fsmStatus managed
        object property"
    ::= { cfprApFabricSanCloudEntry 12 }

cfprApFabricSanCloudFsmTry OBJECT-TYPE
    SYNTAX       Gauge32
    MAX-ACCESS   read-only
    STATUS       current
    DESCRIPTION
        "Cisco Firepower fabric:SanCloud:fsmTry managed object property"
    ::= { cfprApFabricSanCloudEntry 13 }

cfprApFabricSanCloudMode OBJECT-TYPE
    SYNTAX       CfprApFabricSwitchingMode
    MAX-ACCESS   read-only
    STATUS       current
    DESCRIPTION
        "Cisco Firepower fabric:SanCloud:mode managed object property"
    ::= { cfprApFabricSanCloudEntry 14 }

cfprApFabricSanCloudFsmTable OBJECT-TYPE
    SYNTAX           SEQUENCE OF CfprApFabricSanCloudFsmEntry
    MAX-ACCESS       not-accessible
    STATUS           current
    DESCRIPTION
        "Cisco Firepower fabric:SanCloudFsm managed object table"
    ::= { cfprApFabricObjects 97 }

cfprApFabricSanCloudFsmEntry OBJECT-TYPE
    SYNTAX           CfprApFabricSanCloudFsmEntry
    MAX-ACCESS       not-accessible
    STATUS           current
    DESCRIPTION
        "Entry for the cfprApFabricSanCloudFsmTable table."
    INDEX { cfprApFabricSanCloudFsmInstanceId }
    ::= { cfprApFabricSanCloudFsmTable 1 }

CfprApFabricSanCloudFsmEntry ::= SEQUENCE {
    cfprApFabricSanCloudFsmInstanceId                                CfprApManagedObjectId,
    cfprApFabricSanCloudFsmDn                                        CfprApManagedObjectDn,
    cfprApFabricSanCloudFsmRn                                        SnmpAdminString,
    cfprApFabricSanCloudFsmCompletionTime                            DateAndTime,
    cfprApFabricSanCloudFsmCurrentFsm                                CfprApFabricSanCloudFsmCurrentFsm,
    cfprApFabricSanCloudFsmDescrData                                 SnmpAdminString,
    cfprApFabricSanCloudFsmFsmStatus                                 CfprApFsmFsmStageStatus,
    cfprApFabricSanCloudFsmProgress                                  Gauge32,
    cfprApFabricSanCloudFsmRmtErrCode                                Gauge32,
    cfprApFabricSanCloudFsmRmtErrDescr                               SnmpAdminString,
    cfprApFabricSanCloudFsmRmtRslt                                   CfprApConditionRemoteInvRslt
}

cfprApFabricSanCloudFsmInstanceId OBJECT-TYPE
    SYNTAX       CfprApManagedObjectId
    MAX-ACCESS   not-accessible
    STATUS       current
    DESCRIPTION
        "Instance identifier of the managed object."
    ::= { cfprApFabricSanCloudFsmEntry 1 }

cfprApFabricSanCloudFsmDn OBJECT-TYPE
    SYNTAX       CfprApManagedObjectDn
    MAX-ACCESS   read-only
    STATUS       current
    DESCRIPTION
        "Cisco Firepower fabric:SanCloudFsm:dn managed object property"
    ::= { cfprApFabricSanCloudFsmEntry 2 }

cfprApFabricSanCloudFsmRn OBJECT-TYPE
    SYNTAX       SnmpAdminString
    MAX-ACCESS   read-only
    STATUS       current
    DESCRIPTION
        "Cisco Firepower fabric:SanCloudFsm:rn managed object property"
    ::= { cfprApFabricSanCloudFsmEntry 3 }

cfprApFabricSanCloudFsmCompletionTime OBJECT-TYPE
    SYNTAX       DateAndTime
    MAX-ACCESS   read-only
    STATUS       current
    DESCRIPTION
        "Cisco Firepower fabric:SanCloudFsm:completionTime
        managed object property"
    ::= { cfprApFabricSanCloudFsmEntry 4 }

cfprApFabricSanCloudFsmCurrentFsm OBJECT-TYPE
    SYNTAX       CfprApFabricSanCloudFsmCurrentFsm
    MAX-ACCESS   read-only
    STATUS       current
    DESCRIPTION
        "Cisco Firepower fabric:SanCloudFsm:currentFsm
        managed object property"
    ::= { cfprApFabricSanCloudFsmEntry 5 }

cfprApFabricSanCloudFsmDescrData OBJECT-TYPE
    SYNTAX       SnmpAdminString
    MAX-ACCESS   read-only
    STATUS       current
    DESCRIPTION
        "Cisco Firepower fabric:SanCloudFsm:descr managed object property"
    ::= { cfprApFabricSanCloudFsmEntry 6 }

cfprApFabricSanCloudFsmFsmStatus OBJECT-TYPE
    SYNTAX       CfprApFsmFsmStageStatus
    MAX-ACCESS   read-only
    STATUS       current
    DESCRIPTION
        "Cisco Firepower fabric:SanCloudFsm:fsmStatus managed
        object property"
    ::= { cfprApFabricSanCloudFsmEntry 7 }

cfprApFabricSanCloudFsmProgress OBJECT-TYPE
    SYNTAX       Gauge32
    MAX-ACCESS   read-only
    STATUS       current
    DESCRIPTION
        "Cisco Firepower fabric:SanCloudFsm:progress managed
        object property"
    ::= { cfprApFabricSanCloudFsmEntry 8 }

cfprApFabricSanCloudFsmRmtErrCode OBJECT-TYPE
    SYNTAX       Gauge32
    MAX-ACCESS   read-only
    STATUS       current
    DESCRIPTION
        "Cisco Firepower fabric:SanCloudFsm:rmtErrCode
        managed object property"
    ::= { cfprApFabricSanCloudFsmEntry 9 }

cfprApFabricSanCloudFsmRmtErrDescr OBJECT-TYPE
    SYNTAX       SnmpAdminString
    MAX-ACCESS   read-only
    STATUS       current
    DESCRIPTION
        "Cisco Firepower fabric:SanCloudFsm:rmtErrDescr
        managed object property"
    ::= { cfprApFabricSanCloudFsmEntry 10 }

cfprApFabricSanCloudFsmRmtRslt OBJECT-TYPE
    SYNTAX       CfprApConditionRemoteInvRslt
    MAX-ACCESS   read-only
    STATUS       current
    DESCRIPTION
        "Cisco Firepower fabric:SanCloudFsm:rmtRslt managed
        object property"
    ::= { cfprApFabricSanCloudFsmEntry 11 }

cfprApFabricSanCloudFsmStageTable OBJECT-TYPE
    SYNTAX           SEQUENCE OF CfprApFabricSanCloudFsmStageEntry
    MAX-ACCESS       not-accessible
    STATUS           current
    DESCRIPTION
        "Cisco Firepower fabric:SanCloudFsmStage managed object table"
    ::= { cfprApFabricObjects 98 }

cfprApFabricSanCloudFsmStageEntry OBJECT-TYPE
    SYNTAX           CfprApFabricSanCloudFsmStageEntry
    MAX-ACCESS       not-accessible
    STATUS           current
    DESCRIPTION
        "Entry for the cfprApFabricSanCloudFsmStageTable table."
    INDEX { cfprApFabricSanCloudFsmStageInstanceId }
    ::= { cfprApFabricSanCloudFsmStageTable 1 }

CfprApFabricSanCloudFsmStageEntry ::= SEQUENCE {
    cfprApFabricSanCloudFsmStageInstanceId                           CfprApManagedObjectId,
    cfprApFabricSanCloudFsmStageDn                                   CfprApManagedObjectDn,
    cfprApFabricSanCloudFsmStageRn                                   SnmpAdminString,
    cfprApFabricSanCloudFsmStageDescrData                            SnmpAdminString,
    cfprApFabricSanCloudFsmStageLastUpdateTime                       DateAndTime,
    cfprApFabricSanCloudFsmStageName                                 CfprApFabricSanCloudFsmStageName,
    cfprApFabricSanCloudFsmStageOrder                                Gauge32,
    cfprApFabricSanCloudFsmStageRetry                                Gauge32,
    cfprApFabricSanCloudFsmStageStageStatus                          CfprApFsmFsmStageStatus
}

cfprApFabricSanCloudFsmStageInstanceId OBJECT-TYPE
    SYNTAX       CfprApManagedObjectId
    MAX-ACCESS   not-accessible
    STATUS       current
    DESCRIPTION
        "Instance identifier of the managed object."
    ::= { cfprApFabricSanCloudFsmStageEntry 1 }

cfprApFabricSanCloudFsmStageDn OBJECT-TYPE
    SYNTAX       CfprApManagedObjectDn
    MAX-ACCESS   read-only
    STATUS       current
    DESCRIPTION
        "Cisco Firepower fabric:SanCloudFsmStage:dn managed
        object property"
    ::= { cfprApFabricSanCloudFsmStageEntry 2 }

cfprApFabricSanCloudFsmStageRn OBJECT-TYPE
    SYNTAX       SnmpAdminString
    MAX-ACCESS   read-only
    STATUS       current
    DESCRIPTION
        "Cisco Firepower fabric:SanCloudFsmStage:rn managed
        object property"
    ::= { cfprApFabricSanCloudFsmStageEntry 3 }

cfprApFabricSanCloudFsmStageDescrData OBJECT-TYPE
    SYNTAX       SnmpAdminString
    MAX-ACCESS   read-only
    STATUS       current
    DESCRIPTION
        "Cisco Firepower fabric:SanCloudFsmStage:descr
        managed object property"
    ::= { cfprApFabricSanCloudFsmStageEntry 4 }

cfprApFabricSanCloudFsmStageLastUpdateTime OBJECT-TYPE
    SYNTAX       DateAndTime
    MAX-ACCESS   read-only
    STATUS       current
    DESCRIPTION
        "Cisco Firepower fabric:SanCloudFsmStage:lastUpdateTime
        managed object property"
    ::= { cfprApFabricSanCloudFsmStageEntry 5 }

cfprApFabricSanCloudFsmStageName OBJECT-TYPE
    SYNTAX       CfprApFabricSanCloudFsmStageName
    MAX-ACCESS   read-only
    STATUS       current
    DESCRIPTION
        "Cisco Firepower fabric:SanCloudFsmStage:name managed
        object property"
    ::= { cfprApFabricSanCloudFsmStageEntry 6 }

cfprApFabricSanCloudFsmStageOrder OBJECT-TYPE
    SYNTAX       Gauge32
    MAX-ACCESS   read-only
    STATUS       current
    DESCRIPTION
        "Cisco Firepower fabric:SanCloudFsmStage:order
        managed object property"
    ::= { cfprApFabricSanCloudFsmStageEntry 7 }

cfprApFabricSanCloudFsmStageRetry OBJECT-TYPE
    SYNTAX       Gauge32
    MAX-ACCESS   read-only
    STATUS       current
    DESCRIPTION
        "Cisco Firepower fabric:SanCloudFsmStage:retry
        managed object property"
    ::= { cfprApFabricSanCloudFsmStageEntry 8 }

cfprApFabricSanCloudFsmStageStageStatus OBJECT-TYPE
    SYNTAX       CfprApFsmFsmStageStatus
    MAX-ACCESS   read-only
    STATUS       current
    DESCRIPTION
        "Cisco Firepower fabric:SanCloudFsmStage:stageStatus
        managed object property"
    ::= { cfprApFabricSanCloudFsmStageEntry 9 }

cfprApFabricSanCloudFsmTaskTable OBJECT-TYPE
    SYNTAX           SEQUENCE OF CfprApFabricSanCloudFsmTaskEntry
    MAX-ACCESS       not-accessible
    STATUS           current
    DESCRIPTION
        "Cisco Firepower fabric:SanCloudFsmTask managed object table"
    ::= { cfprApFabricObjects 99 }

cfprApFabricSanCloudFsmTaskEntry OBJECT-TYPE
    SYNTAX           CfprApFabricSanCloudFsmTaskEntry
    MAX-ACCESS       not-accessible
    STATUS           current
    DESCRIPTION
        "Entry for the cfprApFabricSanCloudFsmTaskTable table."
    INDEX { cfprApFabricSanCloudFsmTaskInstanceId }
    ::= { cfprApFabricSanCloudFsmTaskTable 1 }

CfprApFabricSanCloudFsmTaskEntry ::= SEQUENCE {
    cfprApFabricSanCloudFsmTaskInstanceId                            CfprApManagedObjectId,
    cfprApFabricSanCloudFsmTaskDn                                    CfprApManagedObjectDn,
    cfprApFabricSanCloudFsmTaskRn                                    SnmpAdminString,
    cfprApFabricSanCloudFsmTaskCompletion                            CfprApFsmCompletion,
    cfprApFabricSanCloudFsmTaskFlags                                 CfprApFsmFlags,
    cfprApFabricSanCloudFsmTaskItem                                  CfprApFabricSanCloudFsmTaskItem,
    cfprApFabricSanCloudFsmTaskSeqId                                 Gauge32
}

cfprApFabricSanCloudFsmTaskInstanceId OBJECT-TYPE
    SYNTAX       CfprApManagedObjectId
    MAX-ACCESS   not-accessible
    STATUS       current
    DESCRIPTION
        "Instance identifier of the managed object."
    ::= { cfprApFabricSanCloudFsmTaskEntry 1 }

cfprApFabricSanCloudFsmTaskDn OBJECT-TYPE
    SYNTAX       CfprApManagedObjectDn
    MAX-ACCESS   read-only
    STATUS       current
    DESCRIPTION
        "Cisco Firepower fabric:SanCloudFsmTask:dn managed
        object property"
    ::= { cfprApFabricSanCloudFsmTaskEntry 2 }

cfprApFabricSanCloudFsmTaskRn OBJECT-TYPE
    SYNTAX       SnmpAdminString
    MAX-ACCESS   read-only
    STATUS       current
    DESCRIPTION
        "Cisco Firepower fabric:SanCloudFsmTask:rn managed
        object property"
    ::= { cfprApFabricSanCloudFsmTaskEntry 3 }

cfprApFabricSanCloudFsmTaskCompletion OBJECT-TYPE
    SYNTAX       CfprApFsmCompletion
    MAX-ACCESS   read-only
    STATUS       current
    DESCRIPTION
        "Cisco Firepower fabric:SanCloudFsmTask:completion
        managed object property"
    ::= { cfprApFabricSanCloudFsmTaskEntry 4 }

cfprApFabricSanCloudFsmTaskFlags OBJECT-TYPE
    SYNTAX       CfprApFsmFlags
    MAX-ACCESS   read-only
    STATUS       current
    DESCRIPTION
        "Cisco Firepower fabric:SanCloudFsmTask:flags managed
        object property"
    ::= { cfprApFabricSanCloudFsmTaskEntry 5 }

cfprApFabricSanCloudFsmTaskItem OBJECT-TYPE
    SYNTAX       CfprApFabricSanCloudFsmTaskItem
    MAX-ACCESS   read-only
    STATUS       current
    DESCRIPTION
        "Cisco Firepower fabric:SanCloudFsmTask:item managed
        object property"
    ::= { cfprApFabricSanCloudFsmTaskEntry 6 }

cfprApFabricSanCloudFsmTaskSeqId OBJECT-TYPE
    SYNTAX       Gauge32
    MAX-ACCESS   read-only
    STATUS       current
    DESCRIPTION
        "Cisco Firepower fabric:SanCloudFsmTask:seqId managed
        object property"
    ::= { cfprApFabricSanCloudFsmTaskEntry 7 }

cfprApFabricSanPinGroupTable OBJECT-TYPE
    SYNTAX           SEQUENCE OF CfprApFabricSanPinGroupEntry
    MAX-ACCESS       not-accessible
    STATUS           current
    DESCRIPTION
        "Cisco Firepower fabric:SanPinGroup managed object table"
    ::= { cfprApFabricObjects 101 }

cfprApFabricSanPinGroupEntry OBJECT-TYPE
    SYNTAX           CfprApFabricSanPinGroupEntry
    MAX-ACCESS       not-accessible
    STATUS           current
    DESCRIPTION
        "Entry for the cfprApFabricSanPinGroupTable table."
    INDEX { cfprApFabricSanPinGroupInstanceId }
    ::= { cfprApFabricSanPinGroupTable 1 }

CfprApFabricSanPinGroupEntry ::= SEQUENCE {
    cfprApFabricSanPinGroupInstanceId                                CfprApManagedObjectId,
    cfprApFabricSanPinGroupDn                                        CfprApManagedObjectDn,
    cfprApFabricSanPinGroupRn                                        SnmpAdminString,
    cfprApFabricSanPinGroupDescr                                     SnmpAdminString,
    cfprApFabricSanPinGroupIntId                                     SnmpAdminString,
    cfprApFabricSanPinGroupName                                      SnmpAdminString,
    cfprApFabricSanPinGroupPolicyLevel                               Gauge32,
    cfprApFabricSanPinGroupPolicyOwner                               CfprApPolicyPolicyOwner,
    cfprApFabricSanPinGroupSize                                      Gauge32
}

cfprApFabricSanPinGroupInstanceId OBJECT-TYPE
    SYNTAX       CfprApManagedObjectId
    MAX-ACCESS   not-accessible
    STATUS       current
    DESCRIPTION
        "Instance identifier of the managed object."
    ::= { cfprApFabricSanPinGroupEntry 1 }

cfprApFabricSanPinGroupDn OBJECT-TYPE
    SYNTAX       CfprApManagedObjectDn
    MAX-ACCESS   read-only
    STATUS       current
    DESCRIPTION
        "Cisco Firepower fabric:SanPinGroup:dn managed object property"
    ::= { cfprApFabricSanPinGroupEntry 2 }

cfprApFabricSanPinGroupRn OBJECT-TYPE
    SYNTAX       SnmpAdminString
    MAX-ACCESS   read-only
    STATUS       current
    DESCRIPTION
        "Cisco Firepower fabric:SanPinGroup:rn managed object property"
    ::= { cfprApFabricSanPinGroupEntry 3 }

cfprApFabricSanPinGroupDescr OBJECT-TYPE
    SYNTAX       SnmpAdminString
    MAX-ACCESS   read-only
    STATUS       current
    DESCRIPTION
        "Cisco Firepower fabric:SanPinGroup:descr managed object property"
    ::= { cfprApFabricSanPinGroupEntry 4 }

cfprApFabricSanPinGroupIntId OBJECT-TYPE
    SYNTAX       SnmpAdminString
    MAX-ACCESS   read-only
    STATUS       current
    DESCRIPTION
        "Cisco Firepower fabric:SanPinGroup:intId managed object property"
    ::= { cfprApFabricSanPinGroupEntry 5 }

cfprApFabricSanPinGroupName OBJECT-TYPE
    SYNTAX       SnmpAdminString
    MAX-ACCESS   read-only
    STATUS       current
    DESCRIPTION
        "Cisco Firepower fabric:SanPinGroup:name managed object property"
    ::= { cfprApFabricSanPinGroupEntry 6 }

cfprApFabricSanPinGroupPolicyLevel OBJECT-TYPE
    SYNTAX       Gauge32
    MAX-ACCESS   read-only
    STATUS       current
    DESCRIPTION
        "Cisco Firepower fabric:SanPinGroup:policyLevel
        managed object property"
    ::= { cfprApFabricSanPinGroupEntry 7 }

cfprApFabricSanPinGroupPolicyOwner OBJECT-TYPE
    SYNTAX       CfprApPolicyPolicyOwner
    MAX-ACCESS   read-only
    STATUS       current
    DESCRIPTION
        "Cisco Firepower fabric:SanPinGroup:policyOwner
        managed object property"
    ::= { cfprApFabricSanPinGroupEntry 8 }

cfprApFabricSanPinGroupSize OBJECT-TYPE
    SYNTAX       Gauge32
    MAX-ACCESS   read-only
    STATUS       current
    DESCRIPTION
        "Cisco Firepower fabric:SanPinGroup:size managed object property"
    ::= { cfprApFabricSanPinGroupEntry 9 }

cfprApFabricSanPinTargetTable OBJECT-TYPE
    SYNTAX           SEQUENCE OF CfprApFabricSanPinTargetEntry
    MAX-ACCESS       not-accessible
    STATUS           current
    DESCRIPTION
        "Cisco Firepower fabric:SanPinTarget managed object table"
    ::= { cfprApFabricObjects 102 }

cfprApFabricSanPinTargetEntry OBJECT-TYPE
    SYNTAX           CfprApFabricSanPinTargetEntry
    MAX-ACCESS       not-accessible
    STATUS           current
    DESCRIPTION
        "Entry for the cfprApFabricSanPinTargetTable table."
    INDEX { cfprApFabricSanPinTargetInstanceId }
    ::= { cfprApFabricSanPinTargetTable 1 }

CfprApFabricSanPinTargetEntry ::= SEQUENCE {
    cfprApFabricSanPinTargetInstanceId                               CfprApManagedObjectId,
    cfprApFabricSanPinTargetDn                                       CfprApManagedObjectDn,
    cfprApFabricSanPinTargetRn                                       SnmpAdminString,
    cfprApFabricSanPinTargetEpDn                                     SnmpAdminString,
    cfprApFabricSanPinTargetFabricId                                 SnmpAdminString,
    cfprApFabricSanPinTargetTargetStatus                             CfprApFabricTargetStatus
}

cfprApFabricSanPinTargetInstanceId OBJECT-TYPE
    SYNTAX       CfprApManagedObjectId
    MAX-ACCESS   not-accessible
    STATUS       current
    DESCRIPTION
        "Instance identifier of the managed object."
    ::= { cfprApFabricSanPinTargetEntry 1 }

cfprApFabricSanPinTargetDn OBJECT-TYPE
    SYNTAX       CfprApManagedObjectDn
    MAX-ACCESS   read-only
    STATUS       current
    DESCRIPTION
        "Cisco Firepower fabric:SanPinTarget:dn managed object property"
    ::= { cfprApFabricSanPinTargetEntry 2 }

cfprApFabricSanPinTargetRn OBJECT-TYPE
    SYNTAX       SnmpAdminString
    MAX-ACCESS   read-only
    STATUS       current
    DESCRIPTION
        "Cisco Firepower fabric:SanPinTarget:rn managed object property"
    ::= { cfprApFabricSanPinTargetEntry 3 }

cfprApFabricSanPinTargetEpDn OBJECT-TYPE
    SYNTAX       SnmpAdminString
    MAX-ACCESS   read-only
    STATUS       current
    DESCRIPTION
        "Cisco Firepower fabric:SanPinTarget:epDn managed object property"
    ::= { cfprApFabricSanPinTargetEntry 4 }

cfprApFabricSanPinTargetFabricId OBJECT-TYPE
    SYNTAX       SnmpAdminString
    MAX-ACCESS   read-only
    STATUS       current
    DESCRIPTION
        "Cisco Firepower fabric:SanPinTarget:fabricId managed
        object property"
    ::= { cfprApFabricSanPinTargetEntry 5 }

cfprApFabricSanPinTargetTargetStatus OBJECT-TYPE
    SYNTAX       CfprApFabricTargetStatus
    MAX-ACCESS   read-only
    STATUS       current
    DESCRIPTION
        "Cisco Firepower fabric:SanPinTarget:targetStatus
        managed object property"
    ::= { cfprApFabricSanPinTargetEntry 6 }

cfprApFabricSspEthMonTable OBJECT-TYPE
    SYNTAX           SEQUENCE OF CfprApFabricSspEthMonEntry
    MAX-ACCESS       not-accessible
    STATUS           current
    DESCRIPTION
        "Cisco Firepower fabric:SspEthMon managed object table"
    ::= { cfprApFabricObjects 103 }

cfprApFabricSspEthMonEntry OBJECT-TYPE
    SYNTAX           CfprApFabricSspEthMonEntry
    MAX-ACCESS       not-accessible
    STATUS           current
    DESCRIPTION
        "Entry for the cfprApFabricSspEthMonTable table."
    INDEX { cfprApFabricSspEthMonInstanceId }
    ::= { cfprApFabricSspEthMonTable 1 }

CfprApFabricSspEthMonEntry ::= SEQUENCE {
    cfprApFabricSspEthMonInstanceId                                  CfprApManagedObjectId,
    cfprApFabricSspEthMonDn                                          CfprApManagedObjectDn,
    cfprApFabricSspEthMonRn                                          SnmpAdminString,
    cfprApFabricSspEthMonAdminState                                  CfprApFabricSspMonAdminState,
    cfprApFabricSspEthMonAppendFlag                                  CfprApFabricSspEthMonAppendFlag,
    cfprApFabricSspEthMonConfigFailReason                            SnmpAdminString,
    cfprApFabricSspEthMonDelPcap                                     CfprApFabricSspMonDelPcap,
    cfprApFabricSspEthMonDropCount                                   Unsigned64,
    cfprApFabricSspEthMonErrorCode                                   SnmpAdminString,
    cfprApFabricSspEthMonId                                          CfprApNetworkSwitchId,
    cfprApFabricSspEthMonIsConfigSuccess                             TruthValue,
    cfprApFabricSspEthMonIsConfiguredByAG                            TruthValue,
    cfprApFabricSspEthMonName                                        SnmpAdminString,
    cfprApFabricSspEthMonOperState                                   CfprApFabricSspMonOperState,
    cfprApFabricSspEthMonOperStateReason                             CfprApFabricSspMonOperStateReason,
    cfprApFabricSspEthMonPeerDn                                      SnmpAdminString,
    cfprApFabricSspEthMonReBoot                                      SnmpAdminString,
    cfprApFabricSspEthMonSession                                     Gauge32,
    cfprApFabricSspEthMonSessionMemUsage                             Gauge32,
    cfprApFabricSspEthMonSourceConfigured                            Gauge32
}

cfprApFabricSspEthMonInstanceId OBJECT-TYPE
    SYNTAX       CfprApManagedObjectId
    MAX-ACCESS   not-accessible
    STATUS       current
    DESCRIPTION
        "Instance identifier of the managed object."
    ::= { cfprApFabricSspEthMonEntry 1 }

cfprApFabricSspEthMonDn OBJECT-TYPE
    SYNTAX       CfprApManagedObjectDn
    MAX-ACCESS   read-only
    STATUS       current
    DESCRIPTION
        "Cisco Firepower fabric:SspEthMon:dn managed object property"
    ::= { cfprApFabricSspEthMonEntry 2 }

cfprApFabricSspEthMonRn OBJECT-TYPE
    SYNTAX       SnmpAdminString
    MAX-ACCESS   read-only
    STATUS       current
    DESCRIPTION
        "Cisco Firepower fabric:SspEthMon:rn managed object property"
    ::= { cfprApFabricSspEthMonEntry 3 }

cfprApFabricSspEthMonAdminState OBJECT-TYPE
    SYNTAX       CfprApFabricSspMonAdminState
    MAX-ACCESS   read-only
    STATUS       current
    DESCRIPTION
        "Cisco Firepower fabric:SspEthMon:adminState managed
        object property"
    ::= { cfprApFabricSspEthMonEntry 4 }

cfprApFabricSspEthMonAppendFlag OBJECT-TYPE
    SYNTAX       CfprApFabricSspEthMonAppendFlag
    MAX-ACCESS   read-only
    STATUS       current
    DESCRIPTION
        "Cisco Firepower fabric:SspEthMon:appendFlag managed
        object property"
    ::= { cfprApFabricSspEthMonEntry 5 }

cfprApFabricSspEthMonConfigFailReason OBJECT-TYPE
    SYNTAX       SnmpAdminString
    MAX-ACCESS   read-only
    STATUS       current
    DESCRIPTION
        "Cisco Firepower fabric:SspEthMon:configFailReason
        managed object property"
    ::= { cfprApFabricSspEthMonEntry 6 }

cfprApFabricSspEthMonDelPcap OBJECT-TYPE
    SYNTAX       CfprApFabricSspMonDelPcap
    MAX-ACCESS   read-only
    STATUS       current
    DESCRIPTION
        "Cisco Firepower fabric:SspEthMon:delPcap managed object property"
    ::= { cfprApFabricSspEthMonEntry 7 }

cfprApFabricSspEthMonDropCount OBJECT-TYPE
    SYNTAX       Unsigned64
    MAX-ACCESS   read-only
    STATUS       current
    DESCRIPTION
        "Cisco Firepower fabric:SspEthMon:dropCount managed
        object property"
    ::= { cfprApFabricSspEthMonEntry 8 }

cfprApFabricSspEthMonErrorCode OBJECT-TYPE
    SYNTAX       SnmpAdminString
    MAX-ACCESS   read-only
    STATUS       current
    DESCRIPTION
        "Cisco Firepower fabric:SspEthMon:errorCode managed
        object property"
    ::= { cfprApFabricSspEthMonEntry 9 }

cfprApFabricSspEthMonId OBJECT-TYPE
    SYNTAX       CfprApNetworkSwitchId
    MAX-ACCESS   read-only
    STATUS       current
    DESCRIPTION
        "Cisco Firepower fabric:SspEthMon:id managed object property"
    ::= { cfprApFabricSspEthMonEntry 10 }

cfprApFabricSspEthMonIsConfigSuccess OBJECT-TYPE
    SYNTAX       TruthValue
    MAX-ACCESS   read-only
    STATUS       current
    DESCRIPTION
        "Cisco Firepower fabric:SspEthMon:isConfigSuccess
        managed object property"
    ::= { cfprApFabricSspEthMonEntry 11 }

cfprApFabricSspEthMonIsConfiguredByAG OBJECT-TYPE
    SYNTAX       TruthValue
    MAX-ACCESS   read-only
    STATUS       current
    DESCRIPTION
        "Cisco Firepower fabric:SspEthMon:isConfiguredByAG
        managed object property"
    ::= { cfprApFabricSspEthMonEntry 12 }

cfprApFabricSspEthMonName OBJECT-TYPE
    SYNTAX       SnmpAdminString
    MAX-ACCESS   read-only
    STATUS       current
    DESCRIPTION
        "Cisco Firepower fabric:SspEthMon:name managed object property"
    ::= { cfprApFabricSspEthMonEntry 13 }

cfprApFabricSspEthMonOperState OBJECT-TYPE
    SYNTAX       CfprApFabricSspMonOperState
    MAX-ACCESS   read-only
    STATUS       current
    DESCRIPTION
        "Cisco Firepower fabric:SspEthMon:operState managed
        object property"
    ::= { cfprApFabricSspEthMonEntry 14 }

cfprApFabricSspEthMonOperStateReason OBJECT-TYPE
    SYNTAX       CfprApFabricSspMonOperStateReason
    MAX-ACCESS   read-only
    STATUS       current
    DESCRIPTION
        "Cisco Firepower fabric:SspEthMon:operStateReason
        managed object property"
    ::= { cfprApFabricSspEthMonEntry 15 }

cfprApFabricSspEthMonPeerDn OBJECT-TYPE
    SYNTAX       SnmpAdminString
    MAX-ACCESS   read-only
    STATUS       current
    DESCRIPTION
        "Cisco Firepower fabric:SspEthMon:peerDn managed object property"
    ::= { cfprApFabricSspEthMonEntry 16 }

cfprApFabricSspEthMonReBoot OBJECT-TYPE
    SYNTAX       SnmpAdminString
    MAX-ACCESS   read-only
    STATUS       current
    DESCRIPTION
        "Cisco Firepower fabric:SspEthMon:reBoot managed object property"
    ::= { cfprApFabricSspEthMonEntry 17 }

cfprApFabricSspEthMonSession OBJECT-TYPE
    SYNTAX       Gauge32
    MAX-ACCESS   read-only
    STATUS       current
    DESCRIPTION
        "Cisco Firepower fabric:SspEthMon:session managed object property"
    ::= { cfprApFabricSspEthMonEntry 18 }

cfprApFabricSspEthMonSessionMemUsage OBJECT-TYPE
    SYNTAX       Gauge32
    MAX-ACCESS   read-only
    STATUS       current
    DESCRIPTION
        "Cisco Firepower fabric:SspEthMon:sessionMemUsage
        managed object property"
    ::= { cfprApFabricSspEthMonEntry 19 }

cfprApFabricSspEthMonSourceConfigured OBJECT-TYPE
    SYNTAX       Gauge32
    MAX-ACCESS   read-only
    STATUS       current
    DESCRIPTION
        "Cisco Firepower fabric:SspEthMon:sourceConfigured
        managed object property"
    ::= { cfprApFabricSspEthMonEntry 20 }

cfprApFabricSspEthMonFilterEpTable OBJECT-TYPE
    SYNTAX           SEQUENCE OF CfprApFabricSspEthMonFilterEpEntry
    MAX-ACCESS       not-accessible
    STATUS           current
    DESCRIPTION
        "Cisco Firepower fabric:SspEthMonFilterEp managed object table"
    ::= { cfprApFabricObjects 104 }

cfprApFabricSspEthMonFilterEpEntry OBJECT-TYPE
    SYNTAX           CfprApFabricSspEthMonFilterEpEntry
    MAX-ACCESS       not-accessible
    STATUS           current
    DESCRIPTION
        "Entry for the cfprApFabricSspEthMonFilterEpTable table."
    INDEX { cfprApFabricSspEthMonFilterEpInstanceId }
    ::= { cfprApFabricSspEthMonFilterEpTable 1 }

CfprApFabricSspEthMonFilterEpEntry ::= SEQUENCE {
    cfprApFabricSspEthMonFilterEpInstanceId                          CfprApManagedObjectId,
    cfprApFabricSspEthMonFilterEpDn                                  CfprApManagedObjectDn,
    cfprApFabricSspEthMonFilterEpRn                                  SnmpAdminString,
    cfprApFabricSspEthMonFilterEpDestIp                              InetAddressIPv4,
    cfprApFabricSspEthMonFilterEpDestMAC                             MacAddress,
    cfprApFabricSspEthMonFilterEpDestPort                            Gauge32,
    cfprApFabricSspEthMonFilterEpEthertype                           Gauge32,
    cfprApFabricSspEthMonFilterEpIvlan                               Gauge32,
    cfprApFabricSspEthMonFilterEpNameId                              SnmpAdminString,
    cfprApFabricSspEthMonFilterEpOvlan                               Gauge32,
    cfprApFabricSspEthMonFilterEpProtocol                            Gauge32,
    cfprApFabricSspEthMonFilterEpSrcIp                               InetAddressIPv4,
    cfprApFabricSspEthMonFilterEpSrcMAC                              MacAddress,
    cfprApFabricSspEthMonFilterEpSrcPort                             Gauge32
}

cfprApFabricSspEthMonFilterEpInstanceId OBJECT-TYPE
    SYNTAX       CfprApManagedObjectId
    MAX-ACCESS   not-accessible
    STATUS       current
    DESCRIPTION
        "Instance identifier of the managed object."
    ::= { cfprApFabricSspEthMonFilterEpEntry 1 }

cfprApFabricSspEthMonFilterEpDn OBJECT-TYPE
    SYNTAX       CfprApManagedObjectDn
    MAX-ACCESS   read-only
    STATUS       current
    DESCRIPTION
        "Cisco Firepower fabric:SspEthMonFilterEp:dn managed
        object property"
    ::= { cfprApFabricSspEthMonFilterEpEntry 2 }

cfprApFabricSspEthMonFilterEpRn OBJECT-TYPE
    SYNTAX       SnmpAdminString
    MAX-ACCESS   read-only
    STATUS       current
    DESCRIPTION
        "Cisco Firepower fabric:SspEthMonFilterEp:rn managed
        object property"
    ::= { cfprApFabricSspEthMonFilterEpEntry 3 }

cfprApFabricSspEthMonFilterEpDestIp OBJECT-TYPE
    SYNTAX       InetAddressIPv4
    MAX-ACCESS   read-only
    STATUS       current
    DESCRIPTION
        "Cisco Firepower fabric:SspEthMonFilterEp:destIp
        managed object property"
    ::= { cfprApFabricSspEthMonFilterEpEntry 4 }

cfprApFabricSspEthMonFilterEpDestMAC OBJECT-TYPE
    SYNTAX       MacAddress
    MAX-ACCESS   read-only
    STATUS       current
    DESCRIPTION
        "Cisco Firepower fabric:SspEthMonFilterEp:destMAC
        managed object property"
    ::= { cfprApFabricSspEthMonFilterEpEntry 5 }

cfprApFabricSspEthMonFilterEpDestPort OBJECT-TYPE
    SYNTAX       Gauge32
    MAX-ACCESS   read-only
    STATUS       current
    DESCRIPTION
        "Cisco Firepower fabric:SspEthMonFilterEp:destPort
        managed object property"
    ::= { cfprApFabricSspEthMonFilterEpEntry 6 }

cfprApFabricSspEthMonFilterEpEthertype OBJECT-TYPE
    SYNTAX       Gauge32
    MAX-ACCESS   read-only
    STATUS       current
    DESCRIPTION
        "Cisco Firepower fabric:SspEthMonFilterEp:ethertype
        managed object property"
    ::= { cfprApFabricSspEthMonFilterEpEntry 7 }

cfprApFabricSspEthMonFilterEpIvlan OBJECT-TYPE
    SYNTAX       Gauge32
    MAX-ACCESS   read-only
    STATUS       current
    DESCRIPTION
        "Cisco Firepower fabric:SspEthMonFilterEp:ivlan
        managed object property"
    ::= { cfprApFabricSspEthMonFilterEpEntry 8 }

cfprApFabricSspEthMonFilterEpNameId OBJECT-TYPE
    SYNTAX       SnmpAdminString
    MAX-ACCESS   read-only
    STATUS       current
    DESCRIPTION
        "Cisco Firepower fabric:SspEthMonFilterEp:nameId
        managed object property"
    ::= { cfprApFabricSspEthMonFilterEpEntry 9 }

cfprApFabricSspEthMonFilterEpOvlan OBJECT-TYPE
    SYNTAX       Gauge32
    MAX-ACCESS   read-only
    STATUS       current
    DESCRIPTION
        "Cisco Firepower fabric:SspEthMonFilterEp:ovlan
        managed object property"
    ::= { cfprApFabricSspEthMonFilterEpEntry 10 }

cfprApFabricSspEthMonFilterEpProtocol OBJECT-TYPE
    SYNTAX       Gauge32
    MAX-ACCESS   read-only
    STATUS       current
    DESCRIPTION
        "Cisco Firepower fabric:SspEthMonFilterEp:protocol
        managed object property"
    ::= { cfprApFabricSspEthMonFilterEpEntry 11 }

cfprApFabricSspEthMonFilterEpSrcIp OBJECT-TYPE
    SYNTAX       InetAddressIPv4
    MAX-ACCESS   read-only
    STATUS       current
    DESCRIPTION
        "Cisco Firepower fabric:SspEthMonFilterEp:srcIp
        managed object property"
    ::= { cfprApFabricSspEthMonFilterEpEntry 12 }

cfprApFabricSspEthMonFilterEpSrcMAC OBJECT-TYPE
    SYNTAX       MacAddress
    MAX-ACCESS   read-only
    STATUS       current
    DESCRIPTION
        "Cisco Firepower fabric:SspEthMonFilterEp:srcMAC
        managed object property"
    ::= { cfprApFabricSspEthMonFilterEpEntry 13 }

cfprApFabricSspEthMonFilterEpSrcPort OBJECT-TYPE
    SYNTAX       Gauge32
    MAX-ACCESS   read-only
    STATUS       current
    DESCRIPTION
        "Cisco Firepower fabric:SspEthMonFilterEp:srcPort
        managed object property"
    ::= { cfprApFabricSspEthMonFilterEpEntry 14 }

cfprApFabricSspEthMonSrcAppEpTable OBJECT-TYPE
    SYNTAX           SEQUENCE OF CfprApFabricSspEthMonSrcAppEpEntry
    MAX-ACCESS       not-accessible
    STATUS           current
    DESCRIPTION
        "Cisco Firepower fabric:SspEthMonSrcAppEp managed object table"
    ::= { cfprApFabricObjects 105 }

cfprApFabricSspEthMonSrcAppEpEntry OBJECT-TYPE
    SYNTAX           CfprApFabricSspEthMonSrcAppEpEntry
    MAX-ACCESS       not-accessible
    STATUS           current
    DESCRIPTION
        "Entry for the cfprApFabricSspEthMonSrcAppEpTable table."
    INDEX { cfprApFabricSspEthMonSrcAppEpInstanceId }
    ::= { cfprApFabricSspEthMonSrcAppEpTable 1 }

CfprApFabricSspEthMonSrcAppEpEntry ::= SEQUENCE {
    cfprApFabricSspEthMonSrcAppEpInstanceId                          CfprApManagedObjectId,
    cfprApFabricSspEthMonSrcAppEpDn                                  CfprApManagedObjectDn,
    cfprApFabricSspEthMonSrcAppEpRn                                  SnmpAdminString,
    cfprApFabricSspEthMonSrcAppEpAppName                             SnmpAdminString,
    cfprApFabricSspEthMonSrcAppEpFilter                              SnmpAdminString,
    cfprApFabricSspEthMonSrcAppEpLinkName                            SnmpAdminString,
    cfprApFabricSspEthMonSrcAppEpPcapfile                            SnmpAdminString,
    cfprApFabricSspEthMonSrcAppEpPcapfilename                        SnmpAdminString,
    cfprApFabricSspEthMonSrcAppEpPcapsize                            Gauge32,
    cfprApFabricSspEthMonSrcAppEpPortName                            SnmpAdminString,
    cfprApFabricSspEthMonSrcAppEpSlotId                              CfprApFabricPktCaptureAppSlotId
}

cfprApFabricSspEthMonSrcAppEpInstanceId OBJECT-TYPE
    SYNTAX       CfprApManagedObjectId
    MAX-ACCESS   not-accessible
    STATUS       current
    DESCRIPTION
        "Instance identifier of the managed object."
    ::= { cfprApFabricSspEthMonSrcAppEpEntry 1 }

cfprApFabricSspEthMonSrcAppEpDn OBJECT-TYPE
    SYNTAX       CfprApManagedObjectDn
    MAX-ACCESS   read-only
    STATUS       current
    DESCRIPTION
        "Cisco Firepower fabric:SspEthMonSrcAppEp:dn managed
        object property"
    ::= { cfprApFabricSspEthMonSrcAppEpEntry 2 }

cfprApFabricSspEthMonSrcAppEpRn OBJECT-TYPE
    SYNTAX       SnmpAdminString
    MAX-ACCESS   read-only
    STATUS       current
    DESCRIPTION
        "Cisco Firepower fabric:SspEthMonSrcAppEp:rn managed
        object property"
    ::= { cfprApFabricSspEthMonSrcAppEpEntry 3 }

cfprApFabricSspEthMonSrcAppEpAppName OBJECT-TYPE
    SYNTAX       SnmpAdminString
    MAX-ACCESS   read-only
    STATUS       current
    DESCRIPTION
        "Cisco Firepower fabric:SspEthMonSrcAppEp:appName
        managed object property"
    ::= { cfprApFabricSspEthMonSrcAppEpEntry 4 }

cfprApFabricSspEthMonSrcAppEpFilter OBJECT-TYPE
    SYNTAX       SnmpAdminString
    MAX-ACCESS   read-only
    STATUS       current
    DESCRIPTION
        "Cisco Firepower fabric:SspEthMonSrcAppEp:filter
        managed object property"
    ::= { cfprApFabricSspEthMonSrcAppEpEntry 5 }

cfprApFabricSspEthMonSrcAppEpLinkName OBJECT-TYPE
    SYNTAX       SnmpAdminString
    MAX-ACCESS   read-only
    STATUS       current
    DESCRIPTION
        "Cisco Firepower fabric:SspEthMonSrcAppEp:linkName
        managed object property"
    ::= { cfprApFabricSspEthMonSrcAppEpEntry 6 }

cfprApFabricSspEthMonSrcAppEpPcapfile OBJECT-TYPE
    SYNTAX       SnmpAdminString
    MAX-ACCESS   read-only
    STATUS       current
    DESCRIPTION
        "Cisco Firepower fabric:SspEthMonSrcAppEp:pcapfile
        managed object property"
    ::= { cfprApFabricSspEthMonSrcAppEpEntry 7 }

cfprApFabricSspEthMonSrcAppEpPcapfilename OBJECT-TYPE
    SYNTAX       SnmpAdminString
    MAX-ACCESS   read-only
    STATUS       current
    DESCRIPTION
        "Cisco Firepower fabric:SspEthMonSrcAppEp:pcapfilename
        managed object property"
    ::= { cfprApFabricSspEthMonSrcAppEpEntry 8 }

cfprApFabricSspEthMonSrcAppEpPcapsize OBJECT-TYPE
    SYNTAX       Gauge32
    MAX-ACCESS   read-only
    STATUS       current
    DESCRIPTION
        "Cisco Firepower fabric:SspEthMonSrcAppEp:pcapsize
        managed object property"
    ::= { cfprApFabricSspEthMonSrcAppEpEntry 9 }

cfprApFabricSspEthMonSrcAppEpPortName OBJECT-TYPE
    SYNTAX       SnmpAdminString
    MAX-ACCESS   read-only
    STATUS       current
    DESCRIPTION
        "Cisco Firepower fabric:SspEthMonSrcAppEp:portName
        managed object property"
    ::= { cfprApFabricSspEthMonSrcAppEpEntry 10 }

cfprApFabricSspEthMonSrcAppEpSlotId OBJECT-TYPE
    SYNTAX       CfprApFabricPktCaptureAppSlotId
    MAX-ACCESS   read-only
    STATUS       current
    DESCRIPTION
        "Cisco Firepower fabric:SspEthMonSrcAppEp:slotId
        managed object property"
    ::= { cfprApFabricSspEthMonSrcAppEpEntry 11 }

cfprApFabricSspEthMonSrcAppLinksEpTable OBJECT-TYPE
    SYNTAX           SEQUENCE OF CfprApFabricSspEthMonSrcAppLinksEpEntry
    MAX-ACCESS       not-accessible
    STATUS           current
    DESCRIPTION
        "Cisco Firepower fabric:SspEthMonSrcAppLinksEp
        managed object table"
    ::= { cfprApFabricObjects 106 }

cfprApFabricSspEthMonSrcAppLinksEpEntry OBJECT-TYPE
    SYNTAX           CfprApFabricSspEthMonSrcAppLinksEpEntry
    MAX-ACCESS       not-accessible
    STATUS           current
    DESCRIPTION
        "Entry for the cfprApFabricSspEthMonSrcAppLinksEpTable table."
    INDEX { cfprApFabricSspEthMonSrcAppLinksEpInstanceId }
    ::= { cfprApFabricSspEthMonSrcAppLinksEpTable 1 }

CfprApFabricSspEthMonSrcAppLinksEpEntry ::= SEQUENCE {
    cfprApFabricSspEthMonSrcAppLinksEpInstanceId                     CfprApManagedObjectId,
    cfprApFabricSspEthMonSrcAppLinksEpDn                             CfprApManagedObjectDn,
    cfprApFabricSspEthMonSrcAppLinksEpRn                             SnmpAdminString,
    cfprApFabricSspEthMonSrcAppLinksEpChassisId                      Gauge32,
    cfprApFabricSspEthMonSrcAppLinksEpEqAggrPortId                   Gauge32,
    cfprApFabricSspEthMonSrcAppLinksEpEqPortId                       Gauge32,
    cfprApFabricSspEthMonSrcAppLinksEpEqSlotId                       Gauge32,
    cfprApFabricSspEthMonSrcAppLinksEpFilter                         SnmpAdminString,
    cfprApFabricSspEthMonSrcAppLinksEpFilterDn                       SnmpAdminString,
    cfprApFabricSspEthMonSrcAppLinksEpLifeCycle                      CfprApSwPktCaptureLifeCycle,
    cfprApFabricSspEthMonSrcAppLinksEpName                           SnmpAdminString,
    cfprApFabricSspEthMonSrcAppLinksEpPcapfile                       SnmpAdminString,
    cfprApFabricSspEthMonSrcAppLinksEpPcapfilename                   SnmpAdminString,
    cfprApFabricSspEthMonSrcAppLinksEpPcapsize                       Gauge32,
    cfprApFabricSspEthMonSrcAppLinksEpSwitchId                       CfprApNetworkSwitchId,
    cfprApFabricSspEthMonSrcAppLinksEpVlan                           Gauge32
}

cfprApFabricSspEthMonSrcAppLinksEpInstanceId OBJECT-TYPE
    SYNTAX       CfprApManagedObjectId
    MAX-ACCESS   not-accessible
    STATUS       current
    DESCRIPTION
        "Instance identifier of the managed object."
    ::= { cfprApFabricSspEthMonSrcAppLinksEpEntry 1 }

cfprApFabricSspEthMonSrcAppLinksEpDn OBJECT-TYPE
    SYNTAX       CfprApManagedObjectDn
    MAX-ACCESS   read-only
    STATUS       current
    DESCRIPTION
        "Cisco Firepower fabric:SspEthMonSrcAppLinksEp:dn
        managed object property"
    ::= { cfprApFabricSspEthMonSrcAppLinksEpEntry 2 }

cfprApFabricSspEthMonSrcAppLinksEpRn OBJECT-TYPE
    SYNTAX       SnmpAdminString
    MAX-ACCESS   read-only
    STATUS       current
    DESCRIPTION
        "Cisco Firepower fabric:SspEthMonSrcAppLinksEp:rn
        managed object property"
    ::= { cfprApFabricSspEthMonSrcAppLinksEpEntry 3 }

cfprApFabricSspEthMonSrcAppLinksEpChassisId OBJECT-TYPE
    SYNTAX       Gauge32
    MAX-ACCESS   read-only
    STATUS       current
    DESCRIPTION
        "Cisco Firepower fabric:SspEthMonSrcAppLinksEp:chassisId
        managed object property"
    ::= { cfprApFabricSspEthMonSrcAppLinksEpEntry 4 }

cfprApFabricSspEthMonSrcAppLinksEpEqAggrPortId OBJECT-TYPE
    SYNTAX       Gauge32
    MAX-ACCESS   read-only
    STATUS       current
    DESCRIPTION
        "Cisco Firepower fabric:SspEthMonSrcAppLinksEp:eqAggrPortId
        managed object property"
    ::= { cfprApFabricSspEthMonSrcAppLinksEpEntry 5 }

cfprApFabricSspEthMonSrcAppLinksEpEqPortId OBJECT-TYPE
    SYNTAX       Gauge32
    MAX-ACCESS   read-only
    STATUS       current
    DESCRIPTION
        "Cisco Firepower fabric:SspEthMonSrcAppLinksEp:eqPortId
        managed object property"
    ::= { cfprApFabricSspEthMonSrcAppLinksEpEntry 6 }

cfprApFabricSspEthMonSrcAppLinksEpEqSlotId OBJECT-TYPE
    SYNTAX       Gauge32
    MAX-ACCESS   read-only
    STATUS       current
    DESCRIPTION
        "Cisco Firepower fabric:SspEthMonSrcAppLinksEp:eqSlotId
        managed object property"
    ::= { cfprApFabricSspEthMonSrcAppLinksEpEntry 7 }

cfprApFabricSspEthMonSrcAppLinksEpFilter OBJECT-TYPE
    SYNTAX       SnmpAdminString
    MAX-ACCESS   read-only
    STATUS       current
    DESCRIPTION
        "Cisco Firepower fabric:SspEthMonSrcAppLinksEp:filter
        managed object property"
    ::= { cfprApFabricSspEthMonSrcAppLinksEpEntry 8 }

cfprApFabricSspEthMonSrcAppLinksEpFilterDn OBJECT-TYPE
    SYNTAX       SnmpAdminString
    MAX-ACCESS   read-only
    STATUS       current
    DESCRIPTION
        "Cisco Firepower fabric:SspEthMonSrcAppLinksEp:filterDn
        managed object property"
    ::= { cfprApFabricSspEthMonSrcAppLinksEpEntry 9 }

cfprApFabricSspEthMonSrcAppLinksEpLifeCycle OBJECT-TYPE
    SYNTAX       CfprApSwPktCaptureLifeCycle
    MAX-ACCESS   read-only
    STATUS       current
    DESCRIPTION
        "Cisco Firepower fabric:SspEthMonSrcAppLinksEp:lifeCycle
        managed object property"
    ::= { cfprApFabricSspEthMonSrcAppLinksEpEntry 10 }

cfprApFabricSspEthMonSrcAppLinksEpName OBJECT-TYPE
    SYNTAX       SnmpAdminString
    MAX-ACCESS   read-only
    STATUS       current
    DESCRIPTION
        "Cisco Firepower fabric:SspEthMonSrcAppLinksEp:name
        managed object property"
    ::= { cfprApFabricSspEthMonSrcAppLinksEpEntry 11 }

cfprApFabricSspEthMonSrcAppLinksEpPcapfile OBJECT-TYPE
    SYNTAX       SnmpAdminString
    MAX-ACCESS   read-only
    STATUS       current
    DESCRIPTION
        "Cisco Firepower fabric:SspEthMonSrcAppLinksEp:pcapfile
        managed object property"
    ::= { cfprApFabricSspEthMonSrcAppLinksEpEntry 12 }

cfprApFabricSspEthMonSrcAppLinksEpPcapfilename OBJECT-TYPE
    SYNTAX       SnmpAdminString
    MAX-ACCESS   read-only
    STATUS       current
    DESCRIPTION
        "Cisco Firepower fabric:SspEthMonSrcAppLinksEp:pcapfilename
        managed object property"
    ::= { cfprApFabricSspEthMonSrcAppLinksEpEntry 13 }

cfprApFabricSspEthMonSrcAppLinksEpPcapsize OBJECT-TYPE
    SYNTAX       Gauge32
    MAX-ACCESS   read-only
    STATUS       current
    DESCRIPTION
        "Cisco Firepower fabric:SspEthMonSrcAppLinksEp:pcapsize
        managed object property"
    ::= { cfprApFabricSspEthMonSrcAppLinksEpEntry 14 }

cfprApFabricSspEthMonSrcAppLinksEpSwitchId OBJECT-TYPE
    SYNTAX       CfprApNetworkSwitchId
    MAX-ACCESS   read-only
    STATUS       current
    DESCRIPTION
        "Cisco Firepower fabric:SspEthMonSrcAppLinksEp:switchId
        managed object property"
    ::= { cfprApFabricSspEthMonSrcAppLinksEpEntry 15 }

cfprApFabricSspEthMonSrcAppLinksEpVlan OBJECT-TYPE
    SYNTAX       Gauge32
    MAX-ACCESS   read-only
    STATUS       current
    DESCRIPTION
        "Cisco Firepower fabric:SspEthMonSrcAppLinksEp:vlan
        managed object property"
    ::= { cfprApFabricSspEthMonSrcAppLinksEpEntry 16 }

cfprApFabricSspEthMonSrcPhyAggrEpTable OBJECT-TYPE
    SYNTAX           SEQUENCE OF CfprApFabricSspEthMonSrcPhyAggrEpEntry
    MAX-ACCESS       not-accessible
    STATUS           current
    DESCRIPTION
        "Cisco Firepower fabric:SspEthMonSrcPhyAggrEp managed
        object table"
    ::= { cfprApFabricObjects 107 }

cfprApFabricSspEthMonSrcPhyAggrEpEntry OBJECT-TYPE
    SYNTAX           CfprApFabricSspEthMonSrcPhyAggrEpEntry
    MAX-ACCESS       not-accessible
    STATUS           current
    DESCRIPTION
        "Entry for the cfprApFabricSspEthMonSrcPhyAggrEpTable table."
    INDEX { cfprApFabricSspEthMonSrcPhyAggrEpInstanceId }
    ::= { cfprApFabricSspEthMonSrcPhyAggrEpTable 1 }

CfprApFabricSspEthMonSrcPhyAggrEpEntry ::= SEQUENCE {
    cfprApFabricSspEthMonSrcPhyAggrEpInstanceId                      CfprApManagedObjectId,
    cfprApFabricSspEthMonSrcPhyAggrEpDn                              CfprApManagedObjectDn,
    cfprApFabricSspEthMonSrcPhyAggrEpRn                              SnmpAdminString,
    cfprApFabricSspEthMonSrcPhyAggrEpAggrPortId                      Gauge32,
    cfprApFabricSspEthMonSrcPhyAggrEpBreakoutPortId                  Gauge32,
    cfprApFabricSspEthMonSrcPhyAggrEpChassisId                       Gauge32,
    cfprApFabricSspEthMonSrcPhyAggrEpFilter                          SnmpAdminString,
    cfprApFabricSspEthMonSrcPhyAggrEpPcapfile                        SnmpAdminString,
    cfprApFabricSspEthMonSrcPhyAggrEpPcapfilename                    SnmpAdminString,
    cfprApFabricSspEthMonSrcPhyAggrEpPcapsize                        Gauge32,
    cfprApFabricSspEthMonSrcPhyAggrEpSlotId                          Gauge32,
    cfprApFabricSspEthMonSrcPhyAggrEpSwitchId                        CfprApNetworkSwitchId
}

cfprApFabricSspEthMonSrcPhyAggrEpInstanceId OBJECT-TYPE
    SYNTAX       CfprApManagedObjectId
    MAX-ACCESS   not-accessible
    STATUS       current
    DESCRIPTION
        "Instance identifier of the managed object."
    ::= { cfprApFabricSspEthMonSrcPhyAggrEpEntry 1 }

cfprApFabricSspEthMonSrcPhyAggrEpDn OBJECT-TYPE
    SYNTAX       CfprApManagedObjectDn
    MAX-ACCESS   read-only
    STATUS       current
    DESCRIPTION
        "Cisco Firepower fabric:SspEthMonSrcPhyAggrEp:dn
        managed object property"
    ::= { cfprApFabricSspEthMonSrcPhyAggrEpEntry 2 }

cfprApFabricSspEthMonSrcPhyAggrEpRn OBJECT-TYPE
    SYNTAX       SnmpAdminString
    MAX-ACCESS   read-only
    STATUS       current
    DESCRIPTION
        "Cisco Firepower fabric:SspEthMonSrcPhyAggrEp:rn
        managed object property"
    ::= { cfprApFabricSspEthMonSrcPhyAggrEpEntry 3 }

cfprApFabricSspEthMonSrcPhyAggrEpAggrPortId OBJECT-TYPE
    SYNTAX       Gauge32
    MAX-ACCESS   read-only
    STATUS       current
    DESCRIPTION
        "Cisco Firepower fabric:SspEthMonSrcPhyAggrEp:aggrPortId
        managed object property"
    ::= { cfprApFabricSspEthMonSrcPhyAggrEpEntry 4 }

cfprApFabricSspEthMonSrcPhyAggrEpBreakoutPortId OBJECT-TYPE
    SYNTAX       Gauge32
    MAX-ACCESS   read-only
    STATUS       current
    DESCRIPTION
        "Cisco Firepower fabric:SspEthMonSrcPhyAggrEp:breakoutPortId
        managed object property"
    ::= { cfprApFabricSspEthMonSrcPhyAggrEpEntry 5 }

cfprApFabricSspEthMonSrcPhyAggrEpChassisId OBJECT-TYPE
    SYNTAX       Gauge32
    MAX-ACCESS   read-only
    STATUS       current
    DESCRIPTION
        "Cisco Firepower fabric:SspEthMonSrcPhyAggrEp:chassisId
        managed object property"
    ::= { cfprApFabricSspEthMonSrcPhyAggrEpEntry 6 }

cfprApFabricSspEthMonSrcPhyAggrEpFilter OBJECT-TYPE
    SYNTAX       SnmpAdminString
    MAX-ACCESS   read-only
    STATUS       current
    DESCRIPTION
        "Cisco Firepower fabric:SspEthMonSrcPhyAggrEp:filter
        managed object property"
    ::= { cfprApFabricSspEthMonSrcPhyAggrEpEntry 7 }

cfprApFabricSspEthMonSrcPhyAggrEpPcapfile OBJECT-TYPE
    SYNTAX       SnmpAdminString
    MAX-ACCESS   read-only
    STATUS       current
    DESCRIPTION
        "Cisco Firepower fabric:SspEthMonSrcPhyAggrEp:pcapfile
        managed object property"
    ::= { cfprApFabricSspEthMonSrcPhyAggrEpEntry 8 }

cfprApFabricSspEthMonSrcPhyAggrEpPcapfilename OBJECT-TYPE
    SYNTAX       SnmpAdminString
    MAX-ACCESS   read-only
    STATUS       current
    DESCRIPTION
        "Cisco Firepower fabric:SspEthMonSrcPhyAggrEp:pcapfilename
        managed object property"
    ::= { cfprApFabricSspEthMonSrcPhyAggrEpEntry 9 }

cfprApFabricSspEthMonSrcPhyAggrEpPcapsize OBJECT-TYPE
    SYNTAX       Gauge32
    MAX-ACCESS   read-only
    STATUS       current
    DESCRIPTION
        "Cisco Firepower fabric:SspEthMonSrcPhyAggrEp:pcapsize
        managed object property"
    ::= { cfprApFabricSspEthMonSrcPhyAggrEpEntry 10 }

cfprApFabricSspEthMonSrcPhyAggrEpSlotId OBJECT-TYPE
    SYNTAX       Gauge32
    MAX-ACCESS   read-only
    STATUS       current
    DESCRIPTION
        "Cisco Firepower fabric:SspEthMonSrcPhyAggrEp:slotId
        managed object property"
    ::= { cfprApFabricSspEthMonSrcPhyAggrEpEntry 11 }

cfprApFabricSspEthMonSrcPhyAggrEpSwitchId OBJECT-TYPE
    SYNTAX       CfprApNetworkSwitchId
    MAX-ACCESS   read-only
    STATUS       current
    DESCRIPTION
        "Cisco Firepower fabric:SspEthMonSrcPhyAggrEp:switchId
        managed object property"
    ::= { cfprApFabricSspEthMonSrcPhyAggrEpEntry 12 }

cfprApFabricSspEthMonSrcPhyEpTable OBJECT-TYPE
    SYNTAX           SEQUENCE OF CfprApFabricSspEthMonSrcPhyEpEntry
    MAX-ACCESS       not-accessible
    STATUS           current
    DESCRIPTION
        "Cisco Firepower fabric:SspEthMonSrcPhyEp managed object table"
    ::= { cfprApFabricObjects 108 }

cfprApFabricSspEthMonSrcPhyEpEntry OBJECT-TYPE
    SYNTAX           CfprApFabricSspEthMonSrcPhyEpEntry
    MAX-ACCESS       not-accessible
    STATUS           current
    DESCRIPTION
        "Entry for the cfprApFabricSspEthMonSrcPhyEpTable table."
    INDEX { cfprApFabricSspEthMonSrcPhyEpInstanceId }
    ::= { cfprApFabricSspEthMonSrcPhyEpTable 1 }

CfprApFabricSspEthMonSrcPhyEpEntry ::= SEQUENCE {
    cfprApFabricSspEthMonSrcPhyEpInstanceId                          CfprApManagedObjectId,
    cfprApFabricSspEthMonSrcPhyEpDn                                  CfprApManagedObjectDn,
    cfprApFabricSspEthMonSrcPhyEpRn                                  SnmpAdminString,
    cfprApFabricSspEthMonSrcPhyEpChassisId                           Gauge32,
    cfprApFabricSspEthMonSrcPhyEpFilter                              SnmpAdminString,
    cfprApFabricSspEthMonSrcPhyEpPcapfile                            SnmpAdminString,
    cfprApFabricSspEthMonSrcPhyEpPcapfilename                        SnmpAdminString,
    cfprApFabricSspEthMonSrcPhyEpPcapsize                            Gauge32,
    cfprApFabricSspEthMonSrcPhyEpPortId                              Gauge32,
    cfprApFabricSspEthMonSrcPhyEpSlotId                              Gauge32,
    cfprApFabricSspEthMonSrcPhyEpSwitchId                            CfprApNetworkSwitchId
}

cfprApFabricSspEthMonSrcPhyEpInstanceId OBJECT-TYPE
    SYNTAX       CfprApManagedObjectId
    MAX-ACCESS   not-accessible
    STATUS       current
    DESCRIPTION
        "Instance identifier of the managed object."
    ::= { cfprApFabricSspEthMonSrcPhyEpEntry 1 }

cfprApFabricSspEthMonSrcPhyEpDn OBJECT-TYPE
    SYNTAX       CfprApManagedObjectDn
    MAX-ACCESS   read-only
    STATUS       current
    DESCRIPTION
        "Cisco Firepower fabric:SspEthMonSrcPhyEp:dn managed
        object property"
    ::= { cfprApFabricSspEthMonSrcPhyEpEntry 2 }

cfprApFabricSspEthMonSrcPhyEpRn OBJECT-TYPE
    SYNTAX       SnmpAdminString
    MAX-ACCESS   read-only
    STATUS       current
    DESCRIPTION
        "Cisco Firepower fabric:SspEthMonSrcPhyEp:rn managed
        object property"
    ::= { cfprApFabricSspEthMonSrcPhyEpEntry 3 }

cfprApFabricSspEthMonSrcPhyEpChassisId OBJECT-TYPE
    SYNTAX       Gauge32
    MAX-ACCESS   read-only
    STATUS       current
    DESCRIPTION
        "Cisco Firepower fabric:SspEthMonSrcPhyEp:chassisId
        managed object property"
    ::= { cfprApFabricSspEthMonSrcPhyEpEntry 4 }

cfprApFabricSspEthMonSrcPhyEpFilter OBJECT-TYPE
    SYNTAX       SnmpAdminString
    MAX-ACCESS   read-only
    STATUS       current
    DESCRIPTION
        "Cisco Firepower fabric:SspEthMonSrcPhyEp:filter
        managed object property"
    ::= { cfprApFabricSspEthMonSrcPhyEpEntry 5 }

cfprApFabricSspEthMonSrcPhyEpPcapfile OBJECT-TYPE
    SYNTAX       SnmpAdminString
    MAX-ACCESS   read-only
    STATUS       current
    DESCRIPTION
        "Cisco Firepower fabric:SspEthMonSrcPhyEp:pcapfile
        managed object property"
    ::= { cfprApFabricSspEthMonSrcPhyEpEntry 6 }

cfprApFabricSspEthMonSrcPhyEpPcapfilename OBJECT-TYPE
    SYNTAX       SnmpAdminString
    MAX-ACCESS   read-only
    STATUS       current
    DESCRIPTION
        "Cisco Firepower fabric:SspEthMonSrcPhyEp:pcapfilename
        managed object property"
    ::= { cfprApFabricSspEthMonSrcPhyEpEntry 7 }

cfprApFabricSspEthMonSrcPhyEpPcapsize OBJECT-TYPE
    SYNTAX       Gauge32
    MAX-ACCESS   read-only
    STATUS       current
    DESCRIPTION
        "Cisco Firepower fabric:SspEthMonSrcPhyEp:pcapsize
        managed object property"
    ::= { cfprApFabricSspEthMonSrcPhyEpEntry 8 }

cfprApFabricSspEthMonSrcPhyEpPortId OBJECT-TYPE
    SYNTAX       Gauge32
    MAX-ACCESS   read-only
    STATUS       current
    DESCRIPTION
        "Cisco Firepower fabric:SspEthMonSrcPhyEp:portId
        managed object property"
    ::= { cfprApFabricSspEthMonSrcPhyEpEntry 9 }

cfprApFabricSspEthMonSrcPhyEpSlotId OBJECT-TYPE
    SYNTAX       Gauge32
    MAX-ACCESS   read-only
    STATUS       current
    DESCRIPTION
        "Cisco Firepower fabric:SspEthMonSrcPhyEp:slotId
        managed object property"
    ::= { cfprApFabricSspEthMonSrcPhyEpEntry 10 }

cfprApFabricSspEthMonSrcPhyEpSwitchId OBJECT-TYPE
    SYNTAX       CfprApNetworkSwitchId
    MAX-ACCESS   read-only
    STATUS       current
    DESCRIPTION
        "Cisco Firepower fabric:SspEthMonSrcPhyEp:switchId
        managed object property"
    ::= { cfprApFabricSspEthMonSrcPhyEpEntry 11 }

cfprApFabricSspLanMonCloudTable OBJECT-TYPE
    SYNTAX           SEQUENCE OF CfprApFabricSspLanMonCloudEntry
    MAX-ACCESS       not-accessible
    STATUS           current
    DESCRIPTION
        "Cisco Firepower fabric:SspLanMonCloud managed object table"
    ::= { cfprApFabricObjects 109 }

cfprApFabricSspLanMonCloudEntry OBJECT-TYPE
    SYNTAX           CfprApFabricSspLanMonCloudEntry
    MAX-ACCESS       not-accessible
    STATUS           current
    DESCRIPTION
        "Entry for the cfprApFabricSspLanMonCloudTable table."
    INDEX { cfprApFabricSspLanMonCloudInstanceId }
    ::= { cfprApFabricSspLanMonCloudTable 1 }

CfprApFabricSspLanMonCloudEntry ::= SEQUENCE {
    cfprApFabricSspLanMonCloudInstanceId                             CfprApManagedObjectId,
    cfprApFabricSspLanMonCloudDn                                     CfprApManagedObjectDn,
    cfprApFabricSspLanMonCloudRn                                     SnmpAdminString,
    cfprApFabricSspLanMonCloudMode                                   CfprApFabricSwitchingMode
}

cfprApFabricSspLanMonCloudInstanceId OBJECT-TYPE
    SYNTAX       CfprApManagedObjectId
    MAX-ACCESS   not-accessible
    STATUS       current
    DESCRIPTION
        "Instance identifier of the managed object."
    ::= { cfprApFabricSspLanMonCloudEntry 1 }

cfprApFabricSspLanMonCloudDn OBJECT-TYPE
    SYNTAX       CfprApManagedObjectDn
    MAX-ACCESS   read-only
    STATUS       current
    DESCRIPTION
        "Cisco Firepower fabric:SspLanMonCloud:dn managed object property"
    ::= { cfprApFabricSspLanMonCloudEntry 2 }

cfprApFabricSspLanMonCloudRn OBJECT-TYPE
    SYNTAX       SnmpAdminString
    MAX-ACCESS   read-only
    STATUS       current
    DESCRIPTION
        "Cisco Firepower fabric:SspLanMonCloud:rn managed object property"
    ::= { cfprApFabricSspLanMonCloudEntry 3 }

cfprApFabricSspLanMonCloudMode OBJECT-TYPE
    SYNTAX       CfprApFabricSwitchingMode
    MAX-ACCESS   read-only
    STATUS       current
    DESCRIPTION
        "Cisco Firepower fabric:SspLanMonCloud:mode managed
        object property"
    ::= { cfprApFabricSspLanMonCloudEntry 4 }

cfprApFabricSubGroupTable OBJECT-TYPE
    SYNTAX           SEQUENCE OF CfprApFabricSubGroupEntry
    MAX-ACCESS       not-accessible
    STATUS           current
    DESCRIPTION
        "Cisco Firepower fabric:SubGroup managed object table"
    ::= { cfprApFabricObjects 110 }

cfprApFabricSubGroupEntry OBJECT-TYPE
    SYNTAX           CfprApFabricSubGroupEntry
    MAX-ACCESS       not-accessible
    STATUS           current
    DESCRIPTION
        "Entry for the cfprApFabricSubGroupTable table."
    INDEX { cfprApFabricSubGroupInstanceId }
    ::= { cfprApFabricSubGroupTable 1 }

CfprApFabricSubGroupEntry ::= SEQUENCE {
    cfprApFabricSubGroupInstanceId                                   CfprApManagedObjectId,
    cfprApFabricSubGroupDn                                           CfprApManagedObjectDn,
    cfprApFabricSubGroupRn                                           SnmpAdminString,
    cfprApFabricSubGroupAggrPortId                                   CfprApFabricSubGroupAggrPortId,
    cfprApFabricSubGroupConfigState                                  CfprApFabricSubGroupConfigState,
    cfprApFabricSubGroupLicGP                                        Unsigned64,
    cfprApFabricSubGroupLicState                                     CfprApLicenseState,
    cfprApFabricSubGroupLocale                                       CfprApNetworkLocale,
    cfprApFabricSubGroupName                                         SnmpAdminString,
    cfprApFabricSubGroupSlotId                                       CfprApFabricSubGroupSlotId,
    cfprApFabricSubGroupSwitchId                                     CfprApNetworkSwitchId,
    cfprApFabricSubGroupTransport                                    CfprApNetworkTransport,
    cfprApFabricSubGroupType                                         CfprApNetworkConnectionType
}

cfprApFabricSubGroupInstanceId OBJECT-TYPE
    SYNTAX       CfprApManagedObjectId
    MAX-ACCESS   not-accessible
    STATUS       current
    DESCRIPTION
        "Instance identifier of the managed object."
    ::= { cfprApFabricSubGroupEntry 1 }

cfprApFabricSubGroupDn OBJECT-TYPE
    SYNTAX       CfprApManagedObjectDn
    MAX-ACCESS   read-only
    STATUS       current
    DESCRIPTION
        "Cisco Firepower fabric:SubGroup:dn managed object property"
    ::= { cfprApFabricSubGroupEntry 2 }

cfprApFabricSubGroupRn OBJECT-TYPE
    SYNTAX       SnmpAdminString
    MAX-ACCESS   read-only
    STATUS       current
    DESCRIPTION
        "Cisco Firepower fabric:SubGroup:rn managed object property"
    ::= { cfprApFabricSubGroupEntry 3 }

cfprApFabricSubGroupAggrPortId OBJECT-TYPE
    SYNTAX       CfprApFabricSubGroupAggrPortId
    MAX-ACCESS   read-only
    STATUS       current
    DESCRIPTION
        "Cisco Firepower fabric:SubGroup:aggrPortId managed
        object property"
    ::= { cfprApFabricSubGroupEntry 4 }

cfprApFabricSubGroupConfigState OBJECT-TYPE
    SYNTAX       CfprApFabricSubGroupConfigState
    MAX-ACCESS   read-only
    STATUS       current
    DESCRIPTION
        "Cisco Firepower fabric:SubGroup:configState managed
        object property"
    ::= { cfprApFabricSubGroupEntry 5 }

cfprApFabricSubGroupLicGP OBJECT-TYPE
    SYNTAX       Unsigned64
    MAX-ACCESS   read-only
    STATUS       current
    DESCRIPTION
        "Cisco Firepower fabric:SubGroup:licGP managed object property"
    ::= { cfprApFabricSubGroupEntry 6 }

cfprApFabricSubGroupLicState OBJECT-TYPE
    SYNTAX       CfprApLicenseState
    MAX-ACCESS   read-only
    STATUS       current
    DESCRIPTION
        "Cisco Firepower fabric:SubGroup:licState managed object property"
    ::= { cfprApFabricSubGroupEntry 7 }

cfprApFabricSubGroupLocale OBJECT-TYPE
    SYNTAX       CfprApNetworkLocale
    MAX-ACCESS   read-only
    STATUS       current
    DESCRIPTION
        "Cisco Firepower fabric:SubGroup:locale managed object property"
    ::= { cfprApFabricSubGroupEntry 8 }

cfprApFabricSubGroupName OBJECT-TYPE
    SYNTAX       SnmpAdminString
    MAX-ACCESS   read-only
    STATUS       current
    DESCRIPTION
        "Cisco Firepower fabric:SubGroup:name managed object property"
    ::= { cfprApFabricSubGroupEntry 9 }

cfprApFabricSubGroupSlotId OBJECT-TYPE
    SYNTAX       CfprApFabricSubGroupSlotId
    MAX-ACCESS   read-only
    STATUS       current
    DESCRIPTION
        "Cisco Firepower fabric:SubGroup:slotId managed object property"
    ::= { cfprApFabricSubGroupEntry 10 }

cfprApFabricSubGroupSwitchId OBJECT-TYPE
    SYNTAX       CfprApNetworkSwitchId
    MAX-ACCESS   read-only
    STATUS       current
    DESCRIPTION
        "Cisco Firepower fabric:SubGroup:switchId managed object property"
    ::= { cfprApFabricSubGroupEntry 11 }

cfprApFabricSubGroupTransport OBJECT-TYPE
    SYNTAX       CfprApNetworkTransport
    MAX-ACCESS   read-only
    STATUS       current
    DESCRIPTION
        "Cisco Firepower fabric:SubGroup:transport managed
        object property"
    ::= { cfprApFabricSubGroupEntry 12 }

cfprApFabricSubGroupType OBJECT-TYPE
    SYNTAX       CfprApNetworkConnectionType
    MAX-ACCESS   read-only
    STATUS       current
    DESCRIPTION
        "Cisco Firepower fabric:SubGroup:type managed object property"
    ::= { cfprApFabricSubGroupEntry 13 }

cfprApFabricSwChPhEpTable OBJECT-TYPE
    SYNTAX           SEQUENCE OF CfprApFabricSwChPhEpEntry
    MAX-ACCESS       not-accessible
    STATUS           current
    DESCRIPTION
        "Cisco Firepower fabric:SwChPhEp managed object table"
    ::= { cfprApFabricObjects 111 }

cfprApFabricSwChPhEpEntry OBJECT-TYPE
    SYNTAX           CfprApFabricSwChPhEpEntry
    MAX-ACCESS       not-accessible
    STATUS           current
    DESCRIPTION
        "Entry for the cfprApFabricSwChPhEpTable table."
    INDEX { cfprApFabricSwChPhEpInstanceId }
    ::= { cfprApFabricSwChPhEpTable 1 }

CfprApFabricSwChPhEpEntry ::= SEQUENCE {
    cfprApFabricSwChPhEpInstanceId                                   CfprApManagedObjectId,
    cfprApFabricSwChPhEpDn                                           CfprApManagedObjectDn,
    cfprApFabricSwChPhEpRn                                           SnmpAdminString,
    cfprApFabricSwChPhEpAdminState                                   CfprApFabricSwChPhEpAdminState,
    cfprApFabricSwChPhEpAggrPortId                                   Gauge32,
    cfprApFabricSwChPhEpChassisId                                    Gauge32,
    cfprApFabricSwChPhEpEpDn                                         SnmpAdminString,
    cfprApFabricSwChPhEpEqType                                       CfprApEquipmentFabricEpType,
    cfprApFabricSwChPhEpFltAggr                                      Unsigned64,
    cfprApFabricSwChPhEpIfRole                                       CfprApFabricSwChEpIfRole,
    cfprApFabricSwChPhEpIfType                                       CfprApFabricPIoEpIfType,
    cfprApFabricSwChPhEpLc                                           CfprApFabricLifeCycle,
    cfprApFabricSwChPhEpLicGP                                        Unsigned64,
    cfprApFabricSwChPhEpLicState                                     CfprApLicenseState,
    cfprApFabricSwChPhEpLocale                                       CfprApFabricInternalEpLocale,
    cfprApFabricSwChPhEpModel                                        SnmpAdminString,
    cfprApFabricSwChPhEpName                                         SnmpAdminString,
    cfprApFabricSwChPhEpOperState                                    CfprApFabricPIoEpOperState,
    cfprApFabricSwChPhEpOperStateReason                              SnmpAdminString,
    cfprApFabricSwChPhEpPeerAggrPortId                               Gauge32,
    cfprApFabricSwChPhEpPeerChassisId                                Gauge32,
    cfprApFabricSwChPhEpPeerDn                                       SnmpAdminString,
    cfprApFabricSwChPhEpPeerPortId                                   Gauge32,
    cfprApFabricSwChPhEpPeerSlotId                                   Gauge32,
    cfprApFabricSwChPhEpPortId                                       CfprApFabricPIoEpPortId,
    cfprApFabricSwChPhEpRevision                                     SnmpAdminString,
    cfprApFabricSwChPhEpSerial                                       SnmpAdminString,
    cfprApFabricSwChPhEpSlotId                                       CfprApFabricPIoEpSlotId,
    cfprApFabricSwChPhEpSwitchId                                     CfprApNetworkSwitchId,
    cfprApFabricSwChPhEpTransport                                    CfprApNetworkTransport,
    cfprApFabricSwChPhEpType                                         CfprApFabricSwChEpType,
    cfprApFabricSwChPhEpVendor                                       SnmpAdminString
}

cfprApFabricSwChPhEpInstanceId OBJECT-TYPE
    SYNTAX       CfprApManagedObjectId
    MAX-ACCESS   not-accessible
    STATUS       current
    DESCRIPTION
        "Instance identifier of the managed object."
    ::= { cfprApFabricSwChPhEpEntry 1 }

cfprApFabricSwChPhEpDn OBJECT-TYPE
    SYNTAX       CfprApManagedObjectDn
    MAX-ACCESS   read-only
    STATUS       current
    DESCRIPTION
        "Cisco Firepower fabric:SwChPhEp:dn managed object property"
    ::= { cfprApFabricSwChPhEpEntry 2 }

cfprApFabricSwChPhEpRn OBJECT-TYPE
    SYNTAX       SnmpAdminString
    MAX-ACCESS   read-only
    STATUS       current
    DESCRIPTION
        "Cisco Firepower fabric:SwChPhEp:rn managed object property"
    ::= { cfprApFabricSwChPhEpEntry 3 }

cfprApFabricSwChPhEpAdminState OBJECT-TYPE
    SYNTAX       CfprApFabricSwChPhEpAdminState
    MAX-ACCESS   read-only
    STATUS       current
    DESCRIPTION
        "Cisco Firepower fabric:SwChPhEp:adminState managed
        object property"
    ::= { cfprApFabricSwChPhEpEntry 4 }

cfprApFabricSwChPhEpAggrPortId OBJECT-TYPE
    SYNTAX       Gauge32
    MAX-ACCESS   read-only
    STATUS       current
    DESCRIPTION
        "Cisco Firepower fabric:SwChPhEp:aggrPortId managed
        object property"
    ::= { cfprApFabricSwChPhEpEntry 5 }

cfprApFabricSwChPhEpChassisId OBJECT-TYPE
    SYNTAX       Gauge32
    MAX-ACCESS   read-only
    STATUS       current
    DESCRIPTION
        "Cisco Firepower fabric:SwChPhEp:chassisId managed
        object property"
    ::= { cfprApFabricSwChPhEpEntry 6 }

cfprApFabricSwChPhEpEpDn OBJECT-TYPE
    SYNTAX       SnmpAdminString
    MAX-ACCESS   read-only
    STATUS       current
    DESCRIPTION
        "Cisco Firepower fabric:SwChPhEp:epDn managed object property"
    ::= { cfprApFabricSwChPhEpEntry 7 }

cfprApFabricSwChPhEpEqType OBJECT-TYPE
    SYNTAX       CfprApEquipmentFabricEpType
    MAX-ACCESS   read-only
    STATUS       current
    DESCRIPTION
        "Cisco Firepower fabric:SwChPhEp:eqType managed object property"
    ::= { cfprApFabricSwChPhEpEntry 8 }

cfprApFabricSwChPhEpFltAggr OBJECT-TYPE
    SYNTAX       Unsigned64
    MAX-ACCESS   read-only
    STATUS       current
    DESCRIPTION
        "Cisco Firepower fabric:SwChPhEp:fltAggr managed object property"
    ::= { cfprApFabricSwChPhEpEntry 9 }

cfprApFabricSwChPhEpIfRole OBJECT-TYPE
    SYNTAX       CfprApFabricSwChEpIfRole
    MAX-ACCESS   read-only
    STATUS       current
    DESCRIPTION
        "Cisco Firepower fabric:SwChPhEp:ifRole managed object property"
    ::= { cfprApFabricSwChPhEpEntry 10 }

cfprApFabricSwChPhEpIfType OBJECT-TYPE
    SYNTAX       CfprApFabricPIoEpIfType
    MAX-ACCESS   read-only
    STATUS       current
    DESCRIPTION
        "Cisco Firepower fabric:SwChPhEp:ifType managed object property"
    ::= { cfprApFabricSwChPhEpEntry 11 }

cfprApFabricSwChPhEpLc OBJECT-TYPE
    SYNTAX       CfprApFabricLifeCycle
    MAX-ACCESS   read-only
    STATUS       current
    DESCRIPTION
        "Cisco Firepower fabric:SwChPhEp:lc managed object property"
    ::= { cfprApFabricSwChPhEpEntry 12 }

cfprApFabricSwChPhEpLicGP OBJECT-TYPE
    SYNTAX       Unsigned64
    MAX-ACCESS   read-only
    STATUS       current
    DESCRIPTION
        "Cisco Firepower fabric:SwChPhEp:licGP managed object property"
    ::= { cfprApFabricSwChPhEpEntry 13 }

cfprApFabricSwChPhEpLicState OBJECT-TYPE
    SYNTAX       CfprApLicenseState
    MAX-ACCESS   read-only
    STATUS       current
    DESCRIPTION
        "Cisco Firepower fabric:SwChPhEp:licState managed object property"
    ::= { cfprApFabricSwChPhEpEntry 14 }

cfprApFabricSwChPhEpLocale OBJECT-TYPE
    SYNTAX       CfprApFabricInternalEpLocale
    MAX-ACCESS   read-only
    STATUS       current
    DESCRIPTION
        "Cisco Firepower fabric:SwChPhEp:locale managed object property"
    ::= { cfprApFabricSwChPhEpEntry 15 }

cfprApFabricSwChPhEpModel OBJECT-TYPE
    SYNTAX       SnmpAdminString
    MAX-ACCESS   read-only
    STATUS       current
    DESCRIPTION
        "Cisco Firepower fabric:SwChPhEp:model managed object property"
    ::= { cfprApFabricSwChPhEpEntry 16 }

cfprApFabricSwChPhEpName OBJECT-TYPE
    SYNTAX       SnmpAdminString
    MAX-ACCESS   read-only
    STATUS       current
    DESCRIPTION
        "Cisco Firepower fabric:SwChPhEp:name managed object property"
    ::= { cfprApFabricSwChPhEpEntry 17 }

cfprApFabricSwChPhEpOperState OBJECT-TYPE
    SYNTAX       CfprApFabricPIoEpOperState
    MAX-ACCESS   read-only
    STATUS       current
    DESCRIPTION
        "Cisco Firepower fabric:SwChPhEp:operState managed
        object property"
    ::= { cfprApFabricSwChPhEpEntry 18 }

cfprApFabricSwChPhEpOperStateReason OBJECT-TYPE
    SYNTAX       SnmpAdminString
    MAX-ACCESS   read-only
    STATUS       current
    DESCRIPTION
        "Cisco Firepower fabric:SwChPhEp:operStateReason
        managed object property"
    ::= { cfprApFabricSwChPhEpEntry 19 }

cfprApFabricSwChPhEpPeerAggrPortId OBJECT-TYPE
    SYNTAX       Gauge32
    MAX-ACCESS   read-only
    STATUS       current
    DESCRIPTION
        "Cisco Firepower fabric:SwChPhEp:peerAggrPortId
        managed object property"
    ::= { cfprApFabricSwChPhEpEntry 20 }

cfprApFabricSwChPhEpPeerChassisId OBJECT-TYPE
    SYNTAX       Gauge32
    MAX-ACCESS   read-only
    STATUS       current
    DESCRIPTION
        "Cisco Firepower fabric:SwChPhEp:peerChassisId
        managed object property"
    ::= { cfprApFabricSwChPhEpEntry 21 }

cfprApFabricSwChPhEpPeerDn OBJECT-TYPE
    SYNTAX       SnmpAdminString
    MAX-ACCESS   read-only
    STATUS       current
    DESCRIPTION
        "Cisco Firepower fabric:SwChPhEp:peerDn managed object property"
    ::= { cfprApFabricSwChPhEpEntry 22 }

cfprApFabricSwChPhEpPeerPortId OBJECT-TYPE
    SYNTAX       Gauge32
    MAX-ACCESS   read-only
    STATUS       current
    DESCRIPTION
        "Cisco Firepower fabric:SwChPhEp:peerPortId managed
        object property"
    ::= { cfprApFabricSwChPhEpEntry 23 }

cfprApFabricSwChPhEpPeerSlotId OBJECT-TYPE
    SYNTAX       Gauge32
    MAX-ACCESS   read-only
    STATUS       current
    DESCRIPTION
        "Cisco Firepower fabric:SwChPhEp:peerSlotId managed
        object property"
    ::= { cfprApFabricSwChPhEpEntry 24 }

cfprApFabricSwChPhEpPortId OBJECT-TYPE
    SYNTAX       CfprApFabricPIoEpPortId
    MAX-ACCESS   read-only
    STATUS       current
    DESCRIPTION
        "Cisco Firepower fabric:SwChPhEp:portId managed object property"
    ::= { cfprApFabricSwChPhEpEntry 25 }

cfprApFabricSwChPhEpRevision OBJECT-TYPE
    SYNTAX       SnmpAdminString
    MAX-ACCESS   read-only
    STATUS       current
    DESCRIPTION
        "Cisco Firepower fabric:SwChPhEp:revision managed object property"
    ::= { cfprApFabricSwChPhEpEntry 26 }

cfprApFabricSwChPhEpSerial OBJECT-TYPE
    SYNTAX       SnmpAdminString
    MAX-ACCESS   read-only
    STATUS       current
    DESCRIPTION
        "Cisco Firepower fabric:SwChPhEp:serial managed object property"
    ::= { cfprApFabricSwChPhEpEntry 27 }

cfprApFabricSwChPhEpSlotId OBJECT-TYPE
    SYNTAX       CfprApFabricPIoEpSlotId
    MAX-ACCESS   read-only
    STATUS       current
    DESCRIPTION
        "Cisco Firepower fabric:SwChPhEp:slotId managed object property"
    ::= { cfprApFabricSwChPhEpEntry 28 }

cfprApFabricSwChPhEpSwitchId OBJECT-TYPE
    SYNTAX       CfprApNetworkSwitchId
    MAX-ACCESS   read-only
    STATUS       current
    DESCRIPTION
        "Cisco Firepower fabric:SwChPhEp:switchId managed object property"
    ::= { cfprApFabricSwChPhEpEntry 29 }

cfprApFabricSwChPhEpTransport OBJECT-TYPE
    SYNTAX       CfprApNetworkTransport
    MAX-ACCESS   read-only
    STATUS       current
    DESCRIPTION
        "Cisco Firepower fabric:SwChPhEp:transport managed
        object property"
    ::= { cfprApFabricSwChPhEpEntry 30 }

cfprApFabricSwChPhEpType OBJECT-TYPE
    SYNTAX       CfprApFabricSwChEpType
    MAX-ACCESS   read-only
    STATUS       current
    DESCRIPTION
        "Cisco Firepower fabric:SwChPhEp:type managed object property"
    ::= { cfprApFabricSwChPhEpEntry 31 }

cfprApFabricSwChPhEpVendor OBJECT-TYPE
    SYNTAX       SnmpAdminString
    MAX-ACCESS   read-only
    STATUS       current
    DESCRIPTION
        "Cisco Firepower fabric:SwChPhEp:vendor managed object property"
    ::= { cfprApFabricSwChPhEpEntry 32 }

cfprApFabricSwSubGroupTable OBJECT-TYPE
    SYNTAX           SEQUENCE OF CfprApFabricSwSubGroupEntry
    MAX-ACCESS       not-accessible
    STATUS           current
    DESCRIPTION
        "Cisco Firepower fabric:SwSubGroup managed object table"
    ::= { cfprApFabricObjects 112 }

cfprApFabricSwSubGroupEntry OBJECT-TYPE
    SYNTAX           CfprApFabricSwSubGroupEntry
    MAX-ACCESS       not-accessible
    STATUS           current
    DESCRIPTION
        "Entry for the cfprApFabricSwSubGroupTable table."
    INDEX { cfprApFabricSwSubGroupInstanceId }
    ::= { cfprApFabricSwSubGroupTable 1 }

CfprApFabricSwSubGroupEntry ::= SEQUENCE {
    cfprApFabricSwSubGroupInstanceId                                 CfprApManagedObjectId,
    cfprApFabricSwSubGroupDn                                         CfprApManagedObjectDn,
    cfprApFabricSwSubGroupRn                                         SnmpAdminString,
    cfprApFabricSwSubGroupAggrPortId                                 CfprApFabricSwSubGroupAggrPortId,
    cfprApFabricSwSubGroupConfigState                                CfprApFabricSwSubGroupConfigState,
    cfprApFabricSwSubGroupLicGP                                      Unsigned64,
    cfprApFabricSwSubGroupLicState                                   CfprApLicenseState,
    cfprApFabricSwSubGroupLocale                                     CfprApNetworkLocale,
    cfprApFabricSwSubGroupName                                       SnmpAdminString,
    cfprApFabricSwSubGroupSlotId                                     CfprApFabricSwSubGroupSlotId,
    cfprApFabricSwSubGroupSwitchId                                   CfprApNetworkSwitchId,
    cfprApFabricSwSubGroupTransport                                  CfprApNetworkTransport,
    cfprApFabricSwSubGroupType                                       CfprApNetworkConnectionType
}

cfprApFabricSwSubGroupInstanceId OBJECT-TYPE
    SYNTAX       CfprApManagedObjectId
    MAX-ACCESS   not-accessible
    STATUS       current
    DESCRIPTION
        "Instance identifier of the managed object."
    ::= { cfprApFabricSwSubGroupEntry 1 }

cfprApFabricSwSubGroupDn OBJECT-TYPE
    SYNTAX       CfprApManagedObjectDn
    MAX-ACCESS   read-only
    STATUS       current
    DESCRIPTION
        "Cisco Firepower fabric:SwSubGroup:dn managed object property"
    ::= { cfprApFabricSwSubGroupEntry 2 }

cfprApFabricSwSubGroupRn OBJECT-TYPE
    SYNTAX       SnmpAdminString
    MAX-ACCESS   read-only
    STATUS       current
    DESCRIPTION
        "Cisco Firepower fabric:SwSubGroup:rn managed object property"
    ::= { cfprApFabricSwSubGroupEntry 3 }

cfprApFabricSwSubGroupAggrPortId OBJECT-TYPE
    SYNTAX       CfprApFabricSwSubGroupAggrPortId
    MAX-ACCESS   read-only
    STATUS       current
    DESCRIPTION
        "Cisco Firepower fabric:SwSubGroup:aggrPortId managed
        object property"
    ::= { cfprApFabricSwSubGroupEntry 4 }

cfprApFabricSwSubGroupConfigState OBJECT-TYPE
    SYNTAX       CfprApFabricSwSubGroupConfigState
    MAX-ACCESS   read-only
    STATUS       current
    DESCRIPTION
        "Cisco Firepower fabric:SwSubGroup:configState
        managed object property"
    ::= { cfprApFabricSwSubGroupEntry 5 }

cfprApFabricSwSubGroupLicGP OBJECT-TYPE
    SYNTAX       Unsigned64
    MAX-ACCESS   read-only
    STATUS       current
    DESCRIPTION
        "Cisco Firepower fabric:SwSubGroup:licGP managed object property"
    ::= { cfprApFabricSwSubGroupEntry 6 }

cfprApFabricSwSubGroupLicState OBJECT-TYPE
    SYNTAX       CfprApLicenseState
    MAX-ACCESS   read-only
    STATUS       current
    DESCRIPTION
        "Cisco Firepower fabric:SwSubGroup:licState managed
        object property"
    ::= { cfprApFabricSwSubGroupEntry 7 }

cfprApFabricSwSubGroupLocale OBJECT-TYPE
    SYNTAX       CfprApNetworkLocale
    MAX-ACCESS   read-only
    STATUS       current
    DESCRIPTION
        "Cisco Firepower fabric:SwSubGroup:locale managed object property"
    ::= { cfprApFabricSwSubGroupEntry 8 }

cfprApFabricSwSubGroupName OBJECT-TYPE
    SYNTAX       SnmpAdminString
    MAX-ACCESS   read-only
    STATUS       current
    DESCRIPTION
        "Cisco Firepower fabric:SwSubGroup:name managed object property"
    ::= { cfprApFabricSwSubGroupEntry 9 }

cfprApFabricSwSubGroupSlotId OBJECT-TYPE
    SYNTAX       CfprApFabricSwSubGroupSlotId
    MAX-ACCESS   read-only
    STATUS       current
    DESCRIPTION
        "Cisco Firepower fabric:SwSubGroup:slotId managed object property"
    ::= { cfprApFabricSwSubGroupEntry 10 }

cfprApFabricSwSubGroupSwitchId OBJECT-TYPE
    SYNTAX       CfprApNetworkSwitchId
    MAX-ACCESS   read-only
    STATUS       current
    DESCRIPTION
        "Cisco Firepower fabric:SwSubGroup:switchId managed
        object property"
    ::= { cfprApFabricSwSubGroupEntry 11 }

cfprApFabricSwSubGroupTransport OBJECT-TYPE
    SYNTAX       CfprApNetworkTransport
    MAX-ACCESS   read-only
    STATUS       current
    DESCRIPTION
        "Cisco Firepower fabric:SwSubGroup:transport managed
        object property"
    ::= { cfprApFabricSwSubGroupEntry 12 }

cfprApFabricSwSubGroupType OBJECT-TYPE
    SYNTAX       CfprApNetworkConnectionType
    MAX-ACCESS   read-only
    STATUS       current
    DESCRIPTION
        "Cisco Firepower fabric:SwSubGroup:type managed object property"
    ::= { cfprApFabricSwSubGroupEntry 13 }

cfprApFabricUdldLinkPolicyTable OBJECT-TYPE
    SYNTAX           SEQUENCE OF CfprApFabricUdldLinkPolicyEntry
    MAX-ACCESS       not-accessible
    STATUS           current
    DESCRIPTION
        "Cisco Firepower fabric:UdldLinkPolicy managed object table"
    ::= { cfprApFabricObjects 113 }

cfprApFabricUdldLinkPolicyEntry OBJECT-TYPE
    SYNTAX           CfprApFabricUdldLinkPolicyEntry
    MAX-ACCESS       not-accessible
    STATUS           current
    DESCRIPTION
        "Entry for the cfprApFabricUdldLinkPolicyTable table."
    INDEX { cfprApFabricUdldLinkPolicyInstanceId }
    ::= { cfprApFabricUdldLinkPolicyTable 1 }

CfprApFabricUdldLinkPolicyEntry ::= SEQUENCE {
    cfprApFabricUdldLinkPolicyInstanceId                             CfprApManagedObjectId,
    cfprApFabricUdldLinkPolicyDn                                     CfprApManagedObjectDn,
    cfprApFabricUdldLinkPolicyRn                                     SnmpAdminString,
    cfprApFabricUdldLinkPolicyAdminState                             CfprApFabricUdldLinkPolicyAdminState,
    cfprApFabricUdldLinkPolicyDescr                                  SnmpAdminString,
    cfprApFabricUdldLinkPolicyIntId                                  SnmpAdminString,
    cfprApFabricUdldLinkPolicyMode                                   CfprApFabricUdldLinkPolicyMode,
    cfprApFabricUdldLinkPolicyName                                   SnmpAdminString,
    cfprApFabricUdldLinkPolicyPolicyLevel                            Gauge32,
    cfprApFabricUdldLinkPolicyPolicyOwner                            CfprApPolicyPolicyOwner,
    cfprApFabricUdldLinkPolicyProtocol                               CfprApFabricEthUdldPolicyProtocol,
    cfprApFabricUdldLinkPolicyType                                   CfprApFabricEthLinkPolicyType
}

cfprApFabricUdldLinkPolicyInstanceId OBJECT-TYPE
    SYNTAX       CfprApManagedObjectId
    MAX-ACCESS   not-accessible
    STATUS       current
    DESCRIPTION
        "Instance identifier of the managed object."
    ::= { cfprApFabricUdldLinkPolicyEntry 1 }

cfprApFabricUdldLinkPolicyDn OBJECT-TYPE
    SYNTAX       CfprApManagedObjectDn
    MAX-ACCESS   read-only
    STATUS       current
    DESCRIPTION
        "Cisco Firepower fabric:UdldLinkPolicy:dn managed object property"
    ::= { cfprApFabricUdldLinkPolicyEntry 2 }

cfprApFabricUdldLinkPolicyRn OBJECT-TYPE
    SYNTAX       SnmpAdminString
    MAX-ACCESS   read-only
    STATUS       current
    DESCRIPTION
        "Cisco Firepower fabric:UdldLinkPolicy:rn managed object property"
    ::= { cfprApFabricUdldLinkPolicyEntry 3 }

cfprApFabricUdldLinkPolicyAdminState OBJECT-TYPE
    SYNTAX       CfprApFabricUdldLinkPolicyAdminState
    MAX-ACCESS   read-only
    STATUS       current
    DESCRIPTION
        "Cisco Firepower fabric:UdldLinkPolicy:adminState
        managed object property"
    ::= { cfprApFabricUdldLinkPolicyEntry 4 }

cfprApFabricUdldLinkPolicyDescr OBJECT-TYPE
    SYNTAX       SnmpAdminString
    MAX-ACCESS   read-only
    STATUS       current
    DESCRIPTION
        "Cisco Firepower fabric:UdldLinkPolicy:descr managed
        object property"
    ::= { cfprApFabricUdldLinkPolicyEntry 5 }

cfprApFabricUdldLinkPolicyIntId OBJECT-TYPE
    SYNTAX       SnmpAdminString
    MAX-ACCESS   read-only
    STATUS       current
    DESCRIPTION
        "Cisco Firepower fabric:UdldLinkPolicy:intId managed
        object property"
    ::= { cfprApFabricUdldLinkPolicyEntry 6 }

cfprApFabricUdldLinkPolicyMode OBJECT-TYPE
    SYNTAX       CfprApFabricUdldLinkPolicyMode
    MAX-ACCESS   read-only
    STATUS       current
    DESCRIPTION
        "Cisco Firepower fabric:UdldLinkPolicy:mode managed
        object property"
    ::= { cfprApFabricUdldLinkPolicyEntry 7 }

cfprApFabricUdldLinkPolicyName OBJECT-TYPE
    SYNTAX       SnmpAdminString
    MAX-ACCESS   read-only
    STATUS       current
    DESCRIPTION
        "Cisco Firepower fabric:UdldLinkPolicy:name managed
        object property"
    ::= { cfprApFabricUdldLinkPolicyEntry 8 }

cfprApFabricUdldLinkPolicyPolicyLevel OBJECT-TYPE
    SYNTAX       Gauge32
    MAX-ACCESS   read-only
    STATUS       current
    DESCRIPTION
        "Cisco Firepower fabric:UdldLinkPolicy:policyLevel
        managed object property"
    ::= { cfprApFabricUdldLinkPolicyEntry 9 }

cfprApFabricUdldLinkPolicyPolicyOwner OBJECT-TYPE
    SYNTAX       CfprApPolicyPolicyOwner
    MAX-ACCESS   read-only
    STATUS       current
    DESCRIPTION
        "Cisco Firepower fabric:UdldLinkPolicy:policyOwner
        managed object property"
    ::= { cfprApFabricUdldLinkPolicyEntry 10 }

cfprApFabricUdldLinkPolicyProtocol OBJECT-TYPE
    SYNTAX       CfprApFabricEthUdldPolicyProtocol
    MAX-ACCESS   read-only
    STATUS       current
    DESCRIPTION
        "Cisco Firepower fabric:UdldLinkPolicy:protocol
        managed object property"
    ::= { cfprApFabricUdldLinkPolicyEntry 11 }

cfprApFabricUdldLinkPolicyType OBJECT-TYPE
    SYNTAX       CfprApFabricEthLinkPolicyType
    MAX-ACCESS   read-only
    STATUS       current
    DESCRIPTION
        "Cisco Firepower fabric:UdldLinkPolicy:type managed
        object property"
    ::= { cfprApFabricUdldLinkPolicyEntry 12 }

cfprApFabricUdldPolicyTable OBJECT-TYPE
    SYNTAX           SEQUENCE OF CfprApFabricUdldPolicyEntry
    MAX-ACCESS       not-accessible
    STATUS           current
    DESCRIPTION
        "Cisco Firepower fabric:UdldPolicy managed object table"
    ::= { cfprApFabricObjects 114 }

cfprApFabricUdldPolicyEntry OBJECT-TYPE
    SYNTAX           CfprApFabricUdldPolicyEntry
    MAX-ACCESS       not-accessible
    STATUS           current
    DESCRIPTION
        "Entry for the cfprApFabricUdldPolicyTable table."
    INDEX { cfprApFabricUdldPolicyInstanceId }
    ::= { cfprApFabricUdldPolicyTable 1 }

CfprApFabricUdldPolicyEntry ::= SEQUENCE {
    cfprApFabricUdldPolicyInstanceId                                 CfprApManagedObjectId,
    cfprApFabricUdldPolicyDn                                         CfprApManagedObjectDn,
    cfprApFabricUdldPolicyRn                                         SnmpAdminString,
    cfprApFabricUdldPolicyDescr                                      SnmpAdminString,
    cfprApFabricUdldPolicyIntId                                      SnmpAdminString,
    cfprApFabricUdldPolicyMsgInterval                                Gauge32,
    cfprApFabricUdldPolicyName                                       SnmpAdminString,
    cfprApFabricUdldPolicyPolicyLevel                                Gauge32,
    cfprApFabricUdldPolicyPolicyOwner                                CfprApPolicyPolicyOwner,
    cfprApFabricUdldPolicyRecoveryAction                             CfprApFabricRecoveryAction
}

cfprApFabricUdldPolicyInstanceId OBJECT-TYPE
    SYNTAX       CfprApManagedObjectId
    MAX-ACCESS   not-accessible
    STATUS       current
    DESCRIPTION
        "Instance identifier of the managed object."
    ::= { cfprApFabricUdldPolicyEntry 1 }

cfprApFabricUdldPolicyDn OBJECT-TYPE
    SYNTAX       CfprApManagedObjectDn
    MAX-ACCESS   read-only
    STATUS       current
    DESCRIPTION
        "Cisco Firepower fabric:UdldPolicy:dn managed object property"
    ::= { cfprApFabricUdldPolicyEntry 2 }

cfprApFabricUdldPolicyRn OBJECT-TYPE
    SYNTAX       SnmpAdminString
    MAX-ACCESS   read-only
    STATUS       current
    DESCRIPTION
        "Cisco Firepower fabric:UdldPolicy:rn managed object property"
    ::= { cfprApFabricUdldPolicyEntry 3 }

cfprApFabricUdldPolicyDescr OBJECT-TYPE
    SYNTAX       SnmpAdminString
    MAX-ACCESS   read-only
    STATUS       current
    DESCRIPTION
        "Cisco Firepower fabric:UdldPolicy:descr managed object property"
    ::= { cfprApFabricUdldPolicyEntry 4 }

cfprApFabricUdldPolicyIntId OBJECT-TYPE
    SYNTAX       SnmpAdminString
    MAX-ACCESS   read-only
    STATUS       current
    DESCRIPTION
        "Cisco Firepower fabric:UdldPolicy:intId managed object property"
    ::= { cfprApFabricUdldPolicyEntry 5 }

cfprApFabricUdldPolicyMsgInterval OBJECT-TYPE
    SYNTAX       Gauge32
    MAX-ACCESS   read-only
    STATUS       current
    DESCRIPTION
        "Cisco Firepower fabric:UdldPolicy:msgInterval
        managed object property"
    ::= { cfprApFabricUdldPolicyEntry 6 }

cfprApFabricUdldPolicyName OBJECT-TYPE
    SYNTAX       SnmpAdminString
    MAX-ACCESS   read-only
    STATUS       current
    DESCRIPTION
        "Cisco Firepower fabric:UdldPolicy:name managed object property"
    ::= { cfprApFabricUdldPolicyEntry 7 }

cfprApFabricUdldPolicyPolicyLevel OBJECT-TYPE
    SYNTAX       Gauge32
    MAX-ACCESS   read-only
    STATUS       current
    DESCRIPTION
        "Cisco Firepower fabric:UdldPolicy:policyLevel
        managed object property"
    ::= { cfprApFabricUdldPolicyEntry 8 }

cfprApFabricUdldPolicyPolicyOwner OBJECT-TYPE
    SYNTAX       CfprApPolicyPolicyOwner
    MAX-ACCESS   read-only
    STATUS       current
    DESCRIPTION
        "Cisco Firepower fabric:UdldPolicy:policyOwner
        managed object property"
    ::= { cfprApFabricUdldPolicyEntry 9 }

cfprApFabricUdldPolicyRecoveryAction OBJECT-TYPE
    SYNTAX       CfprApFabricRecoveryAction
    MAX-ACCESS   read-only
    STATUS       current
    DESCRIPTION
        "Cisco Firepower fabric:UdldPolicy:recoveryAction
        managed object property"
    ::= { cfprApFabricUdldPolicyEntry 10 }

cfprApFabricVConTable OBJECT-TYPE
    SYNTAX           SEQUENCE OF CfprApFabricVConEntry
    MAX-ACCESS       not-accessible
    STATUS           current
    DESCRIPTION
        "Cisco Firepower fabric:VCon managed object table"
    ::= { cfprApFabricObjects 115 }

cfprApFabricVConEntry OBJECT-TYPE
    SYNTAX           CfprApFabricVConEntry
    MAX-ACCESS       not-accessible
    STATUS           current
    DESCRIPTION
        "Entry for the cfprApFabricVConTable table."
    INDEX { cfprApFabricVConInstanceId }
    ::= { cfprApFabricVConTable 1 }

CfprApFabricVConEntry ::= SEQUENCE {
    cfprApFabricVConInstanceId                                       CfprApManagedObjectId,
    cfprApFabricVConDn                                               CfprApManagedObjectDn,
    cfprApFabricVConRn                                               SnmpAdminString,
    cfprApFabricVConEquipmentDn                                      SnmpAdminString,
    cfprApFabricVConFabric                                           SnmpAdminString,
    cfprApFabricVConId                                               SnmpAdminString,
    cfprApFabricVConInstType                                         CfprApFabricVConInstType,
    cfprApFabricVConPlacement                                        CfprApFabricVConPlacementPref,
    cfprApFabricVConSelect                                           CfprApFabricVConSelectPref,
    cfprApFabricVConShare                                            CfprApFabricVConSharePref,
    cfprApFabricVConTransport                                        CfprApFabricVConTransportPref
}

cfprApFabricVConInstanceId OBJECT-TYPE
    SYNTAX       CfprApManagedObjectId
    MAX-ACCESS   not-accessible
    STATUS       current
    DESCRIPTION
        "Instance identifier of the managed object."
    ::= { cfprApFabricVConEntry 1 }

cfprApFabricVConDn OBJECT-TYPE
    SYNTAX       CfprApManagedObjectDn
    MAX-ACCESS   read-only
    STATUS       current
    DESCRIPTION
        "Cisco Firepower fabric:VCon:dn managed object property"
    ::= { cfprApFabricVConEntry 2 }

cfprApFabricVConRn OBJECT-TYPE
    SYNTAX       SnmpAdminString
    MAX-ACCESS   read-only
    STATUS       current
    DESCRIPTION
        "Cisco Firepower fabric:VCon:rn managed object property"
    ::= { cfprApFabricVConEntry 3 }

cfprApFabricVConEquipmentDn OBJECT-TYPE
    SYNTAX       SnmpAdminString
    MAX-ACCESS   read-only
    STATUS       current
    DESCRIPTION
        "Cisco Firepower fabric:VCon:equipmentDn managed object property"
    ::= { cfprApFabricVConEntry 4 }

cfprApFabricVConFabric OBJECT-TYPE
    SYNTAX       SnmpAdminString
    MAX-ACCESS   read-only
    STATUS       current
    DESCRIPTION
        "Cisco Firepower fabric:VCon:fabric managed object property"
    ::= { cfprApFabricVConEntry 5 }

cfprApFabricVConId OBJECT-TYPE
    SYNTAX       SnmpAdminString
    MAX-ACCESS   read-only
    STATUS       current
    DESCRIPTION
        "Cisco Firepower fabric:VCon:id managed object property"
    ::= { cfprApFabricVConEntry 6 }

cfprApFabricVConInstType OBJECT-TYPE
    SYNTAX       CfprApFabricVConInstType
    MAX-ACCESS   read-only
    STATUS       current
    DESCRIPTION
        "Cisco Firepower fabric:VCon:instType managed object property"
    ::= { cfprApFabricVConEntry 7 }

cfprApFabricVConPlacement OBJECT-TYPE
    SYNTAX       CfprApFabricVConPlacementPref
    MAX-ACCESS   read-only
    STATUS       current
    DESCRIPTION
        "Cisco Firepower fabric:VCon:placement managed object property"
    ::= { cfprApFabricVConEntry 8 }

cfprApFabricVConSelect OBJECT-TYPE
    SYNTAX       CfprApFabricVConSelectPref
    MAX-ACCESS   read-only
    STATUS       current
    DESCRIPTION
        "Cisco Firepower fabric:VCon:select managed object property"
    ::= { cfprApFabricVConEntry 9 }

cfprApFabricVConShare OBJECT-TYPE
    SYNTAX       CfprApFabricVConSharePref
    MAX-ACCESS   read-only
    STATUS       current
    DESCRIPTION
        "Cisco Firepower fabric:VCon:share managed object property"
    ::= { cfprApFabricVConEntry 10 }

cfprApFabricVConTransport OBJECT-TYPE
    SYNTAX       CfprApFabricVConTransportPref
    MAX-ACCESS   read-only
    STATUS       current
    DESCRIPTION
        "Cisco Firepower fabric:VCon:transport managed object property"
    ::= { cfprApFabricVConEntry 11 }

cfprApFabricVConProfileTable OBJECT-TYPE
    SYNTAX           SEQUENCE OF CfprApFabricVConProfileEntry
    MAX-ACCESS       not-accessible
    STATUS           current
    DESCRIPTION
        "Cisco Firepower fabric:VConProfile managed object table"
    ::= { cfprApFabricObjects 116 }

cfprApFabricVConProfileEntry OBJECT-TYPE
    SYNTAX           CfprApFabricVConProfileEntry
    MAX-ACCESS       not-accessible
    STATUS           current
    DESCRIPTION
        "Entry for the cfprApFabricVConProfileTable table."
    INDEX { cfprApFabricVConProfileInstanceId }
    ::= { cfprApFabricVConProfileTable 1 }

CfprApFabricVConProfileEntry ::= SEQUENCE {
    cfprApFabricVConProfileInstanceId                                CfprApManagedObjectId,
    cfprApFabricVConProfileDn                                        CfprApManagedObjectDn,
    cfprApFabricVConProfileRn                                        SnmpAdminString,
    cfprApFabricVConProfileDescr                                     SnmpAdminString,
    cfprApFabricVConProfileIntId                                     SnmpAdminString,
    cfprApFabricVConProfileMezzMapping                               CfprApFabricVConMappingScheme,
    cfprApFabricVConProfileName                                      SnmpAdminString,
    cfprApFabricVConProfilePolicyLevel                               Gauge32,
    cfprApFabricVConProfilePolicyOwner                               CfprApPolicyPolicyOwner
}

cfprApFabricVConProfileInstanceId OBJECT-TYPE
    SYNTAX       CfprApManagedObjectId
    MAX-ACCESS   not-accessible
    STATUS       current
    DESCRIPTION
        "Instance identifier of the managed object."
    ::= { cfprApFabricVConProfileEntry 1 }

cfprApFabricVConProfileDn OBJECT-TYPE
    SYNTAX       CfprApManagedObjectDn
    MAX-ACCESS   read-only
    STATUS       current
    DESCRIPTION
        "Cisco Firepower fabric:VConProfile:dn managed object property"
    ::= { cfprApFabricVConProfileEntry 2 }

cfprApFabricVConProfileRn OBJECT-TYPE
    SYNTAX       SnmpAdminString
    MAX-ACCESS   read-only
    STATUS       current
    DESCRIPTION
        "Cisco Firepower fabric:VConProfile:rn managed object property"
    ::= { cfprApFabricVConProfileEntry 3 }

cfprApFabricVConProfileDescr OBJECT-TYPE
    SYNTAX       SnmpAdminString
    MAX-ACCESS   read-only
    STATUS       current
    DESCRIPTION
        "Cisco Firepower fabric:VConProfile:descr managed object property"
    ::= { cfprApFabricVConProfileEntry 4 }

cfprApFabricVConProfileIntId OBJECT-TYPE
    SYNTAX       SnmpAdminString
    MAX-ACCESS   read-only
    STATUS       current
    DESCRIPTION
        "Cisco Firepower fabric:VConProfile:intId managed object property"
    ::= { cfprApFabricVConProfileEntry 5 }

cfprApFabricVConProfileMezzMapping OBJECT-TYPE
    SYNTAX       CfprApFabricVConMappingScheme
    MAX-ACCESS   read-only
    STATUS       current
    DESCRIPTION
        "Cisco Firepower fabric:VConProfile:mezzMapping
        managed object property"
    ::= { cfprApFabricVConProfileEntry 6 }

cfprApFabricVConProfileName OBJECT-TYPE
    SYNTAX       SnmpAdminString
    MAX-ACCESS   read-only
    STATUS       current
    DESCRIPTION
        "Cisco Firepower fabric:VConProfile:name managed object property"
    ::= { cfprApFabricVConProfileEntry 7 }

cfprApFabricVConProfilePolicyLevel OBJECT-TYPE
    SYNTAX       Gauge32
    MAX-ACCESS   read-only
    STATUS       current
    DESCRIPTION
        "Cisco Firepower fabric:VConProfile:policyLevel
        managed object property"
    ::= { cfprApFabricVConProfileEntry 8 }

cfprApFabricVConProfilePolicyOwner OBJECT-TYPE
    SYNTAX       CfprApPolicyPolicyOwner
    MAX-ACCESS   read-only
    STATUS       current
    DESCRIPTION
        "Cisco Firepower fabric:VConProfile:policyOwner
        managed object property"
    ::= { cfprApFabricVConProfileEntry 9 }

cfprApFabricVlanTable OBJECT-TYPE
    SYNTAX           SEQUENCE OF CfprApFabricVlanEntry
    MAX-ACCESS       not-accessible
    STATUS           current
    DESCRIPTION
        "Cisco Firepower fabric:Vlan managed object table"
    ::= { cfprApFabricObjects 117 }

cfprApFabricVlanEntry OBJECT-TYPE
    SYNTAX           CfprApFabricVlanEntry
    MAX-ACCESS       not-accessible
    STATUS           current
    DESCRIPTION
        "Entry for the cfprApFabricVlanTable table."
    INDEX { cfprApFabricVlanInstanceId }
    ::= { cfprApFabricVlanTable 1 }

CfprApFabricVlanEntry ::= SEQUENCE {
    cfprApFabricVlanInstanceId                                       CfprApManagedObjectId,
    cfprApFabricVlanDn                                               CfprApManagedObjectDn,
    cfprApFabricVlanRn                                               SnmpAdminString,
    cfprApFabricVlanAssocPrimaryVlanState                            CfprApFabricVlanAssocPrimaryVlanState,
    cfprApFabricVlanAssocPrimaryVlanSwitchId                         CfprApFabricAVlanAssocPrimaryVlanSwitchId,
    cfprApFabricVlanCloud                                            CfprApFabricCloudType,
    cfprApFabricVlanCompressionType                                  CfprApFabricVlanCompType,
    cfprApFabricVlanConfigIssues                                     CfprApFabricVlanConfigIssues,
    cfprApFabricVlanDefaultNet                                       TruthValue,
    cfprApFabricVlanEpDn                                             SnmpAdminString,
    cfprApFabricVlanFltAggr                                          Unsigned64,
    cfprApFabricVlanGlobal                                           Unsigned64,
    cfprApFabricVlanId                                               Gauge32,
    cfprApFabricVlanIfRole                                           CfprApFabricVnetEpIfRole,
    cfprApFabricVlanIfType                                           CfprApNetworkVnetEpIfType,
    cfprApFabricVlanLocal                                            Unsigned64,
    cfprApFabricVlanLocale                                           CfprApFabricVnetEpLocale,
    cfprApFabricVlanMcastPolicyName                                  SnmpAdminString,
    cfprApFabricVlanName                                             SnmpAdminString,
    cfprApFabricVlanOperMcastPolicyName                              SnmpAdminString,
    cfprApFabricVlanOperState                                        CfprApFabricVlanOperState,
    cfprApFabricVlanOverlapStateForA                                 CfprApFabricVlanOverlapState,
    cfprApFabricVlanOverlapStateForB                                 CfprApFabricVlanOverlapState,
    cfprApFabricVlanPeerDn                                           SnmpAdminString,
    cfprApFabricVlanPolicyOwner                                      CfprApFabricVnetEpPolicyOwner,
    cfprApFabricVlanPubNwDn                                          SnmpAdminString,
    cfprApFabricVlanPubNwId                                          Gauge32,
    cfprApFabricVlanPubNwName                                        SnmpAdminString,
    cfprApFabricVlanSharing                                          CfprApFabricAVlanSharing,
    cfprApFabricVlanSwitchId                                         CfprApFabricVlanSwitchId,
    cfprApFabricVlanTransport                                        CfprApFabricAVlanTransport,
    cfprApFabricVlanType                                             CfprApFabricAVlanType
}

cfprApFabricVlanInstanceId OBJECT-TYPE
    SYNTAX       CfprApManagedObjectId
    MAX-ACCESS   not-accessible
    STATUS       current
    DESCRIPTION
        "Instance identifier of the managed object."
    ::= { cfprApFabricVlanEntry 1 }

cfprApFabricVlanDn OBJECT-TYPE
    SYNTAX       CfprApManagedObjectDn
    MAX-ACCESS   read-only
    STATUS       current
    DESCRIPTION
        "Cisco Firepower fabric:Vlan:dn managed object property"
    ::= { cfprApFabricVlanEntry 2 }

cfprApFabricVlanRn OBJECT-TYPE
    SYNTAX       SnmpAdminString
    MAX-ACCESS   read-only
    STATUS       current
    DESCRIPTION
        "Cisco Firepower fabric:Vlan:rn managed object property"
    ::= { cfprApFabricVlanEntry 3 }

cfprApFabricVlanAssocPrimaryVlanState OBJECT-TYPE
    SYNTAX       CfprApFabricVlanAssocPrimaryVlanState
    MAX-ACCESS   read-only
    STATUS       current
    DESCRIPTION
        "Cisco Firepower fabric:Vlan:assocPrimaryVlanState
        managed object property"
    ::= { cfprApFabricVlanEntry 4 }

cfprApFabricVlanAssocPrimaryVlanSwitchId OBJECT-TYPE
    SYNTAX       CfprApFabricAVlanAssocPrimaryVlanSwitchId
    MAX-ACCESS   read-only
    STATUS       current
    DESCRIPTION
        "Cisco Firepower fabric:Vlan:assocPrimaryVlanSwitchId
        managed object property"
    ::= { cfprApFabricVlanEntry 5 }

cfprApFabricVlanCloud OBJECT-TYPE
    SYNTAX       CfprApFabricCloudType
    MAX-ACCESS   read-only
    STATUS       current
    DESCRIPTION
        "Cisco Firepower fabric:Vlan:cloud managed object property"
    ::= { cfprApFabricVlanEntry 6 }

cfprApFabricVlanCompressionType OBJECT-TYPE
    SYNTAX       CfprApFabricVlanCompType
    MAX-ACCESS   read-only
    STATUS       current
    DESCRIPTION
        "Cisco Firepower fabric:Vlan:compressionType managed
        object property"
    ::= { cfprApFabricVlanEntry 7 }

cfprApFabricVlanConfigIssues OBJECT-TYPE
    SYNTAX       CfprApFabricVlanConfigIssues
    MAX-ACCESS   read-only
    STATUS       current
    DESCRIPTION
        "Cisco Firepower fabric:Vlan:configIssues managed object property"
    ::= { cfprApFabricVlanEntry 8 }

cfprApFabricVlanDefaultNet OBJECT-TYPE
    SYNTAX       TruthValue
    MAX-ACCESS   read-only
    STATUS       current
    DESCRIPTION
        "Cisco Firepower fabric:Vlan:defaultNet managed object property"
    ::= { cfprApFabricVlanEntry 9 }

cfprApFabricVlanEpDn OBJECT-TYPE
    SYNTAX       SnmpAdminString
    MAX-ACCESS   read-only
    STATUS       current
    DESCRIPTION
        "Cisco Firepower fabric:Vlan:epDn managed object property"
    ::= { cfprApFabricVlanEntry 10 }

cfprApFabricVlanFltAggr OBJECT-TYPE
    SYNTAX       Unsigned64
    MAX-ACCESS   read-only
    STATUS       current
    DESCRIPTION
        "Cisco Firepower fabric:Vlan:fltAggr managed object property"
    ::= { cfprApFabricVlanEntry 11 }

cfprApFabricVlanGlobal OBJECT-TYPE
    SYNTAX       Unsigned64
    MAX-ACCESS   read-only
    STATUS       current
    DESCRIPTION
        "Cisco Firepower fabric:Vlan:global managed object property"
    ::= { cfprApFabricVlanEntry 12 }

cfprApFabricVlanId OBJECT-TYPE
    SYNTAX       Gauge32
    MAX-ACCESS   read-only
    STATUS       current
    DESCRIPTION
        "Cisco Firepower fabric:Vlan:id managed object property"
    ::= { cfprApFabricVlanEntry 13 }

cfprApFabricVlanIfRole OBJECT-TYPE
    SYNTAX       CfprApFabricVnetEpIfRole
    MAX-ACCESS   read-only
    STATUS       current
    DESCRIPTION
        "Cisco Firepower fabric:Vlan:ifRole managed object property"
    ::= { cfprApFabricVlanEntry 14 }

cfprApFabricVlanIfType OBJECT-TYPE
    SYNTAX       CfprApNetworkVnetEpIfType
    MAX-ACCESS   read-only
    STATUS       current
    DESCRIPTION
        "Cisco Firepower fabric:Vlan:ifType managed object property"
    ::= { cfprApFabricVlanEntry 15 }

cfprApFabricVlanLocal OBJECT-TYPE
    SYNTAX       Unsigned64
    MAX-ACCESS   read-only
    STATUS       current
    DESCRIPTION
        "Cisco Firepower fabric:Vlan:local managed object property"
    ::= { cfprApFabricVlanEntry 16 }

cfprApFabricVlanLocale OBJECT-TYPE
    SYNTAX       CfprApFabricVnetEpLocale
    MAX-ACCESS   read-only
    STATUS       current
    DESCRIPTION
        "Cisco Firepower fabric:Vlan:locale managed object property"
    ::= { cfprApFabricVlanEntry 17 }

cfprApFabricVlanMcastPolicyName OBJECT-TYPE
    SYNTAX       SnmpAdminString
    MAX-ACCESS   read-only
    STATUS       current
    DESCRIPTION
        "Cisco Firepower fabric:Vlan:mcastPolicyName managed
        object property"
    ::= { cfprApFabricVlanEntry 18 }

cfprApFabricVlanName OBJECT-TYPE
    SYNTAX       SnmpAdminString
    MAX-ACCESS   read-only
    STATUS       current
    DESCRIPTION
        "Cisco Firepower fabric:Vlan:name managed object property"
    ::= { cfprApFabricVlanEntry 19 }

cfprApFabricVlanOperMcastPolicyName OBJECT-TYPE
    SYNTAX       SnmpAdminString
    MAX-ACCESS   read-only
    STATUS       current
    DESCRIPTION
        "Cisco Firepower fabric:Vlan:operMcastPolicyName
        managed object property"
    ::= { cfprApFabricVlanEntry 20 }

cfprApFabricVlanOperState OBJECT-TYPE
    SYNTAX       CfprApFabricVlanOperState
    MAX-ACCESS   read-only
    STATUS       current
    DESCRIPTION
        "Cisco Firepower fabric:Vlan:operState managed object property"
    ::= { cfprApFabricVlanEntry 21 }

cfprApFabricVlanOverlapStateForA OBJECT-TYPE
    SYNTAX       CfprApFabricVlanOverlapState
    MAX-ACCESS   read-only
    STATUS       current
    DESCRIPTION
        "Cisco Firepower fabric:Vlan:overlapStateForA managed
        object property"
    ::= { cfprApFabricVlanEntry 22 }

cfprApFabricVlanOverlapStateForB OBJECT-TYPE
    SYNTAX       CfprApFabricVlanOverlapState
    MAX-ACCESS   read-only
    STATUS       current
    DESCRIPTION
        "Cisco Firepower fabric:Vlan:overlapStateForB managed
        object property"
    ::= { cfprApFabricVlanEntry 23 }

cfprApFabricVlanPeerDn OBJECT-TYPE
    SYNTAX       SnmpAdminString
    MAX-ACCESS   read-only
    STATUS       current
    DESCRIPTION
        "Cisco Firepower fabric:Vlan:peerDn managed object property"
    ::= { cfprApFabricVlanEntry 24 }

cfprApFabricVlanPolicyOwner OBJECT-TYPE
    SYNTAX       CfprApFabricVnetEpPolicyOwner
    MAX-ACCESS   read-only
    STATUS       current
    DESCRIPTION
        "Cisco Firepower fabric:Vlan:policyOwner managed object property"
    ::= { cfprApFabricVlanEntry 25 }

cfprApFabricVlanPubNwDn OBJECT-TYPE
    SYNTAX       SnmpAdminString
    MAX-ACCESS   read-only
    STATUS       current
    DESCRIPTION
        "Cisco Firepower fabric:Vlan:pubNwDn managed object property"
    ::= { cfprApFabricVlanEntry 26 }

cfprApFabricVlanPubNwId OBJECT-TYPE
    SYNTAX       Gauge32
    MAX-ACCESS   read-only
    STATUS       current
    DESCRIPTION
        "Cisco Firepower fabric:Vlan:pubNwId managed object property"
    ::= { cfprApFabricVlanEntry 27 }

cfprApFabricVlanPubNwName OBJECT-TYPE
    SYNTAX       SnmpAdminString
    MAX-ACCESS   read-only
    STATUS       current
    DESCRIPTION
        "Cisco Firepower fabric:Vlan:pubNwName managed object property"
    ::= { cfprApFabricVlanEntry 28 }

cfprApFabricVlanSharing OBJECT-TYPE
    SYNTAX       CfprApFabricAVlanSharing
    MAX-ACCESS   read-only
    STATUS       current
    DESCRIPTION
        "Cisco Firepower fabric:Vlan:sharing managed object property"
    ::= { cfprApFabricVlanEntry 29 }

cfprApFabricVlanSwitchId OBJECT-TYPE
    SYNTAX       CfprApFabricVlanSwitchId
    MAX-ACCESS   read-only
    STATUS       current
    DESCRIPTION
        "Cisco Firepower fabric:Vlan:switchId managed object property"
    ::= { cfprApFabricVlanEntry 30 }

cfprApFabricVlanTransport OBJECT-TYPE
    SYNTAX       CfprApFabricAVlanTransport
    MAX-ACCESS   read-only
    STATUS       current
    DESCRIPTION
        "Cisco Firepower fabric:Vlan:transport managed object property"
    ::= { cfprApFabricVlanEntry 31 }

cfprApFabricVlanType OBJECT-TYPE
    SYNTAX       CfprApFabricAVlanType
    MAX-ACCESS   read-only
    STATUS       current
    DESCRIPTION
        "Cisco Firepower fabric:Vlan:type managed object property"
    ::= { cfprApFabricVlanEntry 32 }

cfprApFabricVlanEpTable OBJECT-TYPE
    SYNTAX           SEQUENCE OF CfprApFabricVlanEpEntry
    MAX-ACCESS       not-accessible
    STATUS           current
    DESCRIPTION
        "Cisco Firepower fabric:VlanEp managed object table"
    ::= { cfprApFabricObjects 118 }

cfprApFabricVlanEpEntry OBJECT-TYPE
    SYNTAX           CfprApFabricVlanEpEntry
    MAX-ACCESS       not-accessible
    STATUS           current
    DESCRIPTION
        "Entry for the cfprApFabricVlanEpTable table."
    INDEX { cfprApFabricVlanEpInstanceId }
    ::= { cfprApFabricVlanEpTable 1 }

CfprApFabricVlanEpEntry ::= SEQUENCE {
    cfprApFabricVlanEpInstanceId                                     CfprApManagedObjectId,
    cfprApFabricVlanEpDnData                                         CfprApManagedObjectDn,
    cfprApFabricVlanEpRn                                             SnmpAdminString,
    cfprApFabricVlanEpAssocPrimaryVlanState                          CfprApFabricVlanAssocPrimaryVlanState,
    cfprApFabricVlanEpAssocPrimaryVlanSwitchId                       CfprApFabricAVlanAssocPrimaryVlanSwitchId,
    cfprApFabricVlanEpEpDn                                           SnmpAdminString,
    cfprApFabricVlanEpId                                             Gauge32,
    cfprApFabricVlanEpIfRole                                         CfprApFabricVnetEpIfRole,
    cfprApFabricVlanEpIfType                                         CfprApNetworkVnetEpIfType,
    cfprApFabricVlanEpIsNative                                       TruthValue,
    cfprApFabricVlanEpLocale                                         CfprApFabricVnetEpLocale,
    cfprApFabricVlanEpName                                           SnmpAdminString,
    cfprApFabricVlanEpOperState                                      CfprApFabricVlanOperState,
    cfprApFabricVlanEpOverlapStateForA                               CfprApFabricVlanOverlapState,
    cfprApFabricVlanEpOverlapStateForB                               CfprApFabricVlanOverlapState,
    cfprApFabricVlanEpPeerDn                                         SnmpAdminString,
    cfprApFabricVlanEpPolicyOwner                                    CfprApFabricVnetEpPolicyOwner,
    cfprApFabricVlanEpPubNwDn                                        SnmpAdminString,
    cfprApFabricVlanEpPubNwId                                        Gauge32,
    cfprApFabricVlanEpPubNwName                                      SnmpAdminString,
    cfprApFabricVlanEpSharing                                        CfprApFabricAVlanSharing,
    cfprApFabricVlanEpSwitchId                                       CfprApNetworkSwitchId,
    cfprApFabricVlanEpTransport                                      CfprApFabricAVlanTransport,
    cfprApFabricVlanEpType                                           CfprApFabricAVlanType
}

cfprApFabricVlanEpInstanceId OBJECT-TYPE
    SYNTAX       CfprApManagedObjectId
    MAX-ACCESS   not-accessible
    STATUS       current
    DESCRIPTION
        "Instance identifier of the managed object."
    ::= { cfprApFabricVlanEpEntry 1 }

cfprApFabricVlanEpDnData OBJECT-TYPE
    SYNTAX       CfprApManagedObjectDn
    MAX-ACCESS   read-only
    STATUS       current
    DESCRIPTION
        "Cisco Firepower fabric:VlanEp:dn managed object property"
    ::= { cfprApFabricVlanEpEntry 2 }

cfprApFabricVlanEpRn OBJECT-TYPE
    SYNTAX       SnmpAdminString
    MAX-ACCESS   read-only
    STATUS       current
    DESCRIPTION
        "Cisco Firepower fabric:VlanEp:rn managed object property"
    ::= { cfprApFabricVlanEpEntry 3 }

cfprApFabricVlanEpAssocPrimaryVlanState OBJECT-TYPE
    SYNTAX       CfprApFabricVlanAssocPrimaryVlanState
    MAX-ACCESS   read-only
    STATUS       current
    DESCRIPTION
        "Cisco Firepower fabric:VlanEp:assocPrimaryVlanState
        managed object property"
    ::= { cfprApFabricVlanEpEntry 4 }

cfprApFabricVlanEpAssocPrimaryVlanSwitchId OBJECT-TYPE
    SYNTAX       CfprApFabricAVlanAssocPrimaryVlanSwitchId
    MAX-ACCESS   read-only
    STATUS       current
    DESCRIPTION
        "Cisco Firepower fabric:VlanEp:assocPrimaryVlanSwitchId
        managed object property"
    ::= { cfprApFabricVlanEpEntry 5 }

cfprApFabricVlanEpEpDn OBJECT-TYPE
    SYNTAX       SnmpAdminString
    MAX-ACCESS   read-only
    STATUS       current
    DESCRIPTION
        "Cisco Firepower fabric:VlanEp:epDn managed object property"
    ::= { cfprApFabricVlanEpEntry 6 }

cfprApFabricVlanEpId OBJECT-TYPE
    SYNTAX       Gauge32
    MAX-ACCESS   read-only
    STATUS       current
    DESCRIPTION
        "Cisco Firepower fabric:VlanEp:id managed object property"
    ::= { cfprApFabricVlanEpEntry 7 }

cfprApFabricVlanEpIfRole OBJECT-TYPE
    SYNTAX       CfprApFabricVnetEpIfRole
    MAX-ACCESS   read-only
    STATUS       current
    DESCRIPTION
        "Cisco Firepower fabric:VlanEp:ifRole managed object property"
    ::= { cfprApFabricVlanEpEntry 8 }

cfprApFabricVlanEpIfType OBJECT-TYPE
    SYNTAX       CfprApNetworkVnetEpIfType
    MAX-ACCESS   read-only
    STATUS       current
    DESCRIPTION
        "Cisco Firepower fabric:VlanEp:ifType managed object property"
    ::= { cfprApFabricVlanEpEntry 9 }

cfprApFabricVlanEpIsNative OBJECT-TYPE
    SYNTAX       TruthValue
    MAX-ACCESS   read-only
    STATUS       current
    DESCRIPTION
        "Cisco Firepower fabric:VlanEp:isNative managed object property"
    ::= { cfprApFabricVlanEpEntry 10 }

cfprApFabricVlanEpLocale OBJECT-TYPE
    SYNTAX       CfprApFabricVnetEpLocale
    MAX-ACCESS   read-only
    STATUS       current
    DESCRIPTION
        "Cisco Firepower fabric:VlanEp:locale managed object property"
    ::= { cfprApFabricVlanEpEntry 11 }

cfprApFabricVlanEpName OBJECT-TYPE
    SYNTAX       SnmpAdminString
    MAX-ACCESS   read-only
    STATUS       current
    DESCRIPTION
        "Cisco Firepower fabric:VlanEp:name managed object property"
    ::= { cfprApFabricVlanEpEntry 12 }

cfprApFabricVlanEpOperState OBJECT-TYPE
    SYNTAX       CfprApFabricVlanOperState
    MAX-ACCESS   read-only
    STATUS       current
    DESCRIPTION
        "Cisco Firepower fabric:VlanEp:operState managed object property"
    ::= { cfprApFabricVlanEpEntry 13 }

cfprApFabricVlanEpOverlapStateForA OBJECT-TYPE
    SYNTAX       CfprApFabricVlanOverlapState
    MAX-ACCESS   read-only
    STATUS       current
    DESCRIPTION
        "Cisco Firepower fabric:VlanEp:overlapStateForA
        managed object property"
    ::= { cfprApFabricVlanEpEntry 14 }

cfprApFabricVlanEpOverlapStateForB OBJECT-TYPE
    SYNTAX       CfprApFabricVlanOverlapState
    MAX-ACCESS   read-only
    STATUS       current
    DESCRIPTION
        "Cisco Firepower fabric:VlanEp:overlapStateForB
        managed object property"
    ::= { cfprApFabricVlanEpEntry 15 }

cfprApFabricVlanEpPeerDn OBJECT-TYPE
    SYNTAX       SnmpAdminString
    MAX-ACCESS   read-only
    STATUS       current
    DESCRIPTION
        "Cisco Firepower fabric:VlanEp:peerDn managed object property"
    ::= { cfprApFabricVlanEpEntry 16 }

cfprApFabricVlanEpPolicyOwner OBJECT-TYPE
    SYNTAX       CfprApFabricVnetEpPolicyOwner
    MAX-ACCESS   read-only
    STATUS       current
    DESCRIPTION
        "Cisco Firepower fabric:VlanEp:policyOwner managed
        object property"
    ::= { cfprApFabricVlanEpEntry 17 }

cfprApFabricVlanEpPubNwDn OBJECT-TYPE
    SYNTAX       SnmpAdminString
    MAX-ACCESS   read-only
    STATUS       current
    DESCRIPTION
        "Cisco Firepower fabric:VlanEp:pubNwDn managed object property"
    ::= { cfprApFabricVlanEpEntry 18 }

cfprApFabricVlanEpPubNwId OBJECT-TYPE
    SYNTAX       Gauge32
    MAX-ACCESS   read-only
    STATUS       current
    DESCRIPTION
        "Cisco Firepower fabric:VlanEp:pubNwId managed object property"
    ::= { cfprApFabricVlanEpEntry 19 }

cfprApFabricVlanEpPubNwName OBJECT-TYPE
    SYNTAX       SnmpAdminString
    MAX-ACCESS   read-only
    STATUS       current
    DESCRIPTION
        "Cisco Firepower fabric:VlanEp:pubNwName managed object property"
    ::= { cfprApFabricVlanEpEntry 20 }

cfprApFabricVlanEpSharing OBJECT-TYPE
    SYNTAX       CfprApFabricAVlanSharing
    MAX-ACCESS   read-only
    STATUS       current
    DESCRIPTION
        "Cisco Firepower fabric:VlanEp:sharing managed object property"
    ::= { cfprApFabricVlanEpEntry 21 }

cfprApFabricVlanEpSwitchId OBJECT-TYPE
    SYNTAX       CfprApNetworkSwitchId
    MAX-ACCESS   read-only
    STATUS       current
    DESCRIPTION
        "Cisco Firepower fabric:VlanEp:switchId managed object property"
    ::= { cfprApFabricVlanEpEntry 22 }

cfprApFabricVlanEpTransport OBJECT-TYPE
    SYNTAX       CfprApFabricAVlanTransport
    MAX-ACCESS   read-only
    STATUS       current
    DESCRIPTION
        "Cisco Firepower fabric:VlanEp:transport managed object property"
    ::= { cfprApFabricVlanEpEntry 23 }

cfprApFabricVlanEpType OBJECT-TYPE
    SYNTAX       CfprApFabricAVlanType
    MAX-ACCESS   read-only
    STATUS       current
    DESCRIPTION
        "Cisco Firepower fabric:VlanEp:type managed object property"
    ::= { cfprApFabricVlanEpEntry 24 }

cfprApFabricVlanGroupReqTable OBJECT-TYPE
    SYNTAX           SEQUENCE OF CfprApFabricVlanGroupReqEntry
    MAX-ACCESS       not-accessible
    STATUS           current
    DESCRIPTION
        "Cisco Firepower fabric:VlanGroupReq managed object table"
    ::= { cfprApFabricObjects 119 }

cfprApFabricVlanGroupReqEntry OBJECT-TYPE
    SYNTAX           CfprApFabricVlanGroupReqEntry
    MAX-ACCESS       not-accessible
    STATUS           current
    DESCRIPTION
        "Entry for the cfprApFabricVlanGroupReqTable table."
    INDEX { cfprApFabricVlanGroupReqInstanceId }
    ::= { cfprApFabricVlanGroupReqTable 1 }

CfprApFabricVlanGroupReqEntry ::= SEQUENCE {
    cfprApFabricVlanGroupReqInstanceId                               CfprApManagedObjectId,
    cfprApFabricVlanGroupReqDn                                       CfprApManagedObjectDn,
    cfprApFabricVlanGroupReqRn                                       SnmpAdminString,
    cfprApFabricVlanGroupReqConfigIssues                             CfprApFabricReqIssues,
    cfprApFabricVlanGroupReqName                                     SnmpAdminString,
    cfprApFabricVlanGroupReqType                                     CfprApFabricAccessType
}

cfprApFabricVlanGroupReqInstanceId OBJECT-TYPE
    SYNTAX       CfprApManagedObjectId
    MAX-ACCESS   not-accessible
    STATUS       current
    DESCRIPTION
        "Instance identifier of the managed object."
    ::= { cfprApFabricVlanGroupReqEntry 1 }

cfprApFabricVlanGroupReqDn OBJECT-TYPE
    SYNTAX       CfprApManagedObjectDn
    MAX-ACCESS   read-only
    STATUS       current
    DESCRIPTION
        "Cisco Firepower fabric:VlanGroupReq:dn managed object property"
    ::= { cfprApFabricVlanGroupReqEntry 2 }

cfprApFabricVlanGroupReqRn OBJECT-TYPE
    SYNTAX       SnmpAdminString
    MAX-ACCESS   read-only
    STATUS       current
    DESCRIPTION
        "Cisco Firepower fabric:VlanGroupReq:rn managed object property"
    ::= { cfprApFabricVlanGroupReqEntry 3 }

cfprApFabricVlanGroupReqConfigIssues OBJECT-TYPE
    SYNTAX       CfprApFabricReqIssues
    MAX-ACCESS   read-only
    STATUS       current
    DESCRIPTION
        "Cisco Firepower fabric:VlanGroupReq:configIssues
        managed object property"
    ::= { cfprApFabricVlanGroupReqEntry 4 }

cfprApFabricVlanGroupReqName OBJECT-TYPE
    SYNTAX       SnmpAdminString
    MAX-ACCESS   read-only
    STATUS       current
    DESCRIPTION
        "Cisco Firepower fabric:VlanGroupReq:name managed object property"
    ::= { cfprApFabricVlanGroupReqEntry 5 }

cfprApFabricVlanGroupReqType OBJECT-TYPE
    SYNTAX       CfprApFabricAccessType
    MAX-ACCESS   read-only
    STATUS       current
    DESCRIPTION
        "Cisco Firepower fabric:VlanGroupReq:type managed object property"
    ::= { cfprApFabricVlanGroupReqEntry 6 }

cfprApFabricVlanPermitTable OBJECT-TYPE
    SYNTAX           SEQUENCE OF CfprApFabricVlanPermitEntry
    MAX-ACCESS       not-accessible
    STATUS           current
    DESCRIPTION
        "Cisco Firepower fabric:VlanPermit managed object table"
    ::= { cfprApFabricObjects 120 }

cfprApFabricVlanPermitEntry OBJECT-TYPE
    SYNTAX           CfprApFabricVlanPermitEntry
    MAX-ACCESS       not-accessible
    STATUS           current
    DESCRIPTION
        "Entry for the cfprApFabricVlanPermitTable table."
    INDEX { cfprApFabricVlanPermitInstanceId }
    ::= { cfprApFabricVlanPermitTable 1 }

CfprApFabricVlanPermitEntry ::= SEQUENCE {
    cfprApFabricVlanPermitInstanceId                                 CfprApManagedObjectId,
    cfprApFabricVlanPermitDn                                         CfprApManagedObjectDn,
    cfprApFabricVlanPermitRn                                         SnmpAdminString,
    cfprApFabricVlanPermitCloud                                      CfprApFabricCloudType,
    cfprApFabricVlanPermitName                                       SnmpAdminString,
    cfprApFabricVlanPermitSwitchId                                   SnmpAdminString
}

cfprApFabricVlanPermitInstanceId OBJECT-TYPE
    SYNTAX       CfprApManagedObjectId
    MAX-ACCESS   not-accessible
    STATUS       current
    DESCRIPTION
        "Instance identifier of the managed object."
    ::= { cfprApFabricVlanPermitEntry 1 }

cfprApFabricVlanPermitDn OBJECT-TYPE
    SYNTAX       CfprApManagedObjectDn
    MAX-ACCESS   read-only
    STATUS       current
    DESCRIPTION
        "Cisco Firepower fabric:VlanPermit:dn managed object property"
    ::= { cfprApFabricVlanPermitEntry 2 }

cfprApFabricVlanPermitRn OBJECT-TYPE
    SYNTAX       SnmpAdminString
    MAX-ACCESS   read-only
    STATUS       current
    DESCRIPTION
        "Cisco Firepower fabric:VlanPermit:rn managed object property"
    ::= { cfprApFabricVlanPermitEntry 3 }

cfprApFabricVlanPermitCloud OBJECT-TYPE
    SYNTAX       CfprApFabricCloudType
    MAX-ACCESS   read-only
    STATUS       current
    DESCRIPTION
        "Cisco Firepower fabric:VlanPermit:cloud managed object property"
    ::= { cfprApFabricVlanPermitEntry 4 }

cfprApFabricVlanPermitName OBJECT-TYPE
    SYNTAX       SnmpAdminString
    MAX-ACCESS   read-only
    STATUS       current
    DESCRIPTION
        "Cisco Firepower fabric:VlanPermit:name managed object property"
    ::= { cfprApFabricVlanPermitEntry 5 }

cfprApFabricVlanPermitSwitchId OBJECT-TYPE
    SYNTAX       SnmpAdminString
    MAX-ACCESS   read-only
    STATUS       current
    DESCRIPTION
        "Cisco Firepower fabric:VlanPermit:switchId managed
        object property"
    ::= { cfprApFabricVlanPermitEntry 6 }

cfprApFabricVlanReqTable OBJECT-TYPE
    SYNTAX           SEQUENCE OF CfprApFabricVlanReqEntry
    MAX-ACCESS       not-accessible
    STATUS           current
    DESCRIPTION
        "Cisco Firepower fabric:VlanReq managed object table"
    ::= { cfprApFabricObjects 121 }

cfprApFabricVlanReqEntry OBJECT-TYPE
    SYNTAX           CfprApFabricVlanReqEntry
    MAX-ACCESS       not-accessible
    STATUS           current
    DESCRIPTION
        "Entry for the cfprApFabricVlanReqTable table."
    INDEX { cfprApFabricVlanReqInstanceId }
    ::= { cfprApFabricVlanReqTable 1 }

CfprApFabricVlanReqEntry ::= SEQUENCE {
    cfprApFabricVlanReqInstanceId                                    CfprApManagedObjectId,
    cfprApFabricVlanReqDn                                            CfprApManagedObjectDn,
    cfprApFabricVlanReqRn                                            SnmpAdminString,
    cfprApFabricVlanReqConfigIssues                                  CfprApFabricReqIssues,
    cfprApFabricVlanReqName                                          SnmpAdminString,
    cfprApFabricVlanReqType                                          CfprApFabricAccessType
}

cfprApFabricVlanReqInstanceId OBJECT-TYPE
    SYNTAX       CfprApManagedObjectId
    MAX-ACCESS   not-accessible
    STATUS       current
    DESCRIPTION
        "Instance identifier of the managed object."
    ::= { cfprApFabricVlanReqEntry 1 }

cfprApFabricVlanReqDn OBJECT-TYPE
    SYNTAX       CfprApManagedObjectDn
    MAX-ACCESS   read-only
    STATUS       current
    DESCRIPTION
        "Cisco Firepower fabric:VlanReq:dn managed object property"
    ::= { cfprApFabricVlanReqEntry 2 }

cfprApFabricVlanReqRn OBJECT-TYPE
    SYNTAX       SnmpAdminString
    MAX-ACCESS   read-only
    STATUS       current
    DESCRIPTION
        "Cisco Firepower fabric:VlanReq:rn managed object property"
    ::= { cfprApFabricVlanReqEntry 3 }

cfprApFabricVlanReqConfigIssues OBJECT-TYPE
    SYNTAX       CfprApFabricReqIssues
    MAX-ACCESS   read-only
    STATUS       current
    DESCRIPTION
        "Cisco Firepower fabric:VlanReq:configIssues managed
        object property"
    ::= { cfprApFabricVlanReqEntry 4 }

cfprApFabricVlanReqName OBJECT-TYPE
    SYNTAX       SnmpAdminString
    MAX-ACCESS   read-only
    STATUS       current
    DESCRIPTION
        "Cisco Firepower fabric:VlanReq:name managed object property"
    ::= { cfprApFabricVlanReqEntry 5 }

cfprApFabricVlanReqType OBJECT-TYPE
    SYNTAX       CfprApFabricAccessType
    MAX-ACCESS   read-only
    STATUS       current
    DESCRIPTION
        "Cisco Firepower fabric:VlanReq:type managed object property"
    ::= { cfprApFabricVlanReqEntry 6 }

cfprApFabricVnetEpSyncEpTable OBJECT-TYPE
    SYNTAX           SEQUENCE OF CfprApFabricVnetEpSyncEpEntry
    MAX-ACCESS       not-accessible
    STATUS           current
    DESCRIPTION
        "Cisco Firepower fabric:VnetEpSyncEp managed object table"
    ::= { cfprApFabricObjects 122 }

cfprApFabricVnetEpSyncEpEntry OBJECT-TYPE
    SYNTAX           CfprApFabricVnetEpSyncEpEntry
    MAX-ACCESS       not-accessible
    STATUS           current
    DESCRIPTION
        "Entry for the cfprApFabricVnetEpSyncEpTable table."
    INDEX { cfprApFabricVnetEpSyncEpInstanceId }
    ::= { cfprApFabricVnetEpSyncEpTable 1 }

CfprApFabricVnetEpSyncEpEntry ::= SEQUENCE {
    cfprApFabricVnetEpSyncEpInstanceId                               CfprApManagedObjectId,
    cfprApFabricVnetEpSyncEpDn                                       CfprApManagedObjectDn,
    cfprApFabricVnetEpSyncEpRn                                       SnmpAdminString,
    cfprApFabricVnetEpSyncEpFsmDescr                                 SnmpAdminString,
    cfprApFabricVnetEpSyncEpFsmPrev                                  SnmpAdminString,
    cfprApFabricVnetEpSyncEpFsmProgr                                 Gauge32,
    cfprApFabricVnetEpSyncEpFsmRmtInvErrCode                         Gauge32,
    cfprApFabricVnetEpSyncEpFsmRmtInvErrDescr                        SnmpAdminString,
    cfprApFabricVnetEpSyncEpFsmRmtInvRslt                            CfprApConditionRemoteInvRslt,
    cfprApFabricVnetEpSyncEpFsmStageDescr                            SnmpAdminString,
    cfprApFabricVnetEpSyncEpFsmStamp                                 DateAndTime,
    cfprApFabricVnetEpSyncEpFsmStatus                                SnmpAdminString,
    cfprApFabricVnetEpSyncEpFsmTry                                   Gauge32,
    cfprApFabricVnetEpSyncEpGenNumSync                               Gauge32,
    cfprApFabricVnetEpSyncEpId                                       Gauge32,
    cfprApFabricVnetEpSyncEpIsChangedObjectUpdate                    TruthValue
}

cfprApFabricVnetEpSyncEpInstanceId OBJECT-TYPE
    SYNTAX       CfprApManagedObjectId
    MAX-ACCESS   not-accessible
    STATUS       current
    DESCRIPTION
        "Instance identifier of the managed object."
    ::= { cfprApFabricVnetEpSyncEpEntry 1 }

cfprApFabricVnetEpSyncEpDn OBJECT-TYPE
    SYNTAX       CfprApManagedObjectDn
    MAX-ACCESS   read-only
    STATUS       current
    DESCRIPTION
        "Cisco Firepower fabric:VnetEpSyncEp:dn managed object property"
    ::= { cfprApFabricVnetEpSyncEpEntry 2 }

cfprApFabricVnetEpSyncEpRn OBJECT-TYPE
    SYNTAX       SnmpAdminString
    MAX-ACCESS   read-only
    STATUS       current
    DESCRIPTION
        "Cisco Firepower fabric:VnetEpSyncEp:rn managed object property"
    ::= { cfprApFabricVnetEpSyncEpEntry 3 }

cfprApFabricVnetEpSyncEpFsmDescr OBJECT-TYPE
    SYNTAX       SnmpAdminString
    MAX-ACCESS   read-only
    STATUS       current
    DESCRIPTION
        "Cisco Firepower fabric:VnetEpSyncEp:fsmDescr managed
        object property"
    ::= { cfprApFabricVnetEpSyncEpEntry 4 }

cfprApFabricVnetEpSyncEpFsmPrev OBJECT-TYPE
    SYNTAX       SnmpAdminString
    MAX-ACCESS   read-only
    STATUS       current
    DESCRIPTION
        "Cisco Firepower fabric:VnetEpSyncEp:fsmPrev managed
        object property"
    ::= { cfprApFabricVnetEpSyncEpEntry 5 }

cfprApFabricVnetEpSyncEpFsmProgr OBJECT-TYPE
    SYNTAX       Gauge32
    MAX-ACCESS   read-only
    STATUS       current
    DESCRIPTION
        "Cisco Firepower fabric:VnetEpSyncEp:fsmProgr managed
        object property"
    ::= { cfprApFabricVnetEpSyncEpEntry 6 }

cfprApFabricVnetEpSyncEpFsmRmtInvErrCode OBJECT-TYPE
    SYNTAX       Gauge32
    MAX-ACCESS   read-only
    STATUS       current
    DESCRIPTION
        "Cisco Firepower fabric:VnetEpSyncEp:fsmRmtInvErrCode
        managed object property"
    ::= { cfprApFabricVnetEpSyncEpEntry 7 }

cfprApFabricVnetEpSyncEpFsmRmtInvErrDescr OBJECT-TYPE
    SYNTAX       SnmpAdminString
    MAX-ACCESS   read-only
    STATUS       current
    DESCRIPTION
        "Cisco Firepower fabric:VnetEpSyncEp:fsmRmtInvErrDescr
        managed object property"
    ::= { cfprApFabricVnetEpSyncEpEntry 8 }

cfprApFabricVnetEpSyncEpFsmRmtInvRslt OBJECT-TYPE
    SYNTAX       CfprApConditionRemoteInvRslt
    MAX-ACCESS   read-only
    STATUS       current
    DESCRIPTION
        "Cisco Firepower fabric:VnetEpSyncEp:fsmRmtInvRslt
        managed object property"
    ::= { cfprApFabricVnetEpSyncEpEntry 9 }

cfprApFabricVnetEpSyncEpFsmStageDescr OBJECT-TYPE
    SYNTAX       SnmpAdminString
    MAX-ACCESS   read-only
    STATUS       current
    DESCRIPTION
        "Cisco Firepower fabric:VnetEpSyncEp:fsmStageDescr
        managed object property"
    ::= { cfprApFabricVnetEpSyncEpEntry 10 }

cfprApFabricVnetEpSyncEpFsmStamp OBJECT-TYPE
    SYNTAX       DateAndTime
    MAX-ACCESS   read-only
    STATUS       current
    DESCRIPTION
        "Cisco Firepower fabric:VnetEpSyncEp:fsmStamp managed
        object property"
    ::= { cfprApFabricVnetEpSyncEpEntry 11 }

cfprApFabricVnetEpSyncEpFsmStatus OBJECT-TYPE
    SYNTAX       SnmpAdminString
    MAX-ACCESS   read-only
    STATUS       current
    DESCRIPTION
        "Cisco Firepower fabric:VnetEpSyncEp:fsmStatus
        managed object property"
    ::= { cfprApFabricVnetEpSyncEpEntry 12 }

cfprApFabricVnetEpSyncEpFsmTry OBJECT-TYPE
    SYNTAX       Gauge32
    MAX-ACCESS   read-only
    STATUS       current
    DESCRIPTION
        "Cisco Firepower fabric:VnetEpSyncEp:fsmTry managed
        object property"
    ::= { cfprApFabricVnetEpSyncEpEntry 13 }

cfprApFabricVnetEpSyncEpGenNumSync OBJECT-TYPE
    SYNTAX       Gauge32
    MAX-ACCESS   read-only
    STATUS       current
    DESCRIPTION
        "Cisco Firepower fabric:VnetEpSyncEp:genNumSync
        managed object property"
    ::= { cfprApFabricVnetEpSyncEpEntry 14 }

cfprApFabricVnetEpSyncEpId OBJECT-TYPE
    SYNTAX       Gauge32
    MAX-ACCESS   read-only
    STATUS       current
    DESCRIPTION
        "Cisco Firepower fabric:VnetEpSyncEp:id managed object property"
    ::= { cfprApFabricVnetEpSyncEpEntry 15 }

cfprApFabricVnetEpSyncEpIsChangedObjectUpdate OBJECT-TYPE
    SYNTAX       TruthValue
    MAX-ACCESS   read-only
    STATUS       current
    DESCRIPTION
        "Cisco Firepower fabric:VnetEpSyncEp:isChangedObjectUpdate
        managed object property"
    ::= { cfprApFabricVnetEpSyncEpEntry 16 }

cfprApFabricVnetEpSyncEpFsmTable OBJECT-TYPE
    SYNTAX           SEQUENCE OF CfprApFabricVnetEpSyncEpFsmEntry
    MAX-ACCESS       not-accessible
    STATUS           current
    DESCRIPTION
        "Cisco Firepower fabric:VnetEpSyncEpFsm managed object table"
    ::= { cfprApFabricObjects 123 }

cfprApFabricVnetEpSyncEpFsmEntry OBJECT-TYPE
    SYNTAX           CfprApFabricVnetEpSyncEpFsmEntry
    MAX-ACCESS       not-accessible
    STATUS           current
    DESCRIPTION
        "Entry for the cfprApFabricVnetEpSyncEpFsmTable table."
    INDEX { cfprApFabricVnetEpSyncEpFsmInstanceId }
    ::= { cfprApFabricVnetEpSyncEpFsmTable 1 }

CfprApFabricVnetEpSyncEpFsmEntry ::= SEQUENCE {
    cfprApFabricVnetEpSyncEpFsmInstanceId                            CfprApManagedObjectId,
    cfprApFabricVnetEpSyncEpFsmDn                                    CfprApManagedObjectDn,
    cfprApFabricVnetEpSyncEpFsmRn                                    SnmpAdminString,
    cfprApFabricVnetEpSyncEpFsmCompletionTime                        DateAndTime,
    cfprApFabricVnetEpSyncEpFsmCurrentFsm                            CfprApFabricVnetEpSyncEpFsmCurrentFsm,
    cfprApFabricVnetEpSyncEpFsmDescrData                             SnmpAdminString,
    cfprApFabricVnetEpSyncEpFsmFsmStatus                             CfprApFsmFsmStageStatus,
    cfprApFabricVnetEpSyncEpFsmProgress                              Gauge32,
    cfprApFabricVnetEpSyncEpFsmRmtErrCode                            Gauge32,
    cfprApFabricVnetEpSyncEpFsmRmtErrDescr                           SnmpAdminString,
    cfprApFabricVnetEpSyncEpFsmRmtRslt                               CfprApConditionRemoteInvRslt
}

cfprApFabricVnetEpSyncEpFsmInstanceId OBJECT-TYPE
    SYNTAX       CfprApManagedObjectId
    MAX-ACCESS   not-accessible
    STATUS       current
    DESCRIPTION
        "Instance identifier of the managed object."
    ::= { cfprApFabricVnetEpSyncEpFsmEntry 1 }

cfprApFabricVnetEpSyncEpFsmDn OBJECT-TYPE
    SYNTAX       CfprApManagedObjectDn
    MAX-ACCESS   read-only
    STATUS       current
    DESCRIPTION
        "Cisco Firepower fabric:VnetEpSyncEpFsm:dn managed
        object property"
    ::= { cfprApFabricVnetEpSyncEpFsmEntry 2 }

cfprApFabricVnetEpSyncEpFsmRn OBJECT-TYPE
    SYNTAX       SnmpAdminString
    MAX-ACCESS   read-only
    STATUS       current
    DESCRIPTION
        "Cisco Firepower fabric:VnetEpSyncEpFsm:rn managed
        object property"
    ::= { cfprApFabricVnetEpSyncEpFsmEntry 3 }

cfprApFabricVnetEpSyncEpFsmCompletionTime OBJECT-TYPE
    SYNTAX       DateAndTime
    MAX-ACCESS   read-only
    STATUS       current
    DESCRIPTION
        "Cisco Firepower fabric:VnetEpSyncEpFsm:completionTime
        managed object property"
    ::= { cfprApFabricVnetEpSyncEpFsmEntry 4 }

cfprApFabricVnetEpSyncEpFsmCurrentFsm OBJECT-TYPE
    SYNTAX       CfprApFabricVnetEpSyncEpFsmCurrentFsm
    MAX-ACCESS   read-only
    STATUS       current
    DESCRIPTION
        "Cisco Firepower fabric:VnetEpSyncEpFsm:currentFsm
        managed object property"
    ::= { cfprApFabricVnetEpSyncEpFsmEntry 5 }

cfprApFabricVnetEpSyncEpFsmDescrData OBJECT-TYPE
    SYNTAX       SnmpAdminString
    MAX-ACCESS   read-only
    STATUS       current
    DESCRIPTION
        "Cisco Firepower fabric:VnetEpSyncEpFsm:descr managed
        object property"
    ::= { cfprApFabricVnetEpSyncEpFsmEntry 6 }

cfprApFabricVnetEpSyncEpFsmFsmStatus OBJECT-TYPE
    SYNTAX       CfprApFsmFsmStageStatus
    MAX-ACCESS   read-only
    STATUS       current
    DESCRIPTION
        "Cisco Firepower fabric:VnetEpSyncEpFsm:fsmStatus
        managed object property"
    ::= { cfprApFabricVnetEpSyncEpFsmEntry 7 }

cfprApFabricVnetEpSyncEpFsmProgress OBJECT-TYPE
    SYNTAX       Gauge32
    MAX-ACCESS   read-only
    STATUS       current
    DESCRIPTION
        "Cisco Firepower fabric:VnetEpSyncEpFsm:progress
        managed object property"
    ::= { cfprApFabricVnetEpSyncEpFsmEntry 8 }

cfprApFabricVnetEpSyncEpFsmRmtErrCode OBJECT-TYPE
    SYNTAX       Gauge32
    MAX-ACCESS   read-only
    STATUS       current
    DESCRIPTION
        "Cisco Firepower fabric:VnetEpSyncEpFsm:rmtErrCode
        managed object property"
    ::= { cfprApFabricVnetEpSyncEpFsmEntry 9 }

cfprApFabricVnetEpSyncEpFsmRmtErrDescr OBJECT-TYPE
    SYNTAX       SnmpAdminString
    MAX-ACCESS   read-only
    STATUS       current
    DESCRIPTION
        "Cisco Firepower fabric:VnetEpSyncEpFsm:rmtErrDescr
        managed object property"
    ::= { cfprApFabricVnetEpSyncEpFsmEntry 10 }

cfprApFabricVnetEpSyncEpFsmRmtRslt OBJECT-TYPE
    SYNTAX       CfprApConditionRemoteInvRslt
    MAX-ACCESS   read-only
    STATUS       current
    DESCRIPTION
        "Cisco Firepower fabric:VnetEpSyncEpFsm:rmtRslt
        managed object property"
    ::= { cfprApFabricVnetEpSyncEpFsmEntry 11 }

cfprApFabricVnetEpSyncEpFsmStageTable OBJECT-TYPE
    SYNTAX           SEQUENCE OF CfprApFabricVnetEpSyncEpFsmStageEntry
    MAX-ACCESS       not-accessible
    STATUS           current
    DESCRIPTION
        "Cisco Firepower fabric:VnetEpSyncEpFsmStage managed object table"
    ::= { cfprApFabricObjects 124 }

cfprApFabricVnetEpSyncEpFsmStageEntry OBJECT-TYPE
    SYNTAX           CfprApFabricVnetEpSyncEpFsmStageEntry
    MAX-ACCESS       not-accessible
    STATUS           current
    DESCRIPTION
        "Entry for the cfprApFabricVnetEpSyncEpFsmStageTable table."
    INDEX { cfprApFabricVnetEpSyncEpFsmStageInstanceId }
    ::= { cfprApFabricVnetEpSyncEpFsmStageTable 1 }

CfprApFabricVnetEpSyncEpFsmStageEntry ::= SEQUENCE {
    cfprApFabricVnetEpSyncEpFsmStageInstanceId                       CfprApManagedObjectId,
    cfprApFabricVnetEpSyncEpFsmStageDn                               CfprApManagedObjectDn,
    cfprApFabricVnetEpSyncEpFsmStageRn                               SnmpAdminString,
    cfprApFabricVnetEpSyncEpFsmStageDescrData                        SnmpAdminString,
    cfprApFabricVnetEpSyncEpFsmStageLastUpdateTime                   DateAndTime,
    cfprApFabricVnetEpSyncEpFsmStageName                             CfprApFabricVnetEpSyncEpFsmStageName,
    cfprApFabricVnetEpSyncEpFsmStageOrder                            Gauge32,
    cfprApFabricVnetEpSyncEpFsmStageRetry                            Gauge32,
    cfprApFabricVnetEpSyncEpFsmStageStageStatus                      CfprApFsmFsmStageStatus
}

cfprApFabricVnetEpSyncEpFsmStageInstanceId OBJECT-TYPE
    SYNTAX       CfprApManagedObjectId
    MAX-ACCESS   not-accessible
    STATUS       current
    DESCRIPTION
        "Instance identifier of the managed object."
    ::= { cfprApFabricVnetEpSyncEpFsmStageEntry 1 }

cfprApFabricVnetEpSyncEpFsmStageDn OBJECT-TYPE
    SYNTAX       CfprApManagedObjectDn
    MAX-ACCESS   read-only
    STATUS       current
    DESCRIPTION
        "Cisco Firepower fabric:VnetEpSyncEpFsmStage:dn
        managed object property"
    ::= { cfprApFabricVnetEpSyncEpFsmStageEntry 2 }

cfprApFabricVnetEpSyncEpFsmStageRn OBJECT-TYPE
    SYNTAX       SnmpAdminString
    MAX-ACCESS   read-only
    STATUS       current
    DESCRIPTION
        "Cisco Firepower fabric:VnetEpSyncEpFsmStage:rn
        managed object property"
    ::= { cfprApFabricVnetEpSyncEpFsmStageEntry 3 }

cfprApFabricVnetEpSyncEpFsmStageDescrData OBJECT-TYPE
    SYNTAX       SnmpAdminString
    MAX-ACCESS   read-only
    STATUS       current
    DESCRIPTION
        "Cisco Firepower fabric:VnetEpSyncEpFsmStage:descr
        managed object property"
    ::= { cfprApFabricVnetEpSyncEpFsmStageEntry 4 }

cfprApFabricVnetEpSyncEpFsmStageLastUpdateTime OBJECT-TYPE
    SYNTAX       DateAndTime
    MAX-ACCESS   read-only
    STATUS       current
    DESCRIPTION
        "Cisco Firepower fabric:VnetEpSyncEpFsmStage:lastUpdateTime
        managed object property"
    ::= { cfprApFabricVnetEpSyncEpFsmStageEntry 5 }

cfprApFabricVnetEpSyncEpFsmStageName OBJECT-TYPE
    SYNTAX       CfprApFabricVnetEpSyncEpFsmStageName
    MAX-ACCESS   read-only
    STATUS       current
    DESCRIPTION
        "Cisco Firepower fabric:VnetEpSyncEpFsmStage:name
        managed object property"
    ::= { cfprApFabricVnetEpSyncEpFsmStageEntry 6 }

cfprApFabricVnetEpSyncEpFsmStageOrder OBJECT-TYPE
    SYNTAX       Gauge32
    MAX-ACCESS   read-only
    STATUS       current
    DESCRIPTION
        "Cisco Firepower fabric:VnetEpSyncEpFsmStage:order
        managed object property"
    ::= { cfprApFabricVnetEpSyncEpFsmStageEntry 7 }

cfprApFabricVnetEpSyncEpFsmStageRetry OBJECT-TYPE
    SYNTAX       Gauge32
    MAX-ACCESS   read-only
    STATUS       current
    DESCRIPTION
        "Cisco Firepower fabric:VnetEpSyncEpFsmStage:retry
        managed object property"
    ::= { cfprApFabricVnetEpSyncEpFsmStageEntry 8 }

cfprApFabricVnetEpSyncEpFsmStageStageStatus OBJECT-TYPE
    SYNTAX       CfprApFsmFsmStageStatus
    MAX-ACCESS   read-only
    STATUS       current
    DESCRIPTION
        "Cisco Firepower fabric:VnetEpSyncEpFsmStage:stageStatus
        managed object property"
    ::= { cfprApFabricVnetEpSyncEpFsmStageEntry 9 }

cfprApFabricVnetEpSyncEpFsmTaskTable OBJECT-TYPE
    SYNTAX           SEQUENCE OF CfprApFabricVnetEpSyncEpFsmTaskEntry
    MAX-ACCESS       not-accessible
    STATUS           current
    DESCRIPTION
        "Cisco Firepower fabric:VnetEpSyncEpFsmTask managed object table"
    ::= { cfprApFabricObjects 125 }

cfprApFabricVnetEpSyncEpFsmTaskEntry OBJECT-TYPE
    SYNTAX           CfprApFabricVnetEpSyncEpFsmTaskEntry
    MAX-ACCESS       not-accessible
    STATUS           current
    DESCRIPTION
        "Entry for the cfprApFabricVnetEpSyncEpFsmTaskTable table."
    INDEX { cfprApFabricVnetEpSyncEpFsmTaskInstanceId }
    ::= { cfprApFabricVnetEpSyncEpFsmTaskTable 1 }

CfprApFabricVnetEpSyncEpFsmTaskEntry ::= SEQUENCE {
    cfprApFabricVnetEpSyncEpFsmTaskInstanceId                        CfprApManagedObjectId,
    cfprApFabricVnetEpSyncEpFsmTaskDn                                CfprApManagedObjectDn,
    cfprApFabricVnetEpSyncEpFsmTaskRn                                SnmpAdminString,
    cfprApFabricVnetEpSyncEpFsmTaskCompletion                        CfprApFsmCompletion,
    cfprApFabricVnetEpSyncEpFsmTaskFlags                             CfprApFsmFlags,
    cfprApFabricVnetEpSyncEpFsmTaskItem                              CfprApFabricVnetEpSyncEpFsmTaskItem,
    cfprApFabricVnetEpSyncEpFsmTaskSeqId                             Gauge32
}

cfprApFabricVnetEpSyncEpFsmTaskInstanceId OBJECT-TYPE
    SYNTAX       CfprApManagedObjectId
    MAX-ACCESS   not-accessible
    STATUS       current
    DESCRIPTION
        "Instance identifier of the managed object."
    ::= { cfprApFabricVnetEpSyncEpFsmTaskEntry 1 }

cfprApFabricVnetEpSyncEpFsmTaskDn OBJECT-TYPE
    SYNTAX       CfprApManagedObjectDn
    MAX-ACCESS   read-only
    STATUS       current
    DESCRIPTION
        "Cisco Firepower fabric:VnetEpSyncEpFsmTask:dn
        managed object property"
    ::= { cfprApFabricVnetEpSyncEpFsmTaskEntry 2 }

cfprApFabricVnetEpSyncEpFsmTaskRn OBJECT-TYPE
    SYNTAX       SnmpAdminString
    MAX-ACCESS   read-only
    STATUS       current
    DESCRIPTION
        "Cisco Firepower fabric:VnetEpSyncEpFsmTask:rn
        managed object property"
    ::= { cfprApFabricVnetEpSyncEpFsmTaskEntry 3 }

cfprApFabricVnetEpSyncEpFsmTaskCompletion OBJECT-TYPE
    SYNTAX       CfprApFsmCompletion
    MAX-ACCESS   read-only
    STATUS       current
    DESCRIPTION
        "Cisco Firepower fabric:VnetEpSyncEpFsmTask:completion
        managed object property"
    ::= { cfprApFabricVnetEpSyncEpFsmTaskEntry 4 }

cfprApFabricVnetEpSyncEpFsmTaskFlags OBJECT-TYPE
    SYNTAX       CfprApFsmFlags
    MAX-ACCESS   read-only
    STATUS       current
    DESCRIPTION
        "Cisco Firepower fabric:VnetEpSyncEpFsmTask:flags
        managed object property"
    ::= { cfprApFabricVnetEpSyncEpFsmTaskEntry 5 }

cfprApFabricVnetEpSyncEpFsmTaskItem OBJECT-TYPE
    SYNTAX       CfprApFabricVnetEpSyncEpFsmTaskItem
    MAX-ACCESS   read-only
    STATUS       current
    DESCRIPTION
        "Cisco Firepower fabric:VnetEpSyncEpFsmTask:item
        managed object property"
    ::= { cfprApFabricVnetEpSyncEpFsmTaskEntry 6 }

cfprApFabricVnetEpSyncEpFsmTaskSeqId OBJECT-TYPE
    SYNTAX       Gauge32
    MAX-ACCESS   read-only
    STATUS       current
    DESCRIPTION
        "Cisco Firepower fabric:VnetEpSyncEpFsmTask:seqId
        managed object property"
    ::= { cfprApFabricVnetEpSyncEpFsmTaskEntry 7 }

cfprApFabricVsanTable OBJECT-TYPE
    SYNTAX           SEQUENCE OF CfprApFabricVsanEntry
    MAX-ACCESS       not-accessible
    STATUS           current
    DESCRIPTION
        "Cisco Firepower fabric:Vsan managed object table"
    ::= { cfprApFabricObjects 126 }

cfprApFabricVsanEntry OBJECT-TYPE
    SYNTAX           CfprApFabricVsanEntry
    MAX-ACCESS       not-accessible
    STATUS           current
    DESCRIPTION
        "Entry for the cfprApFabricVsanTable table."
    INDEX { cfprApFabricVsanInstanceId }
    ::= { cfprApFabricVsanTable 1 }

CfprApFabricVsanEntry ::= SEQUENCE {
    cfprApFabricVsanInstanceId                                       CfprApManagedObjectId,
    cfprApFabricVsanDn                                               CfprApManagedObjectDn,
    cfprApFabricVsanRn                                               SnmpAdminString,
    cfprApFabricVsanDefaultZoning                                    CfprApFabricDefaultZoningState,
    cfprApFabricVsanEpDn                                             SnmpAdminString,
    cfprApFabricVsanFcZoneSharingMode                                CfprApFabricFcZoneSharingMode,
    cfprApFabricVsanFcoeVlan                                         Gauge32,
    cfprApFabricVsanFltAggr                                          Unsigned64,
    cfprApFabricVsanGlobal                                           Unsigned64,
    cfprApFabricVsanId                                               Gauge32,
    cfprApFabricVsanIfRole                                           CfprApFabricVnetEpIfRole,
    cfprApFabricVsanIfType                                           CfprApNetworkVnetEpIfType,
    cfprApFabricVsanLocal                                            Unsigned64,
    cfprApFabricVsanLocale                                           CfprApFabricVnetEpLocale,
    cfprApFabricVsanName                                             SnmpAdminString,
    cfprApFabricVsanOperState                                        CfprApFabricVsanOperState,
    cfprApFabricVsanPeerDn                                           SnmpAdminString,
    cfprApFabricVsanPolicyOwner                                      CfprApFabricVnetEpPolicyOwner,
    cfprApFabricVsanSwitchId                                         CfprApFabricVsanSwitchId,
    cfprApFabricVsanTransport                                        CfprApFabricAVsanTransport,
    cfprApFabricVsanType                                             CfprApFabricAVsanType,
    cfprApFabricVsanZoningState                                      CfprApFabricZoningState
}

cfprApFabricVsanInstanceId OBJECT-TYPE
    SYNTAX       CfprApManagedObjectId
    MAX-ACCESS   not-accessible
    STATUS       current
    DESCRIPTION
        "Instance identifier of the managed object."
    ::= { cfprApFabricVsanEntry 1 }

cfprApFabricVsanDn OBJECT-TYPE
    SYNTAX       CfprApManagedObjectDn
    MAX-ACCESS   read-only
    STATUS       current
    DESCRIPTION
        "Cisco Firepower fabric:Vsan:dn managed object property"
    ::= { cfprApFabricVsanEntry 2 }

cfprApFabricVsanRn OBJECT-TYPE
    SYNTAX       SnmpAdminString
    MAX-ACCESS   read-only
    STATUS       current
    DESCRIPTION
        "Cisco Firepower fabric:Vsan:rn managed object property"
    ::= { cfprApFabricVsanEntry 3 }

cfprApFabricVsanDefaultZoning OBJECT-TYPE
    SYNTAX       CfprApFabricDefaultZoningState
    MAX-ACCESS   read-only
    STATUS       current
    DESCRIPTION
        "Cisco Firepower fabric:Vsan:defaultZoning managed
        object property"
    ::= { cfprApFabricVsanEntry 4 }

cfprApFabricVsanEpDn OBJECT-TYPE
    SYNTAX       SnmpAdminString
    MAX-ACCESS   read-only
    STATUS       current
    DESCRIPTION
        "Cisco Firepower fabric:Vsan:epDn managed object property"
    ::= { cfprApFabricVsanEntry 5 }

cfprApFabricVsanFcZoneSharingMode OBJECT-TYPE
    SYNTAX       CfprApFabricFcZoneSharingMode
    MAX-ACCESS   read-only
    STATUS       current
    DESCRIPTION
        "Cisco Firepower fabric:Vsan:fcZoneSharingMode
        managed object property"
    ::= { cfprApFabricVsanEntry 6 }

cfprApFabricVsanFcoeVlan OBJECT-TYPE
    SYNTAX       Gauge32
    MAX-ACCESS   read-only
    STATUS       current
    DESCRIPTION
        "Cisco Firepower fabric:Vsan:fcoeVlan managed object property"
    ::= { cfprApFabricVsanEntry 7 }

cfprApFabricVsanFltAggr OBJECT-TYPE
    SYNTAX       Unsigned64
    MAX-ACCESS   read-only
    STATUS       current
    DESCRIPTION
        "Cisco Firepower fabric:Vsan:fltAggr managed object property"
    ::= { cfprApFabricVsanEntry 8 }

cfprApFabricVsanGlobal OBJECT-TYPE
    SYNTAX       Unsigned64
    MAX-ACCESS   read-only
    STATUS       current
    DESCRIPTION
        "Cisco Firepower fabric:Vsan:global managed object property"
    ::= { cfprApFabricVsanEntry 9 }

cfprApFabricVsanId OBJECT-TYPE
    SYNTAX       Gauge32
    MAX-ACCESS   read-only
    STATUS       current
    DESCRIPTION
        "Cisco Firepower fabric:Vsan:id managed object property"
    ::= { cfprApFabricVsanEntry 10 }

cfprApFabricVsanIfRole OBJECT-TYPE
    SYNTAX       CfprApFabricVnetEpIfRole
    MAX-ACCESS   read-only
    STATUS       current
    DESCRIPTION
        "Cisco Firepower fabric:Vsan:ifRole managed object property"
    ::= { cfprApFabricVsanEntry 11 }

cfprApFabricVsanIfType OBJECT-TYPE
    SYNTAX       CfprApNetworkVnetEpIfType
    MAX-ACCESS   read-only
    STATUS       current
    DESCRIPTION
        "Cisco Firepower fabric:Vsan:ifType managed object property"
    ::= { cfprApFabricVsanEntry 12 }

cfprApFabricVsanLocal OBJECT-TYPE
    SYNTAX       Unsigned64
    MAX-ACCESS   read-only
    STATUS       current
    DESCRIPTION
        "Cisco Firepower fabric:Vsan:local managed object property"
    ::= { cfprApFabricVsanEntry 13 }

cfprApFabricVsanLocale OBJECT-TYPE
    SYNTAX       CfprApFabricVnetEpLocale
    MAX-ACCESS   read-only
    STATUS       current
    DESCRIPTION
        "Cisco Firepower fabric:Vsan:locale managed object property"
    ::= { cfprApFabricVsanEntry 14 }

cfprApFabricVsanName OBJECT-TYPE
    SYNTAX       SnmpAdminString
    MAX-ACCESS   read-only
    STATUS       current
    DESCRIPTION
        "Cisco Firepower fabric:Vsan:name managed object property"
    ::= { cfprApFabricVsanEntry 15 }

cfprApFabricVsanOperState OBJECT-TYPE
    SYNTAX       CfprApFabricVsanOperState
    MAX-ACCESS   read-only
    STATUS       current
    DESCRIPTION
        "Cisco Firepower fabric:Vsan:operState managed object property"
    ::= { cfprApFabricVsanEntry 16 }

cfprApFabricVsanPeerDn OBJECT-TYPE
    SYNTAX       SnmpAdminString
    MAX-ACCESS   read-only
    STATUS       current
    DESCRIPTION
        "Cisco Firepower fabric:Vsan:peerDn managed object property"
    ::= { cfprApFabricVsanEntry 17 }

cfprApFabricVsanPolicyOwner OBJECT-TYPE
    SYNTAX       CfprApFabricVnetEpPolicyOwner
    MAX-ACCESS   read-only
    STATUS       current
    DESCRIPTION
        "Cisco Firepower fabric:Vsan:policyOwner managed object property"
    ::= { cfprApFabricVsanEntry 18 }

cfprApFabricVsanSwitchId OBJECT-TYPE
    SYNTAX       CfprApFabricVsanSwitchId
    MAX-ACCESS   read-only
    STATUS       current
    DESCRIPTION
        "Cisco Firepower fabric:Vsan:switchId managed object property"
    ::= { cfprApFabricVsanEntry 19 }

cfprApFabricVsanTransport OBJECT-TYPE
    SYNTAX       CfprApFabricAVsanTransport
    MAX-ACCESS   read-only
    STATUS       current
    DESCRIPTION
        "Cisco Firepower fabric:Vsan:transport managed object property"
    ::= { cfprApFabricVsanEntry 20 }

cfprApFabricVsanType OBJECT-TYPE
    SYNTAX       CfprApFabricAVsanType
    MAX-ACCESS   read-only
    STATUS       current
    DESCRIPTION
        "Cisco Firepower fabric:Vsan:type managed object property"
    ::= { cfprApFabricVsanEntry 21 }

cfprApFabricVsanZoningState OBJECT-TYPE
    SYNTAX       CfprApFabricZoningState
    MAX-ACCESS   read-only
    STATUS       current
    DESCRIPTION
        "Cisco Firepower fabric:Vsan:zoningState managed object property"
    ::= { cfprApFabricVsanEntry 22 }

cfprApFabricVsanEpTable OBJECT-TYPE
    SYNTAX           SEQUENCE OF CfprApFabricVsanEpEntry
    MAX-ACCESS       not-accessible
    STATUS           current
    DESCRIPTION
        "Cisco Firepower fabric:VsanEp managed object table"
    ::= { cfprApFabricObjects 127 }

cfprApFabricVsanEpEntry OBJECT-TYPE
    SYNTAX           CfprApFabricVsanEpEntry
    MAX-ACCESS       not-accessible
    STATUS           current
    DESCRIPTION
        "Entry for the cfprApFabricVsanEpTable table."
    INDEX { cfprApFabricVsanEpInstanceId }
    ::= { cfprApFabricVsanEpTable 1 }

CfprApFabricVsanEpEntry ::= SEQUENCE {
    cfprApFabricVsanEpInstanceId                                     CfprApManagedObjectId,
    cfprApFabricVsanEpDnData                                         CfprApManagedObjectDn,
    cfprApFabricVsanEpRn                                             SnmpAdminString,
    cfprApFabricVsanEpEpDn                                           SnmpAdminString,
    cfprApFabricVsanEpFcoeVlan                                       Gauge32,
    cfprApFabricVsanEpId                                             Gauge32,
    cfprApFabricVsanEpIfRole                                         CfprApFabricVnetEpIfRole,
    cfprApFabricVsanEpIfType                                         CfprApNetworkVnetEpIfType,
    cfprApFabricVsanEpLocale                                         CfprApFabricVnetEpLocale,
    cfprApFabricVsanEpName                                           SnmpAdminString,
    cfprApFabricVsanEpOperState                                      CfprApFabricVsanOperState,
    cfprApFabricVsanEpPeerDn                                         SnmpAdminString,
    cfprApFabricVsanEpPolicyOwner                                    CfprApFabricVnetEpPolicyOwner,
    cfprApFabricVsanEpSwitchId                                       CfprApNetworkSwitchId,
    cfprApFabricVsanEpTransport                                      CfprApFabricAVsanTransport,
    cfprApFabricVsanEpType                                           CfprApFabricAVsanType,
    cfprApFabricVsanEpZoningState                                    CfprApFabricZoningState
}

cfprApFabricVsanEpInstanceId OBJECT-TYPE
    SYNTAX       CfprApManagedObjectId
    MAX-ACCESS   not-accessible
    STATUS       current
    DESCRIPTION
        "Instance identifier of the managed object."
    ::= { cfprApFabricVsanEpEntry 1 }

cfprApFabricVsanEpDnData OBJECT-TYPE
    SYNTAX       CfprApManagedObjectDn
    MAX-ACCESS   read-only
    STATUS       current
    DESCRIPTION
        "Cisco Firepower fabric:VsanEp:dn managed object property"
    ::= { cfprApFabricVsanEpEntry 2 }

cfprApFabricVsanEpRn OBJECT-TYPE
    SYNTAX       SnmpAdminString
    MAX-ACCESS   read-only
    STATUS       current
    DESCRIPTION
        "Cisco Firepower fabric:VsanEp:rn managed object property"
    ::= { cfprApFabricVsanEpEntry 3 }

cfprApFabricVsanEpEpDn OBJECT-TYPE
    SYNTAX       SnmpAdminString
    MAX-ACCESS   read-only
    STATUS       current
    DESCRIPTION
        "Cisco Firepower fabric:VsanEp:epDn managed object property"
    ::= { cfprApFabricVsanEpEntry 4 }

cfprApFabricVsanEpFcoeVlan OBJECT-TYPE
    SYNTAX       Gauge32
    MAX-ACCESS   read-only
    STATUS       current
    DESCRIPTION
        "Cisco Firepower fabric:VsanEp:fcoeVlan managed object property"
    ::= { cfprApFabricVsanEpEntry 5 }

cfprApFabricVsanEpId OBJECT-TYPE
    SYNTAX       Gauge32
    MAX-ACCESS   read-only
    STATUS       current
    DESCRIPTION
        "Cisco Firepower fabric:VsanEp:id managed object property"
    ::= { cfprApFabricVsanEpEntry 6 }

cfprApFabricVsanEpIfRole OBJECT-TYPE
    SYNTAX       CfprApFabricVnetEpIfRole
    MAX-ACCESS   read-only
    STATUS       current
    DESCRIPTION
        "Cisco Firepower fabric:VsanEp:ifRole managed object property"
    ::= { cfprApFabricVsanEpEntry 7 }

cfprApFabricVsanEpIfType OBJECT-TYPE
    SYNTAX       CfprApNetworkVnetEpIfType
    MAX-ACCESS   read-only
    STATUS       current
    DESCRIPTION
        "Cisco Firepower fabric:VsanEp:ifType managed object property"
    ::= { cfprApFabricVsanEpEntry 8 }

cfprApFabricVsanEpLocale OBJECT-TYPE
    SYNTAX       CfprApFabricVnetEpLocale
    MAX-ACCESS   read-only
    STATUS       current
    DESCRIPTION
        "Cisco Firepower fabric:VsanEp:locale managed object property"
    ::= { cfprApFabricVsanEpEntry 9 }

cfprApFabricVsanEpName OBJECT-TYPE
    SYNTAX       SnmpAdminString
    MAX-ACCESS   read-only
    STATUS       current
    DESCRIPTION
        "Cisco Firepower fabric:VsanEp:name managed object property"
    ::= { cfprApFabricVsanEpEntry 10 }

cfprApFabricVsanEpOperState OBJECT-TYPE
    SYNTAX       CfprApFabricVsanOperState
    MAX-ACCESS   read-only
    STATUS       current
    DESCRIPTION
        "Cisco Firepower fabric:VsanEp:operState managed object property"
    ::= { cfprApFabricVsanEpEntry 11 }

cfprApFabricVsanEpPeerDn OBJECT-TYPE
    SYNTAX       SnmpAdminString
    MAX-ACCESS   read-only
    STATUS       current
    DESCRIPTION
        "Cisco Firepower fabric:VsanEp:peerDn managed object property"
    ::= { cfprApFabricVsanEpEntry 12 }

cfprApFabricVsanEpPolicyOwner OBJECT-TYPE
    SYNTAX       CfprApFabricVnetEpPolicyOwner
    MAX-ACCESS   read-only
    STATUS       current
    DESCRIPTION
        "Cisco Firepower fabric:VsanEp:policyOwner managed
        object property"
    ::= { cfprApFabricVsanEpEntry 13 }

cfprApFabricVsanEpSwitchId OBJECT-TYPE
    SYNTAX       CfprApNetworkSwitchId
    MAX-ACCESS   read-only
    STATUS       current
    DESCRIPTION
        "Cisco Firepower fabric:VsanEp:switchId managed object property"
    ::= { cfprApFabricVsanEpEntry 14 }

cfprApFabricVsanEpTransport OBJECT-TYPE
    SYNTAX       CfprApFabricAVsanTransport
    MAX-ACCESS   read-only
    STATUS       current
    DESCRIPTION
        "Cisco Firepower fabric:VsanEp:transport managed object property"
    ::= { cfprApFabricVsanEpEntry 15 }

cfprApFabricVsanEpType OBJECT-TYPE
    SYNTAX       CfprApFabricAVsanType
    MAX-ACCESS   read-only
    STATUS       current
    DESCRIPTION
        "Cisco Firepower fabric:VsanEp:type managed object property"
    ::= { cfprApFabricVsanEpEntry 16 }

cfprApFabricVsanEpZoningState OBJECT-TYPE
    SYNTAX       CfprApFabricZoningState
    MAX-ACCESS   read-only
    STATUS       current
    DESCRIPTION
        "Cisco Firepower fabric:VsanEp:zoningState managed
        object property"
    ::= { cfprApFabricVsanEpEntry 17 }

cfprApFabricVsanMembershipTable OBJECT-TYPE
    SYNTAX           SEQUENCE OF CfprApFabricVsanMembershipEntry
    MAX-ACCESS       not-accessible
    STATUS           current
    DESCRIPTION
        "Cisco Firepower fabric:VsanMembership managed object table"
    ::= { cfprApFabricObjects 128 }

cfprApFabricVsanMembershipEntry OBJECT-TYPE
    SYNTAX           CfprApFabricVsanMembershipEntry
    MAX-ACCESS       not-accessible
    STATUS           current
    DESCRIPTION
        "Entry for the cfprApFabricVsanMembershipTable table."
    INDEX { cfprApFabricVsanMembershipInstanceId }
    ::= { cfprApFabricVsanMembershipTable 1 }

CfprApFabricVsanMembershipEntry ::= SEQUENCE {
    cfprApFabricVsanMembershipInstanceId                             CfprApManagedObjectId,
    cfprApFabricVsanMembershipDn                                     CfprApManagedObjectDn,
    cfprApFabricVsanMembershipRn                                     SnmpAdminString,
    cfprApFabricVsanMembershipMemberStatus                           CfprApFabricMemberStatus,
    cfprApFabricVsanMembershipParentAdminState                       CfprApFabricAdminState,
    cfprApFabricVsanMembershipStateQual                              SnmpAdminString,
    cfprApFabricVsanMembershipVsanId                                 Gauge32
}

cfprApFabricVsanMembershipInstanceId OBJECT-TYPE
    SYNTAX       CfprApManagedObjectId
    MAX-ACCESS   not-accessible
    STATUS       current
    DESCRIPTION
        "Instance identifier of the managed object."
    ::= { cfprApFabricVsanMembershipEntry 1 }

cfprApFabricVsanMembershipDn OBJECT-TYPE
    SYNTAX       CfprApManagedObjectDn
    MAX-ACCESS   read-only
    STATUS       current
    DESCRIPTION
        "Cisco Firepower fabric:VsanMembership:dn managed object property"
    ::= { cfprApFabricVsanMembershipEntry 2 }

cfprApFabricVsanMembershipRn OBJECT-TYPE
    SYNTAX       SnmpAdminString
    MAX-ACCESS   read-only
    STATUS       current
    DESCRIPTION
        "Cisco Firepower fabric:VsanMembership:rn managed object property"
    ::= { cfprApFabricVsanMembershipEntry 3 }

cfprApFabricVsanMembershipMemberStatus OBJECT-TYPE
    SYNTAX       CfprApFabricMemberStatus
    MAX-ACCESS   read-only
    STATUS       current
    DESCRIPTION
        "Cisco Firepower fabric:VsanMembership:memberStatus
        managed object property"
    ::= { cfprApFabricVsanMembershipEntry 4 }

cfprApFabricVsanMembershipParentAdminState OBJECT-TYPE
    SYNTAX       CfprApFabricAdminState
    MAX-ACCESS   read-only
    STATUS       current
    DESCRIPTION
        "Cisco Firepower fabric:VsanMembership:parentAdminState
        managed object property"
    ::= { cfprApFabricVsanMembershipEntry 5 }

cfprApFabricVsanMembershipStateQual OBJECT-TYPE
    SYNTAX       SnmpAdminString
    MAX-ACCESS   read-only
    STATUS       current
    DESCRIPTION
        "Cisco Firepower fabric:VsanMembership:stateQual
        managed object property"
    ::= { cfprApFabricVsanMembershipEntry 6 }

cfprApFabricVsanMembershipVsanId OBJECT-TYPE
    SYNTAX       Gauge32
    MAX-ACCESS   read-only
    STATUS       current
    DESCRIPTION
        "Cisco Firepower fabric:VsanMembership:vsanId managed
        object property"
    ::= { cfprApFabricVsanMembershipEntry 7 }

cfprApFabricZoneIdUniverseTable OBJECT-TYPE
    SYNTAX           SEQUENCE OF CfprApFabricZoneIdUniverseEntry
    MAX-ACCESS       not-accessible
    STATUS           current
    DESCRIPTION
        "Cisco Firepower fabric:ZoneIdUniverse managed object table"
    ::= { cfprApFabricObjects 129 }

cfprApFabricZoneIdUniverseEntry OBJECT-TYPE
    SYNTAX           CfprApFabricZoneIdUniverseEntry
    MAX-ACCESS       not-accessible
    STATUS           current
    DESCRIPTION
        "Entry for the cfprApFabricZoneIdUniverseTable table."
    INDEX { cfprApFabricZoneIdUniverseInstanceId }
    ::= { cfprApFabricZoneIdUniverseTable 1 }

CfprApFabricZoneIdUniverseEntry ::= SEQUENCE {
    cfprApFabricZoneIdUniverseInstanceId                             CfprApManagedObjectId,
    cfprApFabricZoneIdUniverseDn                                     CfprApManagedObjectDn,
    cfprApFabricZoneIdUniverseRn                                     SnmpAdminString
}

cfprApFabricZoneIdUniverseInstanceId OBJECT-TYPE
    SYNTAX       CfprApManagedObjectId
    MAX-ACCESS   not-accessible
    STATUS       current
    DESCRIPTION
        "Instance identifier of the managed object."
    ::= { cfprApFabricZoneIdUniverseEntry 1 }

cfprApFabricZoneIdUniverseDn OBJECT-TYPE
    SYNTAX       CfprApManagedObjectDn
    MAX-ACCESS   read-only
    STATUS       current
    DESCRIPTION
        "Cisco Firepower fabric:ZoneIdUniverse:dn managed object property"
    ::= { cfprApFabricZoneIdUniverseEntry 2 }

cfprApFabricZoneIdUniverseRn OBJECT-TYPE
    SYNTAX       SnmpAdminString
    MAX-ACCESS   read-only
    STATUS       current
    DESCRIPTION
        "Cisco Firepower fabric:ZoneIdUniverse:rn managed object property"
    ::= { cfprApFabricZoneIdUniverseEntry 3 }

END
