-- *********************************************************************
-- CISCO-FIREPOWER-AP-IMGPROV-MIB.my
-- 
-- MIB representation of the Cisco Firepower
-- IMGPROV management information model package
-- 
-- Created July 2022 by Charles Bullis
-- 
-- Copyright (c) 2005-2022 Cisco Systems, Inc. All rights reserved.
-- 
-- *********************************************************************

CISCO-FIREPOWER-AP-IMGPROV-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApPolicyPolicyOwner
        FROM CISCO-FIREPOWER-AP-TC-MIB;

cfprApImgprovObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        IMGPROV management information model package"
    ::= { ciscoFirepowerApMIBObjects 37 }

cfprApImgprovPolicyTable OBJECT-TYPE
    SYNTAX           SEQUENCE OF CfprApImgprovPolicyEntry
    MAX-ACCESS       not-accessible
    STATUS           current
    DESCRIPTION
        "Cisco Firepower imgprov:Policy managed object table"
    ::= { cfprApImgprovObjects 1 }

cfprApImgprovPolicyEntry OBJECT-TYPE
    SYNTAX           CfprApImgprovPolicyEntry
    MAX-ACCESS       not-accessible
    STATUS           current
    DESCRIPTION
        "Entry for the cfprApImgprovPolicyTable table."
    INDEX { cfprApImgprovPolicyInstanceId }
    ::= { cfprApImgprovPolicyTable 1 }

CfprApImgprovPolicyEntry ::= SEQUENCE {
    cfprApImgprovPolicyInstanceId                                    CfprApManagedObjectId,
    cfprApImgprovPolicyDn                                            CfprApManagedObjectDn,
    cfprApImgprovPolicyRn                                            SnmpAdminString,
    cfprApImgprovPolicyDescr                                         SnmpAdminString,
    cfprApImgprovPolicyIntId                                         SnmpAdminString,
    cfprApImgprovPolicyName                                          SnmpAdminString,
    cfprApImgprovPolicyPolicyLevel                                   Gauge32,
    cfprApImgprovPolicyPolicyOwner                                   CfprApPolicyPolicyOwner
}

cfprApImgprovPolicyInstanceId OBJECT-TYPE
    SYNTAX       CfprApManagedObjectId
    MAX-ACCESS   not-accessible
    STATUS       current
    DESCRIPTION
        "Instance identifier of the managed object."
    ::= { cfprApImgprovPolicyEntry 1 }

cfprApImgprovPolicyDn OBJECT-TYPE
    SYNTAX       CfprApManagedObjectDn
    MAX-ACCESS   read-only
    STATUS       current
    DESCRIPTION
        "Cisco Firepower imgprov:Policy:dn managed object property"
    ::= { cfprApImgprovPolicyEntry 2 }

cfprApImgprovPolicyRn OBJECT-TYPE
    SYNTAX       SnmpAdminString
    MAX-ACCESS   read-only
    STATUS       current
    DESCRIPTION
        "Cisco Firepower imgprov:Policy:rn managed object property"
    ::= { cfprApImgprovPolicyEntry 3 }

cfprApImgprovPolicyDescr OBJECT-TYPE
    SYNTAX       SnmpAdminString
    MAX-ACCESS   read-only
    STATUS       current
    DESCRIPTION
        "Cisco Firepower imgprov:Policy:descr managed object property"
    ::= { cfprApImgprovPolicyEntry 4 }

cfprApImgprovPolicyIntId OBJECT-TYPE
    SYNTAX       SnmpAdminString
    MAX-ACCESS   read-only
    STATUS       current
    DESCRIPTION
        "Cisco Firepower imgprov:Policy:intId managed object property"
    ::= { cfprApImgprovPolicyEntry 5 }

cfprApImgprovPolicyName OBJECT-TYPE
    SYNTAX       SnmpAdminString
    MAX-ACCESS   read-only
    STATUS       current
    DESCRIPTION
        "Cisco Firepower imgprov:Policy:name managed object property"
    ::= { cfprApImgprovPolicyEntry 6 }

cfprApImgprovPolicyPolicyLevel OBJECT-TYPE
    SYNTAX       Gauge32
    MAX-ACCESS   read-only
    STATUS       current
    DESCRIPTION
        "Cisco Firepower imgprov:Policy:policyLevel managed
        object property"
    ::= { cfprApImgprovPolicyEntry 7 }

cfprApImgprovPolicyPolicyOwner OBJECT-TYPE
    SYNTAX       CfprApPolicyPolicyOwner
    MAX-ACCESS   read-only
    STATUS       current
    DESCRIPTION
        "Cisco Firepower imgprov:Policy:policyOwner managed
        object property"
    ::= { cfprApImgprovPolicyEntry 8 }

cfprApImgprovTargetTable OBJECT-TYPE
    SYNTAX           SEQUENCE OF CfprApImgprovTargetEntry
    MAX-ACCESS       not-accessible
    STATUS           current
    DESCRIPTION
        "Cisco Firepower imgprov:Target managed object table"
    ::= { cfprApImgprovObjects 2 }

cfprApImgprovTargetEntry OBJECT-TYPE
    SYNTAX           CfprApImgprovTargetEntry
    MAX-ACCESS       not-accessible
    STATUS           current
    DESCRIPTION
        "Entry for the cfprApImgprovTargetTable table."
    INDEX { cfprApImgprovTargetInstanceId }
    ::= { cfprApImgprovTargetTable 1 }

CfprApImgprovTargetEntry ::= SEQUENCE {
    cfprApImgprovTargetInstanceId                                    CfprApManagedObjectId,
    cfprApImgprovTargetDn                                            CfprApManagedObjectDn,
    cfprApImgprovTargetRn                                            SnmpAdminString,
    cfprApImgprovTargetName                                          SnmpAdminString
}

cfprApImgprovTargetInstanceId OBJECT-TYPE
    SYNTAX       CfprApManagedObjectId
    MAX-ACCESS   not-accessible
    STATUS       current
    DESCRIPTION
        "Instance identifier of the managed object."
    ::= { cfprApImgprovTargetEntry 1 }

cfprApImgprovTargetDn OBJECT-TYPE
    SYNTAX       CfprApManagedObjectDn
    MAX-ACCESS   read-only
    STATUS       current
    DESCRIPTION
        "Cisco Firepower imgprov:Target:dn managed object property"
    ::= { cfprApImgprovTargetEntry 2 }

cfprApImgprovTargetRn OBJECT-TYPE
    SYNTAX       SnmpAdminString
    MAX-ACCESS   read-only
    STATUS       current
    DESCRIPTION
        "Cisco Firepower imgprov:Target:rn managed object property"
    ::= { cfprApImgprovTargetEntry 3 }

cfprApImgprovTargetName OBJECT-TYPE
    SYNTAX       SnmpAdminString
    MAX-ACCESS   read-only
    STATUS       current
    DESCRIPTION
        "Cisco Firepower imgprov:Target:name managed object property"
    ::= { cfprApImgprovTargetEntry 4 }

END
