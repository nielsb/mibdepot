-- *********************************************************************
-- CISCO-FIREPOWER-AP-STORAGE-MIB.my
-- 
-- MIB representation of the Cisco Firepower
-- STORAGE management information model package
-- 
-- Created July 2022 by Charles Bullis
-- 
-- Copyright (c) 2005-2022 Cisco Systems, Inc. All rights reserved.
-- 
-- *********************************************************************

CISCO-FIREPOWER-AP-STORAGE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApAaaConfigState,
    CfprApConditionRemoteInvRslt,
    CfprApEquipmentOperability,
    CfprApEquipmentPowerState,
    CfprApEquipmentPresence,
    CfprApEquipmentSensorThresholdStatus,
    CfprApFabricZoningState,
    CfprApFsmCompletion,
    CfprApFsmFlags,
    CfprApFsmFsmStageStatus,
    CfprApFsmLifecycle,
    CfprApPolicyPolicyOwner,
    CfprApStorageAccessType,
    CfprApStorageActualWriteType,
    CfprApStorageBatteryType,
    CfprApStorageBbuStatus,
    CfprApStorageBootableType,
    CfprApStorageCacheType,
    CfprApStorageConfiguration,
    CfprApStorageConfiguredWriteType,
    CfprApStorageConnectionProtocol,
    CfprApStorageControllerFaultMonitoring,
    CfprApStorageControllerId,
    CfprApStorageControllerStatus,
    CfprApStorageControllerType,
    CfprApStorageDisklessAction,
    CfprApStorageEpAccess,
    CfprApStorageEtherIfVlanType,
    CfprApStorageFFCardHealth,
    CfprApStorageFFCardMode,
    CfprApStorageFFCardSizeMismatch,
    CfprApStorageFFCardState,
    CfprApStorageFFCardSync,
    CfprApStorageFFCardWriteEnable,
    CfprApStorageFFControllerHealth,
    CfprApStorageFFControllerState,
    CfprApStorageFFDriveRemovable,
    CfprApStorageFFDriveState,
    CfprApStorageFFDriveType,
    CfprApStorageFFDriveVisible,
    CfprApStorageFFFormatRunning,
    CfprApStorageFFHasError,
    CfprApStorageFFRAIDHealth,
    CfprApStorageFFRAIDState,
    CfprApStorageFFRWType,
    CfprApStorageFFRaidSyncSupport,
    CfprApStorageFFSlotENUM,
    CfprApStorageFFType,
    CfprApStorageFileSystemStatus,
    CfprApStorageFlexFlashControllerId,
    CfprApStorageIOType,
    CfprApStorageKeyType,
    CfprApStorageLearnCycleRequested,
    CfprApStorageLearnMode,
    CfprApStorageLinkSpeed,
    CfprApStorageLocalDiskConfigFlexFlashRAIDReportingState,
    CfprApStorageLocalDiskConfigFlexFlashState,
    CfprApStorageLocalDiskMode,
    CfprApStorageLocalDiskPartitionType,
    CfprApStorageLunType,
    CfprApStorageOperatingModeType,
    CfprApStorageOperationRequestType,
    CfprApStorageOperationState,
    CfprApStorageOperationStateType,
    CfprApStoragePDriveStatus,
    CfprApStoragePowerState,
    CfprApStorageProtocol,
    CfprApStorageRaidBatteryOperabilityQualifier,
    CfprApStorageReadType,
    CfprApStorageSystemFsmCurrentFsm,
    CfprApStorageSystemFsmStageName,
    CfprApStorageSystemFsmTaskItem,
    CfprApStorageTechnology,
    CfprApStorageVDriveState,
    CfprApStorageVsanRefSwitchId,
    CfprApVnicConfigIssues
        FROM CISCO-FIREPOWER-AP-TC-MIB;

cfprApStorageObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        STORAGE management information model package"
    ::= { ciscoFirepowerApMIBObjects 74 }

cfprApStorageAuthKeyTable OBJECT-TYPE
    SYNTAX           SEQUENCE OF CfprApStorageAuthKeyEntry
    MAX-ACCESS       not-accessible
    STATUS           current
    DESCRIPTION
        "Cisco Firepower storage:AuthKey managed object table"
    ::= { cfprApStorageObjects 1 }

cfprApStorageAuthKeyEntry OBJECT-TYPE
    SYNTAX           CfprApStorageAuthKeyEntry
    MAX-ACCESS       not-accessible
    STATUS           current
    DESCRIPTION
        "Entry for the cfprApStorageAuthKeyTable table."
    INDEX { cfprApStorageAuthKeyInstanceId }
    ::= { cfprApStorageAuthKeyTable 1 }

CfprApStorageAuthKeyEntry ::= SEQUENCE {
    cfprApStorageAuthKeyInstanceId                                   CfprApManagedObjectId,
    cfprApStorageAuthKeyDn                                           CfprApManagedObjectDn,
    cfprApStorageAuthKeyRn                                           SnmpAdminString,
    cfprApStorageAuthKeyDescr                                        SnmpAdminString,
    cfprApStorageAuthKeyIntId                                        SnmpAdminString,
    cfprApStorageAuthKeyName                                         SnmpAdminString,
    cfprApStorageAuthKeyPassword                                     SnmpAdminString,
    cfprApStorageAuthKeyPolicyLevel                                  Gauge32,
    cfprApStorageAuthKeyPolicyOwner                                  CfprApPolicyPolicyOwner,
    cfprApStorageAuthKeyType                                         CfprApStorageKeyType,
    cfprApStorageAuthKeyUserId                                       SnmpAdminString
}

cfprApStorageAuthKeyInstanceId OBJECT-TYPE
    SYNTAX       CfprApManagedObjectId
    MAX-ACCESS   not-accessible
    STATUS       current
    DESCRIPTION
        "Instance identifier of the managed object."
    ::= { cfprApStorageAuthKeyEntry 1 }

cfprApStorageAuthKeyDn OBJECT-TYPE
    SYNTAX       CfprApManagedObjectDn
    MAX-ACCESS   read-only
    STATUS       current
    DESCRIPTION
        "Cisco Firepower storage:AuthKey:dn managed object property"
    ::= { cfprApStorageAuthKeyEntry 2 }

cfprApStorageAuthKeyRn OBJECT-TYPE
    SYNTAX       SnmpAdminString
    MAX-ACCESS   read-only
    STATUS       current
    DESCRIPTION
        "Cisco Firepower storage:AuthKey:rn managed object property"
    ::= { cfprApStorageAuthKeyEntry 3 }

cfprApStorageAuthKeyDescr OBJECT-TYPE
    SYNTAX       SnmpAdminString
    MAX-ACCESS   read-only
    STATUS       current
    DESCRIPTION
        "Cisco Firepower storage:AuthKey:descr managed object property"
    ::= { cfprApStorageAuthKeyEntry 4 }

cfprApStorageAuthKeyIntId OBJECT-TYPE
    SYNTAX       SnmpAdminString
    MAX-ACCESS   read-only
    STATUS       current
    DESCRIPTION
        "Cisco Firepower storage:AuthKey:intId managed object property"
    ::= { cfprApStorageAuthKeyEntry 5 }

cfprApStorageAuthKeyName OBJECT-TYPE
    SYNTAX       SnmpAdminString
    MAX-ACCESS   read-only
    STATUS       current
    DESCRIPTION
        "Cisco Firepower storage:AuthKey:name managed object property"
    ::= { cfprApStorageAuthKeyEntry 6 }

cfprApStorageAuthKeyPassword OBJECT-TYPE
    SYNTAX       SnmpAdminString
    MAX-ACCESS   read-only
    STATUS       current
    DESCRIPTION
        "Cisco Firepower storage:AuthKey:password managed object property"
    ::= { cfprApStorageAuthKeyEntry 7 }

cfprApStorageAuthKeyPolicyLevel OBJECT-TYPE
    SYNTAX       Gauge32
    MAX-ACCESS   read-only
    STATUS       current
    DESCRIPTION
        "Cisco Firepower storage:AuthKey:policyLevel managed
        object property"
    ::= { cfprApStorageAuthKeyEntry 8 }

cfprApStorageAuthKeyPolicyOwner OBJECT-TYPE
    SYNTAX       CfprApPolicyPolicyOwner
    MAX-ACCESS   read-only
    STATUS       current
    DESCRIPTION
        "Cisco Firepower storage:AuthKey:policyOwner managed
        object property"
    ::= { cfprApStorageAuthKeyEntry 9 }

cfprApStorageAuthKeyType OBJECT-TYPE
    SYNTAX       CfprApStorageKeyType
    MAX-ACCESS   read-only
    STATUS       current
    DESCRIPTION
        "Cisco Firepower storage:AuthKey:type managed object property"
    ::= { cfprApStorageAuthKeyEntry 10 }

cfprApStorageAuthKeyUserId OBJECT-TYPE
    SYNTAX       SnmpAdminString
    MAX-ACCESS   read-only
    STATUS       current
    DESCRIPTION
        "Cisco Firepower storage:AuthKey:userId managed object property"
    ::= { cfprApStorageAuthKeyEntry 11 }

cfprApStorageControllerTable OBJECT-TYPE
    SYNTAX           SEQUENCE OF CfprApStorageControllerEntry
    MAX-ACCESS       not-accessible
    STATUS           current
    DESCRIPTION
        "Cisco Firepower storage:Controller managed object table"
    ::= { cfprApStorageObjects 4 }

cfprApStorageControllerEntry OBJECT-TYPE
    SYNTAX           CfprApStorageControllerEntry
    MAX-ACCESS       not-accessible
    STATUS           current
    DESCRIPTION
        "Entry for the cfprApStorageControllerTable table."
    INDEX { cfprApStorageControllerInstanceId }
    ::= { cfprApStorageControllerTable 1 }

CfprApStorageControllerEntry ::= SEQUENCE {
    cfprApStorageControllerInstanceId                                CfprApManagedObjectId,
    cfprApStorageControllerDn                                        CfprApManagedObjectDn,
    cfprApStorageControllerRn                                        SnmpAdminString,
    cfprApStorageControllerControllerStatus                          CfprApStorageControllerStatus,
    cfprApStorageControllerDeviceRaidSupport                         SnmpAdminString,
    cfprApStorageControllerFaultMonitoring                           CfprApStorageControllerFaultMonitoring,
    cfprApStorageControllerHwRevision                                SnmpAdminString,
    cfprApStorageControllerId                                        CfprApStorageControllerId,
    cfprApStorageControllerLc                                        CfprApFsmLifecycle,
    cfprApStorageControllerLocationDn                                SnmpAdminString,
    cfprApStorageControllerModel                                     SnmpAdminString,
    cfprApStorageControllerOobControllerId                           Gauge32,
    cfprApStorageControllerOobInterfaceSupported                     TruthValue,
    cfprApStorageControllerOperQualifierReason                       SnmpAdminString,
    cfprApStorageControllerOperState                                 CfprApEquipmentOperability,
    cfprApStorageControllerOperability                               CfprApEquipmentOperability,
    cfprApStorageControllerPartNumber                                SnmpAdminString,
    cfprApStorageControllerPciAddr                                   SnmpAdminString,
    cfprApStorageControllerPciSlot                                   SnmpAdminString,
    cfprApStorageControllerPerf                                      CfprApEquipmentSensorThresholdStatus,
    cfprApStorageControllerPower                                     CfprApEquipmentPowerState,
    cfprApStorageControllerPresence                                  CfprApEquipmentPresence,
    cfprApStorageControllerRaidSupport                               SnmpAdminString,
    cfprApStorageControllerRebuildRate                               Gauge32,
    cfprApStorageControllerRevision                                  SnmpAdminString,
    cfprApStorageControllerSerial                                    SnmpAdminString,
    cfprApStorageControllerThermal                                   CfprApEquipmentSensorThresholdStatus,
    cfprApStorageControllerType                                      CfprApStorageControllerType,
    cfprApStorageControllerVendor                                    SnmpAdminString,
    cfprApStorageControllerVid                                       SnmpAdminString,
    cfprApStorageControllerVoltage                                   CfprApEquipmentSensorThresholdStatus
}

cfprApStorageControllerInstanceId OBJECT-TYPE
    SYNTAX       CfprApManagedObjectId
    MAX-ACCESS   not-accessible
    STATUS       current
    DESCRIPTION
        "Instance identifier of the managed object."
    ::= { cfprApStorageControllerEntry 1 }

cfprApStorageControllerDn OBJECT-TYPE
    SYNTAX       CfprApManagedObjectDn
    MAX-ACCESS   read-only
    STATUS       current
    DESCRIPTION
        "Cisco Firepower storage:Controller:dn managed object property"
    ::= { cfprApStorageControllerEntry 2 }

cfprApStorageControllerRn OBJECT-TYPE
    SYNTAX       SnmpAdminString
    MAX-ACCESS   read-only
    STATUS       current
    DESCRIPTION
        "Cisco Firepower storage:Controller:rn managed object property"
    ::= { cfprApStorageControllerEntry 3 }

cfprApStorageControllerControllerStatus OBJECT-TYPE
    SYNTAX       CfprApStorageControllerStatus
    MAX-ACCESS   read-only
    STATUS       current
    DESCRIPTION
        "Cisco Firepower storage:Controller:controllerStatus
        managed object property"
    ::= { cfprApStorageControllerEntry 4 }

cfprApStorageControllerDeviceRaidSupport OBJECT-TYPE
    SYNTAX       SnmpAdminString
    MAX-ACCESS   read-only
    STATUS       current
    DESCRIPTION
        "Cisco Firepower storage:Controller:deviceRaidSupport
        managed object property"
    ::= { cfprApStorageControllerEntry 5 }

cfprApStorageControllerFaultMonitoring OBJECT-TYPE
    SYNTAX       CfprApStorageControllerFaultMonitoring
    MAX-ACCESS   read-only
    STATUS       current
    DESCRIPTION
        "Cisco Firepower storage:Controller:faultMonitoring
        managed object property"
    ::= { cfprApStorageControllerEntry 6 }

cfprApStorageControllerHwRevision OBJECT-TYPE
    SYNTAX       SnmpAdminString
    MAX-ACCESS   read-only
    STATUS       current
    DESCRIPTION
        "Cisco Firepower storage:Controller:hwRevision
        managed object property"
    ::= { cfprApStorageControllerEntry 7 }

cfprApStorageControllerId OBJECT-TYPE
    SYNTAX       CfprApStorageControllerId
    MAX-ACCESS   read-only
    STATUS       current
    DESCRIPTION
        "Cisco Firepower storage:Controller:id managed object property"
    ::= { cfprApStorageControllerEntry 8 }

cfprApStorageControllerLc OBJECT-TYPE
    SYNTAX       CfprApFsmLifecycle
    MAX-ACCESS   read-only
    STATUS       current
    DESCRIPTION
        "Cisco Firepower storage:Controller:lc managed object property"
    ::= { cfprApStorageControllerEntry 9 }

cfprApStorageControllerLocationDn OBJECT-TYPE
    SYNTAX       SnmpAdminString
    MAX-ACCESS   read-only
    STATUS       current
    DESCRIPTION
        "Cisco Firepower storage:Controller:locationDn
        managed object property"
    ::= { cfprApStorageControllerEntry 10 }

cfprApStorageControllerModel OBJECT-TYPE
    SYNTAX       SnmpAdminString
    MAX-ACCESS   read-only
    STATUS       current
    DESCRIPTION
        "Cisco Firepower storage:Controller:model managed object property"
    ::= { cfprApStorageControllerEntry 11 }

cfprApStorageControllerOobControllerId OBJECT-TYPE
    SYNTAX       Gauge32
    MAX-ACCESS   read-only
    STATUS       current
    DESCRIPTION
        "Cisco Firepower storage:Controller:oobControllerId
        managed object property"
    ::= { cfprApStorageControllerEntry 12 }

cfprApStorageControllerOobInterfaceSupported OBJECT-TYPE
    SYNTAX       TruthValue
    MAX-ACCESS   read-only
    STATUS       current
    DESCRIPTION
        "Cisco Firepower storage:Controller:oobInterfaceSupported
        managed object property"
    ::= { cfprApStorageControllerEntry 13 }

cfprApStorageControllerOperQualifierReason OBJECT-TYPE
    SYNTAX       SnmpAdminString
    MAX-ACCESS   read-only
    STATUS       current
    DESCRIPTION
        "Cisco Firepower storage:Controller:operQualifierReason
        managed object property"
    ::= { cfprApStorageControllerEntry 14 }

cfprApStorageControllerOperState OBJECT-TYPE
    SYNTAX       CfprApEquipmentOperability
    MAX-ACCESS   read-only
    STATUS       current
    DESCRIPTION
        "Cisco Firepower storage:Controller:operState managed
        object property"
    ::= { cfprApStorageControllerEntry 15 }

cfprApStorageControllerOperability OBJECT-TYPE
    SYNTAX       CfprApEquipmentOperability
    MAX-ACCESS   read-only
    STATUS       current
    DESCRIPTION
        "Cisco Firepower storage:Controller:operability
        managed object property"
    ::= { cfprApStorageControllerEntry 16 }

cfprApStorageControllerPartNumber OBJECT-TYPE
    SYNTAX       SnmpAdminString
    MAX-ACCESS   read-only
    STATUS       current
    DESCRIPTION
        "Cisco Firepower storage:Controller:partNumber
        managed object property"
    ::= { cfprApStorageControllerEntry 17 }

cfprApStorageControllerPciAddr OBJECT-TYPE
    SYNTAX       SnmpAdminString
    MAX-ACCESS   read-only
    STATUS       current
    DESCRIPTION
        "Cisco Firepower storage:Controller:pciAddr managed
        object property"
    ::= { cfprApStorageControllerEntry 18 }

cfprApStorageControllerPciSlot OBJECT-TYPE
    SYNTAX       SnmpAdminString
    MAX-ACCESS   read-only
    STATUS       current
    DESCRIPTION
        "Cisco Firepower storage:Controller:pciSlot managed
        object property"
    ::= { cfprApStorageControllerEntry 19 }

cfprApStorageControllerPerf OBJECT-TYPE
    SYNTAX       CfprApEquipmentSensorThresholdStatus
    MAX-ACCESS   read-only
    STATUS       current
    DESCRIPTION
        "Cisco Firepower storage:Controller:perf managed object property"
    ::= { cfprApStorageControllerEntry 20 }

cfprApStorageControllerPower OBJECT-TYPE
    SYNTAX       CfprApEquipmentPowerState
    MAX-ACCESS   read-only
    STATUS       current
    DESCRIPTION
        "Cisco Firepower storage:Controller:power managed object property"
    ::= { cfprApStorageControllerEntry 21 }

cfprApStorageControllerPresence OBJECT-TYPE
    SYNTAX       CfprApEquipmentPresence
    MAX-ACCESS   read-only
    STATUS       current
    DESCRIPTION
        "Cisco Firepower storage:Controller:presence managed
        object property"
    ::= { cfprApStorageControllerEntry 22 }

cfprApStorageControllerRaidSupport OBJECT-TYPE
    SYNTAX       SnmpAdminString
    MAX-ACCESS   read-only
    STATUS       current
    DESCRIPTION
        "Cisco Firepower storage:Controller:raidSupport
        managed object property"
    ::= { cfprApStorageControllerEntry 23 }

cfprApStorageControllerRebuildRate OBJECT-TYPE
    SYNTAX       Gauge32
    MAX-ACCESS   read-only
    STATUS       current
    DESCRIPTION
        "Cisco Firepower storage:Controller:rebuildRate
        managed object property"
    ::= { cfprApStorageControllerEntry 24 }

cfprApStorageControllerRevision OBJECT-TYPE
    SYNTAX       SnmpAdminString
    MAX-ACCESS   read-only
    STATUS       current
    DESCRIPTION
        "Cisco Firepower storage:Controller:revision managed
        object property"
    ::= { cfprApStorageControllerEntry 25 }

cfprApStorageControllerSerial OBJECT-TYPE
    SYNTAX       SnmpAdminString
    MAX-ACCESS   read-only
    STATUS       current
    DESCRIPTION
        "Cisco Firepower storage:Controller:serial managed
        object property"
    ::= { cfprApStorageControllerEntry 26 }

cfprApStorageControllerThermal OBJECT-TYPE
    SYNTAX       CfprApEquipmentSensorThresholdStatus
    MAX-ACCESS   read-only
    STATUS       current
    DESCRIPTION
        "Cisco Firepower storage:Controller:thermal managed
        object property"
    ::= { cfprApStorageControllerEntry 27 }

cfprApStorageControllerType OBJECT-TYPE
    SYNTAX       CfprApStorageControllerType
    MAX-ACCESS   read-only
    STATUS       current
    DESCRIPTION
        "Cisco Firepower storage:Controller:type managed object property"
    ::= { cfprApStorageControllerEntry 28 }

cfprApStorageControllerVendor OBJECT-TYPE
    SYNTAX       SnmpAdminString
    MAX-ACCESS   read-only
    STATUS       current
    DESCRIPTION
        "Cisco Firepower storage:Controller:vendor managed
        object property"
    ::= { cfprApStorageControllerEntry 29 }

cfprApStorageControllerVid OBJECT-TYPE
    SYNTAX       SnmpAdminString
    MAX-ACCESS   read-only
    STATUS       current
    DESCRIPTION
        "Cisco Firepower storage:Controller:vid managed object property"
    ::= { cfprApStorageControllerEntry 30 }

cfprApStorageControllerVoltage OBJECT-TYPE
    SYNTAX       CfprApEquipmentSensorThresholdStatus
    MAX-ACCESS   read-only
    STATUS       current
    DESCRIPTION
        "Cisco Firepower storage:Controller:voltage managed
        object property"
    ::= { cfprApStorageControllerEntry 31 }

cfprApStorageDomainEpTable OBJECT-TYPE
    SYNTAX           SEQUENCE OF CfprApStorageDomainEpEntry
    MAX-ACCESS       not-accessible
    STATUS           current
    DESCRIPTION
        "Cisco Firepower storage:DomainEp managed object table"
    ::= { cfprApStorageObjects 5 }

cfprApStorageDomainEpEntry OBJECT-TYPE
    SYNTAX           CfprApStorageDomainEpEntry
    MAX-ACCESS       not-accessible
    STATUS           current
    DESCRIPTION
        "Entry for the cfprApStorageDomainEpTable table."
    INDEX { cfprApStorageDomainEpInstanceId }
    ::= { cfprApStorageDomainEpTable 1 }

CfprApStorageDomainEpEntry ::= SEQUENCE {
    cfprApStorageDomainEpInstanceId                                  CfprApManagedObjectId,
    cfprApStorageDomainEpDn                                          CfprApManagedObjectDn,
    cfprApStorageDomainEpRn                                          SnmpAdminString
}

cfprApStorageDomainEpInstanceId OBJECT-TYPE
    SYNTAX       CfprApManagedObjectId
    MAX-ACCESS   not-accessible
    STATUS       current
    DESCRIPTION
        "Instance identifier of the managed object."
    ::= { cfprApStorageDomainEpEntry 1 }

cfprApStorageDomainEpDn OBJECT-TYPE
    SYNTAX       CfprApManagedObjectDn
    MAX-ACCESS   read-only
    STATUS       current
    DESCRIPTION
        "Cisco Firepower storage:DomainEp:dn managed object property"
    ::= { cfprApStorageDomainEpEntry 2 }

cfprApStorageDomainEpRn OBJECT-TYPE
    SYNTAX       SnmpAdminString
    MAX-ACCESS   read-only
    STATUS       current
    DESCRIPTION
        "Cisco Firepower storage:DomainEp:rn managed object property"
    ::= { cfprApStorageDomainEpEntry 3 }

cfprApStorageDriveTable OBJECT-TYPE
    SYNTAX           SEQUENCE OF CfprApStorageDriveEntry
    MAX-ACCESS       not-accessible
    STATUS           current
    DESCRIPTION
        "Cisco Firepower storage:Drive managed object table"
    ::= { cfprApStorageObjects 6 }

cfprApStorageDriveEntry OBJECT-TYPE
    SYNTAX           CfprApStorageDriveEntry
    MAX-ACCESS       not-accessible
    STATUS           current
    DESCRIPTION
        "Entry for the cfprApStorageDriveTable table."
    INDEX { cfprApStorageDriveInstanceId }
    ::= { cfprApStorageDriveTable 1 }

CfprApStorageDriveEntry ::= SEQUENCE {
    cfprApStorageDriveInstanceId                                     CfprApManagedObjectId,
    cfprApStorageDriveDn                                             CfprApManagedObjectDn,
    cfprApStorageDriveRn                                             SnmpAdminString,
    cfprApStorageDriveId                                             Gauge32,
    cfprApStorageDriveModel                                          SnmpAdminString,
    cfprApStorageDrivePciAddr                                        SnmpAdminString,
    cfprApStorageDriveRevision                                       SnmpAdminString,
    cfprApStorageDriveSerial                                         SnmpAdminString,
    cfprApStorageDriveVendor                                         SnmpAdminString
}

cfprApStorageDriveInstanceId OBJECT-TYPE
    SYNTAX       CfprApManagedObjectId
    MAX-ACCESS   not-accessible
    STATUS       current
    DESCRIPTION
        "Instance identifier of the managed object."
    ::= { cfprApStorageDriveEntry 1 }

cfprApStorageDriveDn OBJECT-TYPE
    SYNTAX       CfprApManagedObjectDn
    MAX-ACCESS   read-only
    STATUS       current
    DESCRIPTION
        "Cisco Firepower storage:Drive:dn managed object property"
    ::= { cfprApStorageDriveEntry 2 }

cfprApStorageDriveRn OBJECT-TYPE
    SYNTAX       SnmpAdminString
    MAX-ACCESS   read-only
    STATUS       current
    DESCRIPTION
        "Cisco Firepower storage:Drive:rn managed object property"
    ::= { cfprApStorageDriveEntry 3 }

cfprApStorageDriveId OBJECT-TYPE
    SYNTAX       Gauge32
    MAX-ACCESS   read-only
    STATUS       current
    DESCRIPTION
        "Cisco Firepower storage:Drive:id managed object property"
    ::= { cfprApStorageDriveEntry 4 }

cfprApStorageDriveModel OBJECT-TYPE
    SYNTAX       SnmpAdminString
    MAX-ACCESS   read-only
    STATUS       current
    DESCRIPTION
        "Cisco Firepower storage:Drive:model managed object property"
    ::= { cfprApStorageDriveEntry 5 }

cfprApStorageDrivePciAddr OBJECT-TYPE
    SYNTAX       SnmpAdminString
    MAX-ACCESS   read-only
    STATUS       current
    DESCRIPTION
        "Cisco Firepower storage:Drive:pciAddr managed object property"
    ::= { cfprApStorageDriveEntry 6 }

cfprApStorageDriveRevision OBJECT-TYPE
    SYNTAX       SnmpAdminString
    MAX-ACCESS   read-only
    STATUS       current
    DESCRIPTION
        "Cisco Firepower storage:Drive:revision managed object property"
    ::= { cfprApStorageDriveEntry 7 }

cfprApStorageDriveSerial OBJECT-TYPE
    SYNTAX       SnmpAdminString
    MAX-ACCESS   read-only
    STATUS       current
    DESCRIPTION
        "Cisco Firepower storage:Drive:serial managed object property"
    ::= { cfprApStorageDriveEntry 8 }

cfprApStorageDriveVendor OBJECT-TYPE
    SYNTAX       SnmpAdminString
    MAX-ACCESS   read-only
    STATUS       current
    DESCRIPTION
        "Cisco Firepower storage:Drive:vendor managed object property"
    ::= { cfprApStorageDriveEntry 9 }

cfprApStorageEnclosureTable OBJECT-TYPE
    SYNTAX           SEQUENCE OF CfprApStorageEnclosureEntry
    MAX-ACCESS       not-accessible
    STATUS           current
    DESCRIPTION
        "Cisco Firepower storage:Enclosure managed object table"
    ::= { cfprApStorageObjects 7 }

cfprApStorageEnclosureEntry OBJECT-TYPE
    SYNTAX           CfprApStorageEnclosureEntry
    MAX-ACCESS       not-accessible
    STATUS           current
    DESCRIPTION
        "Entry for the cfprApStorageEnclosureTable table."
    INDEX { cfprApStorageEnclosureInstanceId }
    ::= { cfprApStorageEnclosureTable 1 }

CfprApStorageEnclosureEntry ::= SEQUENCE {
    cfprApStorageEnclosureInstanceId                                 CfprApManagedObjectId,
    cfprApStorageEnclosureDn                                         CfprApManagedObjectDn,
    cfprApStorageEnclosureRn                                         SnmpAdminString,
    cfprApStorageEnclosureId                                         Gauge32,
    cfprApStorageEnclosureLc                                         CfprApFsmLifecycle,
    cfprApStorageEnclosureModel                                      SnmpAdminString,
    cfprApStorageEnclosureNumSlots                                   Gauge32,
    cfprApStorageEnclosureRevision                                   SnmpAdminString,
    cfprApStorageEnclosureSerial                                     SnmpAdminString,
    cfprApStorageEnclosureVendor                                     SnmpAdminString
}

cfprApStorageEnclosureInstanceId OBJECT-TYPE
    SYNTAX       CfprApManagedObjectId
    MAX-ACCESS   not-accessible
    STATUS       current
    DESCRIPTION
        "Instance identifier of the managed object."
    ::= { cfprApStorageEnclosureEntry 1 }

cfprApStorageEnclosureDn OBJECT-TYPE
    SYNTAX       CfprApManagedObjectDn
    MAX-ACCESS   read-only
    STATUS       current
    DESCRIPTION
        "Cisco Firepower storage:Enclosure:dn managed object property"
    ::= { cfprApStorageEnclosureEntry 2 }

cfprApStorageEnclosureRn OBJECT-TYPE
    SYNTAX       SnmpAdminString
    MAX-ACCESS   read-only
    STATUS       current
    DESCRIPTION
        "Cisco Firepower storage:Enclosure:rn managed object property"
    ::= { cfprApStorageEnclosureEntry 3 }

cfprApStorageEnclosureId OBJECT-TYPE
    SYNTAX       Gauge32
    MAX-ACCESS   read-only
    STATUS       current
    DESCRIPTION
        "Cisco Firepower storage:Enclosure:id managed object property"
    ::= { cfprApStorageEnclosureEntry 4 }

cfprApStorageEnclosureLc OBJECT-TYPE
    SYNTAX       CfprApFsmLifecycle
    MAX-ACCESS   read-only
    STATUS       current
    DESCRIPTION
        "Cisco Firepower storage:Enclosure:lc managed object property"
    ::= { cfprApStorageEnclosureEntry 5 }

cfprApStorageEnclosureModel OBJECT-TYPE
    SYNTAX       SnmpAdminString
    MAX-ACCESS   read-only
    STATUS       current
    DESCRIPTION
        "Cisco Firepower storage:Enclosure:model managed object property"
    ::= { cfprApStorageEnclosureEntry 6 }

cfprApStorageEnclosureNumSlots OBJECT-TYPE
    SYNTAX       Gauge32
    MAX-ACCESS   read-only
    STATUS       current
    DESCRIPTION
        "Cisco Firepower storage:Enclosure:numSlots managed
        object property"
    ::= { cfprApStorageEnclosureEntry 7 }

cfprApStorageEnclosureRevision OBJECT-TYPE
    SYNTAX       SnmpAdminString
    MAX-ACCESS   read-only
    STATUS       current
    DESCRIPTION
        "Cisco Firepower storage:Enclosure:revision managed
        object property"
    ::= { cfprApStorageEnclosureEntry 8 }

cfprApStorageEnclosureSerial OBJECT-TYPE
    SYNTAX       SnmpAdminString
    MAX-ACCESS   read-only
    STATUS       current
    DESCRIPTION
        "Cisco Firepower storage:Enclosure:serial managed object property"
    ::= { cfprApStorageEnclosureEntry 9 }

cfprApStorageEnclosureVendor OBJECT-TYPE
    SYNTAX       SnmpAdminString
    MAX-ACCESS   read-only
    STATUS       current
    DESCRIPTION
        "Cisco Firepower storage:Enclosure:vendor managed object property"
    ::= { cfprApStorageEnclosureEntry 10 }

cfprApStorageEpUserTable OBJECT-TYPE
    SYNTAX           SEQUENCE OF CfprApStorageEpUserEntry
    MAX-ACCESS       not-accessible
    STATUS           current
    DESCRIPTION
        "Cisco Firepower storage:EpUser managed object table"
    ::= { cfprApStorageObjects 8 }

cfprApStorageEpUserEntry OBJECT-TYPE
    SYNTAX           CfprApStorageEpUserEntry
    MAX-ACCESS       not-accessible
    STATUS           current
    DESCRIPTION
        "Entry for the cfprApStorageEpUserTable table."
    INDEX { cfprApStorageEpUserInstanceId }
    ::= { cfprApStorageEpUserTable 1 }

CfprApStorageEpUserEntry ::= SEQUENCE {
    cfprApStorageEpUserInstanceId                                    CfprApManagedObjectId,
    cfprApStorageEpUserDn                                            CfprApManagedObjectDn,
    cfprApStorageEpUserRn                                            SnmpAdminString,
    cfprApStorageEpUserConfigState                                   CfprApAaaConfigState,
    cfprApStorageEpUserConfigStatusMessage                           SnmpAdminString,
    cfprApStorageEpUserDescr                                         SnmpAdminString,
    cfprApStorageEpUserDomain                                        SnmpAdminString,
    cfprApStorageEpUserName                                          SnmpAdminString,
    cfprApStorageEpUserPriv                                          CfprApStorageEpAccess,
    cfprApStorageEpUserPwd                                           SnmpAdminString,
    cfprApStorageEpUserPwdSet                                        TruthValue
}

cfprApStorageEpUserInstanceId OBJECT-TYPE
    SYNTAX       CfprApManagedObjectId
    MAX-ACCESS   not-accessible
    STATUS       current
    DESCRIPTION
        "Instance identifier of the managed object."
    ::= { cfprApStorageEpUserEntry 1 }

cfprApStorageEpUserDn OBJECT-TYPE
    SYNTAX       CfprApManagedObjectDn
    MAX-ACCESS   read-only
    STATUS       current
    DESCRIPTION
        "Cisco Firepower storage:EpUser:dn managed object property"
    ::= { cfprApStorageEpUserEntry 2 }

cfprApStorageEpUserRn OBJECT-TYPE
    SYNTAX       SnmpAdminString
    MAX-ACCESS   read-only
    STATUS       current
    DESCRIPTION
        "Cisco Firepower storage:EpUser:rn managed object property"
    ::= { cfprApStorageEpUserEntry 3 }

cfprApStorageEpUserConfigState OBJECT-TYPE
    SYNTAX       CfprApAaaConfigState
    MAX-ACCESS   read-only
    STATUS       current
    DESCRIPTION
        "Cisco Firepower storage:EpUser:configState managed
        object property"
    ::= { cfprApStorageEpUserEntry 4 }

cfprApStorageEpUserConfigStatusMessage OBJECT-TYPE
    SYNTAX       SnmpAdminString
    MAX-ACCESS   read-only
    STATUS       current
    DESCRIPTION
        "Cisco Firepower storage:EpUser:configStatusMessage
        managed object property"
    ::= { cfprApStorageEpUserEntry 5 }

cfprApStorageEpUserDescr OBJECT-TYPE
    SYNTAX       SnmpAdminString
    MAX-ACCESS   read-only
    STATUS       current
    DESCRIPTION
        "Cisco Firepower storage:EpUser:descr managed object property"
    ::= { cfprApStorageEpUserEntry 6 }

cfprApStorageEpUserDomain OBJECT-TYPE
    SYNTAX       SnmpAdminString
    MAX-ACCESS   read-only
    STATUS       current
    DESCRIPTION
        "Cisco Firepower storage:EpUser:domain managed object property"
    ::= { cfprApStorageEpUserEntry 7 }

cfprApStorageEpUserName OBJECT-TYPE
    SYNTAX       SnmpAdminString
    MAX-ACCESS   read-only
    STATUS       current
    DESCRIPTION
        "Cisco Firepower storage:EpUser:name managed object property"
    ::= { cfprApStorageEpUserEntry 8 }

cfprApStorageEpUserPriv OBJECT-TYPE
    SYNTAX       CfprApStorageEpAccess
    MAX-ACCESS   read-only
    STATUS       current
    DESCRIPTION
        "Cisco Firepower storage:EpUser:priv managed object property"
    ::= { cfprApStorageEpUserEntry 9 }

cfprApStorageEpUserPwd OBJECT-TYPE
    SYNTAX       SnmpAdminString
    MAX-ACCESS   read-only
    STATUS       current
    DESCRIPTION
        "Cisco Firepower storage:EpUser:pwd managed object property"
    ::= { cfprApStorageEpUserEntry 10 }

cfprApStorageEpUserPwdSet OBJECT-TYPE
    SYNTAX       TruthValue
    MAX-ACCESS   read-only
    STATUS       current
    DESCRIPTION
        "Cisco Firepower storage:EpUser:pwdSet managed object property"
    ::= { cfprApStorageEpUserEntry 11 }

cfprApStorageEtherIfTable OBJECT-TYPE
    SYNTAX           SEQUENCE OF CfprApStorageEtherIfEntry
    MAX-ACCESS       not-accessible
    STATUS           current
    DESCRIPTION
        "Cisco Firepower storage:EtherIf managed object table"
    ::= { cfprApStorageObjects 9 }

cfprApStorageEtherIfEntry OBJECT-TYPE
    SYNTAX           CfprApStorageEtherIfEntry
    MAX-ACCESS       not-accessible
    STATUS           current
    DESCRIPTION
        "Entry for the cfprApStorageEtherIfTable table."
    INDEX { cfprApStorageEtherIfInstanceId }
    ::= { cfprApStorageEtherIfTable 1 }

CfprApStorageEtherIfEntry ::= SEQUENCE {
    cfprApStorageEtherIfInstanceId                                   CfprApManagedObjectId,
    cfprApStorageEtherIfDn                                           CfprApManagedObjectDn,
    cfprApStorageEtherIfRn                                           SnmpAdminString,
    cfprApStorageEtherIfName                                         SnmpAdminString,
    cfprApStorageEtherIfVlanType                                     CfprApStorageEtherIfVlanType
}

cfprApStorageEtherIfInstanceId OBJECT-TYPE
    SYNTAX       CfprApManagedObjectId
    MAX-ACCESS   not-accessible
    STATUS       current
    DESCRIPTION
        "Instance identifier of the managed object."
    ::= { cfprApStorageEtherIfEntry 1 }

cfprApStorageEtherIfDn OBJECT-TYPE
    SYNTAX       CfprApManagedObjectDn
    MAX-ACCESS   read-only
    STATUS       current
    DESCRIPTION
        "Cisco Firepower storage:EtherIf:dn managed object property"
    ::= { cfprApStorageEtherIfEntry 2 }

cfprApStorageEtherIfRn OBJECT-TYPE
    SYNTAX       SnmpAdminString
    MAX-ACCESS   read-only
    STATUS       current
    DESCRIPTION
        "Cisco Firepower storage:EtherIf:rn managed object property"
    ::= { cfprApStorageEtherIfEntry 3 }

cfprApStorageEtherIfName OBJECT-TYPE
    SYNTAX       SnmpAdminString
    MAX-ACCESS   read-only
    STATUS       current
    DESCRIPTION
        "Cisco Firepower storage:EtherIf:name managed object property"
    ::= { cfprApStorageEtherIfEntry 4 }

cfprApStorageEtherIfVlanType OBJECT-TYPE
    SYNTAX       CfprApStorageEtherIfVlanType
    MAX-ACCESS   read-only
    STATUS       current
    DESCRIPTION
        "Cisco Firepower storage:EtherIf:vlanType managed object property"
    ::= { cfprApStorageEtherIfEntry 5 }

cfprApStorageFcIfTable OBJECT-TYPE
    SYNTAX           SEQUENCE OF CfprApStorageFcIfEntry
    MAX-ACCESS       not-accessible
    STATUS           current
    DESCRIPTION
        "Cisco Firepower storage:FcIf managed object table"
    ::= { cfprApStorageObjects 10 }

cfprApStorageFcIfEntry OBJECT-TYPE
    SYNTAX           CfprApStorageFcIfEntry
    MAX-ACCESS       not-accessible
    STATUS           current
    DESCRIPTION
        "Entry for the cfprApStorageFcIfTable table."
    INDEX { cfprApStorageFcIfInstanceId }
    ::= { cfprApStorageFcIfTable 1 }

CfprApStorageFcIfEntry ::= SEQUENCE {
    cfprApStorageFcIfInstanceId                                      CfprApManagedObjectId,
    cfprApStorageFcIfDn                                              CfprApManagedObjectDn,
    cfprApStorageFcIfRn                                              SnmpAdminString,
    cfprApStorageFcIfName                                            SnmpAdminString
}

cfprApStorageFcIfInstanceId OBJECT-TYPE
    SYNTAX       CfprApManagedObjectId
    MAX-ACCESS   not-accessible
    STATUS       current
    DESCRIPTION
        "Instance identifier of the managed object."
    ::= { cfprApStorageFcIfEntry 1 }

cfprApStorageFcIfDn OBJECT-TYPE
    SYNTAX       CfprApManagedObjectDn
    MAX-ACCESS   read-only
    STATUS       current
    DESCRIPTION
        "Cisco Firepower storage:FcIf:dn managed object property"
    ::= { cfprApStorageFcIfEntry 2 }

cfprApStorageFcIfRn OBJECT-TYPE
    SYNTAX       SnmpAdminString
    MAX-ACCESS   read-only
    STATUS       current
    DESCRIPTION
        "Cisco Firepower storage:FcIf:rn managed object property"
    ::= { cfprApStorageFcIfEntry 3 }

cfprApStorageFcIfName OBJECT-TYPE
    SYNTAX       SnmpAdminString
    MAX-ACCESS   read-only
    STATUS       current
    DESCRIPTION
        "Cisco Firepower storage:FcIf:name managed object property"
    ::= { cfprApStorageFcIfEntry 4 }

cfprApStorageFcTargetIfTable OBJECT-TYPE
    SYNTAX           SEQUENCE OF CfprApStorageFcTargetIfEntry
    MAX-ACCESS       not-accessible
    STATUS           current
    DESCRIPTION
        "Cisco Firepower storage:FcTargetIf managed object table"
    ::= { cfprApStorageObjects 12 }

cfprApStorageFcTargetIfEntry OBJECT-TYPE
    SYNTAX           CfprApStorageFcTargetIfEntry
    MAX-ACCESS       not-accessible
    STATUS           current
    DESCRIPTION
        "Entry for the cfprApStorageFcTargetIfTable table."
    INDEX { cfprApStorageFcTargetIfInstanceId }
    ::= { cfprApStorageFcTargetIfTable 1 }

CfprApStorageFcTargetIfEntry ::= SEQUENCE {
    cfprApStorageFcTargetIfInstanceId                                CfprApManagedObjectId,
    cfprApStorageFcTargetIfDn                                        CfprApManagedObjectDn,
    cfprApStorageFcTargetIfRn                                        SnmpAdminString,
    cfprApStorageFcTargetIfId                                        Unsigned64,
    cfprApStorageFcTargetIfProt                                      CfprApStorageProtocol
}

cfprApStorageFcTargetIfInstanceId OBJECT-TYPE
    SYNTAX       CfprApManagedObjectId
    MAX-ACCESS   not-accessible
    STATUS       current
    DESCRIPTION
        "Instance identifier of the managed object."
    ::= { cfprApStorageFcTargetIfEntry 1 }

cfprApStorageFcTargetIfDn OBJECT-TYPE
    SYNTAX       CfprApManagedObjectDn
    MAX-ACCESS   read-only
    STATUS       current
    DESCRIPTION
        "Cisco Firepower storage:FcTargetIf:dn managed object property"
    ::= { cfprApStorageFcTargetIfEntry 2 }

cfprApStorageFcTargetIfRn OBJECT-TYPE
    SYNTAX       SnmpAdminString
    MAX-ACCESS   read-only
    STATUS       current
    DESCRIPTION
        "Cisco Firepower storage:FcTargetIf:rn managed object property"
    ::= { cfprApStorageFcTargetIfEntry 3 }

cfprApStorageFcTargetIfId OBJECT-TYPE
    SYNTAX       Unsigned64
    MAX-ACCESS   read-only
    STATUS       current
    DESCRIPTION
        "Cisco Firepower storage:FcTargetIf:id managed object property"
    ::= { cfprApStorageFcTargetIfEntry 4 }

cfprApStorageFcTargetIfProt OBJECT-TYPE
    SYNTAX       CfprApStorageProtocol
    MAX-ACCESS   read-only
    STATUS       current
    DESCRIPTION
        "Cisco Firepower storage:FcTargetIf:prot managed object property"
    ::= { cfprApStorageFcTargetIfEntry 5 }

cfprApStorageFlexFlashCardTable OBJECT-TYPE
    SYNTAX           SEQUENCE OF CfprApStorageFlexFlashCardEntry
    MAX-ACCESS       not-accessible
    STATUS           current
    DESCRIPTION
        "Cisco Firepower storage:FlexFlashCard managed object table"
    ::= { cfprApStorageObjects 13 }

cfprApStorageFlexFlashCardEntry OBJECT-TYPE
    SYNTAX           CfprApStorageFlexFlashCardEntry
    MAX-ACCESS       not-accessible
    STATUS           current
    DESCRIPTION
        "Entry for the cfprApStorageFlexFlashCardTable table."
    INDEX { cfprApStorageFlexFlashCardInstanceId }
    ::= { cfprApStorageFlexFlashCardTable 1 }

CfprApStorageFlexFlashCardEntry ::= SEQUENCE {
    cfprApStorageFlexFlashCardInstanceId                             CfprApManagedObjectId,
    cfprApStorageFlexFlashCardDn                                     CfprApManagedObjectDn,
    cfprApStorageFlexFlashCardRn                                     SnmpAdminString,
    cfprApStorageFlexFlashCardBlockSize                              Gauge32,
    cfprApStorageFlexFlashCardCardHealth                             CfprApStorageFFCardHealth,
    cfprApStorageFlexFlashCardCardMode                               CfprApStorageFFCardMode,
    cfprApStorageFlexFlashCardCardState                              CfprApStorageFFCardState,
    cfprApStorageFlexFlashCardCardSync                               CfprApStorageFFCardSync,
    cfprApStorageFlexFlashCardCardType                               SnmpAdminString,
    cfprApStorageFlexFlashCardConnectionProtocol                     CfprApStorageConnectionProtocol,
    cfprApStorageFlexFlashCardControllerIndex                        Gauge32,
    cfprApStorageFlexFlashCardDrivesEnabled                          SnmpAdminString,
    cfprApStorageFlexFlashCardId                                     Gauge32,
    cfprApStorageFlexFlashCardMfgDate                                SnmpAdminString,
    cfprApStorageFlexFlashCardMfgId                                  SnmpAdminString,
    cfprApStorageFlexFlashCardModel                                  SnmpAdminString,
    cfprApStorageFlexFlashCardNumberOfBlocks                         Unsigned64,
    cfprApStorageFlexFlashCardOemId                                  SnmpAdminString,
    cfprApStorageFlexFlashCardOperQualifierReason                    SnmpAdminString,
    cfprApStorageFlexFlashCardOperability                            CfprApEquipmentOperability,
    cfprApStorageFlexFlashCardPartitionCount                         Gauge32,
    cfprApStorageFlexFlashCardPresence                               CfprApEquipmentPresence,
    cfprApStorageFlexFlashCardReadErrorThreshold                     Gauge32,
    cfprApStorageFlexFlashCardReadIOErrorCount                       Gauge32,
    cfprApStorageFlexFlashCardRevision                               SnmpAdminString,
    cfprApStorageFlexFlashCardSerial                                 SnmpAdminString,
    cfprApStorageFlexFlashCardSignature                              SnmpAdminString,
    cfprApStorageFlexFlashCardSize                                   Unsigned64,
    cfprApStorageFlexFlashCardSlotNumber                             Gauge32,
    cfprApStorageFlexFlashCardVendor                                 SnmpAdminString,
    cfprApStorageFlexFlashCardWriteEnable                            CfprApStorageFFCardWriteEnable,
    cfprApStorageFlexFlashCardWriteErrorThreshold                    Gauge32,
    cfprApStorageFlexFlashCardWriteIOErrorCount                      Gauge32
}

cfprApStorageFlexFlashCardInstanceId OBJECT-TYPE
    SYNTAX       CfprApManagedObjectId
    MAX-ACCESS   not-accessible
    STATUS       current
    DESCRIPTION
        "Instance identifier of the managed object."
    ::= { cfprApStorageFlexFlashCardEntry 1 }

cfprApStorageFlexFlashCardDn OBJECT-TYPE
    SYNTAX       CfprApManagedObjectDn
    MAX-ACCESS   read-only
    STATUS       current
    DESCRIPTION
        "Cisco Firepower storage:FlexFlashCard:dn managed object property"
    ::= { cfprApStorageFlexFlashCardEntry 2 }

cfprApStorageFlexFlashCardRn OBJECT-TYPE
    SYNTAX       SnmpAdminString
    MAX-ACCESS   read-only
    STATUS       current
    DESCRIPTION
        "Cisco Firepower storage:FlexFlashCard:rn managed object property"
    ::= { cfprApStorageFlexFlashCardEntry 3 }

cfprApStorageFlexFlashCardBlockSize OBJECT-TYPE
    SYNTAX       Gauge32
    MAX-ACCESS   read-only
    STATUS       current
    DESCRIPTION
        "Cisco Firepower storage:FlexFlashCard:blockSize
        managed object property"
    ::= { cfprApStorageFlexFlashCardEntry 4 }

cfprApStorageFlexFlashCardCardHealth OBJECT-TYPE
    SYNTAX       CfprApStorageFFCardHealth
    MAX-ACCESS   read-only
    STATUS       current
    DESCRIPTION
        "Cisco Firepower storage:FlexFlashCard:cardHealth
        managed object property"
    ::= { cfprApStorageFlexFlashCardEntry 5 }

cfprApStorageFlexFlashCardCardMode OBJECT-TYPE
    SYNTAX       CfprApStorageFFCardMode
    MAX-ACCESS   read-only
    STATUS       current
    DESCRIPTION
        "Cisco Firepower storage:FlexFlashCard:cardMode
        managed object property"
    ::= { cfprApStorageFlexFlashCardEntry 6 }

cfprApStorageFlexFlashCardCardState OBJECT-TYPE
    SYNTAX       CfprApStorageFFCardState
    MAX-ACCESS   read-only
    STATUS       current
    DESCRIPTION
        "Cisco Firepower storage:FlexFlashCard:cardState
        managed object property"
    ::= { cfprApStorageFlexFlashCardEntry 7 }

cfprApStorageFlexFlashCardCardSync OBJECT-TYPE
    SYNTAX       CfprApStorageFFCardSync
    MAX-ACCESS   read-only
    STATUS       current
    DESCRIPTION
        "Cisco Firepower storage:FlexFlashCard:cardSync
        managed object property"
    ::= { cfprApStorageFlexFlashCardEntry 8 }

cfprApStorageFlexFlashCardCardType OBJECT-TYPE
    SYNTAX       SnmpAdminString
    MAX-ACCESS   read-only
    STATUS       current
    DESCRIPTION
        "Cisco Firepower storage:FlexFlashCard:cardType
        managed object property"
    ::= { cfprApStorageFlexFlashCardEntry 9 }

cfprApStorageFlexFlashCardConnectionProtocol OBJECT-TYPE
    SYNTAX       CfprApStorageConnectionProtocol
    MAX-ACCESS   read-only
    STATUS       current
    DESCRIPTION
        "Cisco Firepower storage:FlexFlashCard:connectionProtocol
        managed object property"
    ::= { cfprApStorageFlexFlashCardEntry 10 }

cfprApStorageFlexFlashCardControllerIndex OBJECT-TYPE
    SYNTAX       Gauge32
    MAX-ACCESS   read-only
    STATUS       current
    DESCRIPTION
        "Cisco Firepower storage:FlexFlashCard:controllerIndex
        managed object property"
    ::= { cfprApStorageFlexFlashCardEntry 11 }

cfprApStorageFlexFlashCardDrivesEnabled OBJECT-TYPE
    SYNTAX       SnmpAdminString
    MAX-ACCESS   read-only
    STATUS       current
    DESCRIPTION
        "Cisco Firepower storage:FlexFlashCard:drivesEnabled
        managed object property"
    ::= { cfprApStorageFlexFlashCardEntry 12 }

cfprApStorageFlexFlashCardId OBJECT-TYPE
    SYNTAX       Gauge32
    MAX-ACCESS   read-only
    STATUS       current
    DESCRIPTION
        "Cisco Firepower storage:FlexFlashCard:id managed object property"
    ::= { cfprApStorageFlexFlashCardEntry 13 }

cfprApStorageFlexFlashCardMfgDate OBJECT-TYPE
    SYNTAX       SnmpAdminString
    MAX-ACCESS   read-only
    STATUS       current
    DESCRIPTION
        "Cisco Firepower storage:FlexFlashCard:mfgDate
        managed object property"
    ::= { cfprApStorageFlexFlashCardEntry 14 }

cfprApStorageFlexFlashCardMfgId OBJECT-TYPE
    SYNTAX       SnmpAdminString
    MAX-ACCESS   read-only
    STATUS       current
    DESCRIPTION
        "Cisco Firepower storage:FlexFlashCard:mfgId managed
        object property"
    ::= { cfprApStorageFlexFlashCardEntry 15 }

cfprApStorageFlexFlashCardModel OBJECT-TYPE
    SYNTAX       SnmpAdminString
    MAX-ACCESS   read-only
    STATUS       current
    DESCRIPTION
        "Cisco Firepower storage:FlexFlashCard:model managed
        object property"
    ::= { cfprApStorageFlexFlashCardEntry 16 }

cfprApStorageFlexFlashCardNumberOfBlocks OBJECT-TYPE
    SYNTAX       Unsigned64
    MAX-ACCESS   read-only
    STATUS       current
    DESCRIPTION
        "Cisco Firepower storage:FlexFlashCard:numberOfBlocks
        managed object property"
    ::= { cfprApStorageFlexFlashCardEntry 17 }

cfprApStorageFlexFlashCardOemId OBJECT-TYPE
    SYNTAX       SnmpAdminString
    MAX-ACCESS   read-only
    STATUS       current
    DESCRIPTION
        "Cisco Firepower storage:FlexFlashCard:oemId managed
        object property"
    ::= { cfprApStorageFlexFlashCardEntry 18 }

cfprApStorageFlexFlashCardOperQualifierReason OBJECT-TYPE
    SYNTAX       SnmpAdminString
    MAX-ACCESS   read-only
    STATUS       current
    DESCRIPTION
        "Cisco Firepower storage:FlexFlashCard:operQualifierReason
        managed object property"
    ::= { cfprApStorageFlexFlashCardEntry 19 }

cfprApStorageFlexFlashCardOperability OBJECT-TYPE
    SYNTAX       CfprApEquipmentOperability
    MAX-ACCESS   read-only
    STATUS       current
    DESCRIPTION
        "Cisco Firepower storage:FlexFlashCard:operability
        managed object property"
    ::= { cfprApStorageFlexFlashCardEntry 20 }

cfprApStorageFlexFlashCardPartitionCount OBJECT-TYPE
    SYNTAX       Gauge32
    MAX-ACCESS   read-only
    STATUS       current
    DESCRIPTION
        "Cisco Firepower storage:FlexFlashCard:partitionCount
        managed object property"
    ::= { cfprApStorageFlexFlashCardEntry 21 }

cfprApStorageFlexFlashCardPresence OBJECT-TYPE
    SYNTAX       CfprApEquipmentPresence
    MAX-ACCESS   read-only
    STATUS       current
    DESCRIPTION
        "Cisco Firepower storage:FlexFlashCard:presence
        managed object property"
    ::= { cfprApStorageFlexFlashCardEntry 22 }

cfprApStorageFlexFlashCardReadErrorThreshold OBJECT-TYPE
    SYNTAX       Gauge32
    MAX-ACCESS   read-only
    STATUS       current
    DESCRIPTION
        "Cisco Firepower storage:FlexFlashCard:readErrorThreshold
        managed object property"
    ::= { cfprApStorageFlexFlashCardEntry 23 }

cfprApStorageFlexFlashCardReadIOErrorCount OBJECT-TYPE
    SYNTAX       Gauge32
    MAX-ACCESS   read-only
    STATUS       current
    DESCRIPTION
        "Cisco Firepower storage:FlexFlashCard:readIOErrorCount
        managed object property"
    ::= { cfprApStorageFlexFlashCardEntry 24 }

cfprApStorageFlexFlashCardRevision OBJECT-TYPE
    SYNTAX       SnmpAdminString
    MAX-ACCESS   read-only
    STATUS       current
    DESCRIPTION
        "Cisco Firepower storage:FlexFlashCard:revision
        managed object property"
    ::= { cfprApStorageFlexFlashCardEntry 25 }

cfprApStorageFlexFlashCardSerial OBJECT-TYPE
    SYNTAX       SnmpAdminString
    MAX-ACCESS   read-only
    STATUS       current
    DESCRIPTION
        "Cisco Firepower storage:FlexFlashCard:serial managed
        object property"
    ::= { cfprApStorageFlexFlashCardEntry 26 }

cfprApStorageFlexFlashCardSignature OBJECT-TYPE
    SYNTAX       SnmpAdminString
    MAX-ACCESS   read-only
    STATUS       current
    DESCRIPTION
        "Cisco Firepower storage:FlexFlashCard:signature
        managed object property"
    ::= { cfprApStorageFlexFlashCardEntry 27 }

cfprApStorageFlexFlashCardSize OBJECT-TYPE
    SYNTAX       Unsigned64
    MAX-ACCESS   read-only
    STATUS       current
    DESCRIPTION
        "Cisco Firepower storage:FlexFlashCard:size managed
        object property"
    ::= { cfprApStorageFlexFlashCardEntry 28 }

cfprApStorageFlexFlashCardSlotNumber OBJECT-TYPE
    SYNTAX       Gauge32
    MAX-ACCESS   read-only
    STATUS       current
    DESCRIPTION
        "Cisco Firepower storage:FlexFlashCard:slotNumber
        managed object property"
    ::= { cfprApStorageFlexFlashCardEntry 29 }

cfprApStorageFlexFlashCardVendor OBJECT-TYPE
    SYNTAX       SnmpAdminString
    MAX-ACCESS   read-only
    STATUS       current
    DESCRIPTION
        "Cisco Firepower storage:FlexFlashCard:vendor managed
        object property"
    ::= { cfprApStorageFlexFlashCardEntry 30 }

cfprApStorageFlexFlashCardWriteEnable OBJECT-TYPE
    SYNTAX       CfprApStorageFFCardWriteEnable
    MAX-ACCESS   read-only
    STATUS       current
    DESCRIPTION
        "Cisco Firepower storage:FlexFlashCard:writeEnable
        managed object property"
    ::= { cfprApStorageFlexFlashCardEntry 31 }

cfprApStorageFlexFlashCardWriteErrorThreshold OBJECT-TYPE
    SYNTAX       Gauge32
    MAX-ACCESS   read-only
    STATUS       current
    DESCRIPTION
        "Cisco Firepower storage:FlexFlashCard:writeErrorThreshold
        managed object property"
    ::= { cfprApStorageFlexFlashCardEntry 32 }

cfprApStorageFlexFlashCardWriteIOErrorCount OBJECT-TYPE
    SYNTAX       Gauge32
    MAX-ACCESS   read-only
    STATUS       current
    DESCRIPTION
        "Cisco Firepower storage:FlexFlashCard:writeIOErrorCount
        managed object property"
    ::= { cfprApStorageFlexFlashCardEntry 33 }

cfprApStorageFlexFlashControllerTable OBJECT-TYPE
    SYNTAX           SEQUENCE OF CfprApStorageFlexFlashControllerEntry
    MAX-ACCESS       not-accessible
    STATUS           current
    DESCRIPTION
        "Cisco Firepower storage:FlexFlashController managed object table"
    ::= { cfprApStorageObjects 14 }

cfprApStorageFlexFlashControllerEntry OBJECT-TYPE
    SYNTAX           CfprApStorageFlexFlashControllerEntry
    MAX-ACCESS       not-accessible
    STATUS           current
    DESCRIPTION
        "Entry for the cfprApStorageFlexFlashControllerTable table."
    INDEX { cfprApStorageFlexFlashControllerInstanceId }
    ::= { cfprApStorageFlexFlashControllerTable 1 }

CfprApStorageFlexFlashControllerEntry ::= SEQUENCE {
    cfprApStorageFlexFlashControllerInstanceId                       CfprApManagedObjectId,
    cfprApStorageFlexFlashControllerDn                               CfprApManagedObjectDn,
    cfprApStorageFlexFlashControllerRn                               SnmpAdminString,
    cfprApStorageFlexFlashControllerAdminSlotNumber                  CfprApStorageFFSlotENUM,
    cfprApStorageFlexFlashControllerConfiguredMode                   CfprApStorageOperatingModeType,
    cfprApStorageFlexFlashControllerControllerHealth                 CfprApStorageFFControllerHealth,
    cfprApStorageFlexFlashControllerControllerState                  CfprApStorageFFControllerState,
    cfprApStorageFlexFlashControllerFirmwareVersion                  SnmpAdminString,
    cfprApStorageFlexFlashControllerFlexFlashType                    CfprApStorageFFType,
    cfprApStorageFlexFlashControllerHasError                         CfprApStorageFFHasError,
    cfprApStorageFlexFlashControllerId                               CfprApStorageFlexFlashControllerId,
    cfprApStorageFlexFlashControllerIsCardMismatch                   CfprApStorageFFCardSizeMismatch,
    cfprApStorageFlexFlashControllerIsFormatFSMRunning               CfprApStorageFFFormatRunning,
    cfprApStorageFlexFlashControllerLocationDn                       SnmpAdminString,
    cfprApStorageFlexFlashControllerModel                            SnmpAdminString,
    cfprApStorageFlexFlashControllerOperQualifierReason              SnmpAdminString,
    cfprApStorageFlexFlashControllerOperState                        CfprApEquipmentOperability,
    cfprApStorageFlexFlashControllerOperability                      CfprApEquipmentOperability,
    cfprApStorageFlexFlashControllerOperatingMode                    CfprApStorageOperatingModeType,
    cfprApStorageFlexFlashControllerOperationRequest                 CfprApStorageOperationRequestType,
    cfprApStorageFlexFlashControllerPciAddr                          SnmpAdminString,
    cfprApStorageFlexFlashControllerPciSlot                          SnmpAdminString,
    cfprApStorageFlexFlashControllerPerf                             CfprApEquipmentSensorThresholdStatus,
    cfprApStorageFlexFlashControllerPhysicalDriveCount               Gauge32,
    cfprApStorageFlexFlashControllerPower                            CfprApEquipmentPowerState,
    cfprApStorageFlexFlashControllerPresence                         CfprApEquipmentPresence,
    cfprApStorageFlexFlashControllerPrimarySlotNumber                Gauge32,
    cfprApStorageFlexFlashControllerRaidSyncSupport                  CfprApStorageFFRaidSyncSupport,
    cfprApStorageFlexFlashControllerReadErrorThreshold               Gauge32,
    cfprApStorageFlexFlashControllerRevision                         SnmpAdminString,
    cfprApStorageFlexFlashControllerSerial                           SnmpAdminString,
    cfprApStorageFlexFlashControllerThermal                          CfprApEquipmentSensorThresholdStatus,
    cfprApStorageFlexFlashControllerType                             CfprApStorageControllerType,
    cfprApStorageFlexFlashControllerVendor                           SnmpAdminString,
    cfprApStorageFlexFlashControllerVirtualDriveCount                Gauge32,
    cfprApStorageFlexFlashControllerVoltage                          CfprApEquipmentSensorThresholdStatus,
    cfprApStorageFlexFlashControllerWriteErrorThreshold              Gauge32
}

cfprApStorageFlexFlashControllerInstanceId OBJECT-TYPE
    SYNTAX       CfprApManagedObjectId
    MAX-ACCESS   not-accessible
    STATUS       current
    DESCRIPTION
        "Instance identifier of the managed object."
    ::= { cfprApStorageFlexFlashControllerEntry 1 }

cfprApStorageFlexFlashControllerDn OBJECT-TYPE
    SYNTAX       CfprApManagedObjectDn
    MAX-ACCESS   read-only
    STATUS       current
    DESCRIPTION
        "Cisco Firepower storage:FlexFlashController:dn
        managed object property"
    ::= { cfprApStorageFlexFlashControllerEntry 2 }

cfprApStorageFlexFlashControllerRn OBJECT-TYPE
    SYNTAX       SnmpAdminString
    MAX-ACCESS   read-only
    STATUS       current
    DESCRIPTION
        "Cisco Firepower storage:FlexFlashController:rn
        managed object property"
    ::= { cfprApStorageFlexFlashControllerEntry 3 }

cfprApStorageFlexFlashControllerAdminSlotNumber OBJECT-TYPE
    SYNTAX       CfprApStorageFFSlotENUM
    MAX-ACCESS   read-only
    STATUS       current
    DESCRIPTION
        "Cisco Firepower storage:FlexFlashController:adminSlotNumber
        managed object property"
    ::= { cfprApStorageFlexFlashControllerEntry 4 }

cfprApStorageFlexFlashControllerConfiguredMode OBJECT-TYPE
    SYNTAX       CfprApStorageOperatingModeType
    MAX-ACCESS   read-only
    STATUS       current
    DESCRIPTION
        "Cisco Firepower storage:FlexFlashController:configuredMode
        managed object property"
    ::= { cfprApStorageFlexFlashControllerEntry 5 }

cfprApStorageFlexFlashControllerControllerHealth OBJECT-TYPE
    SYNTAX       CfprApStorageFFControllerHealth
    MAX-ACCESS   read-only
    STATUS       current
    DESCRIPTION
        "Cisco Firepower storage:FlexFlashController:controllerHealth
        managed object property"
    ::= { cfprApStorageFlexFlashControllerEntry 6 }

cfprApStorageFlexFlashControllerControllerState OBJECT-TYPE
    SYNTAX       CfprApStorageFFControllerState
    MAX-ACCESS   read-only
    STATUS       current
    DESCRIPTION
        "Cisco Firepower storage:FlexFlashController:controllerState
        managed object property"
    ::= { cfprApStorageFlexFlashControllerEntry 7 }

cfprApStorageFlexFlashControllerFirmwareVersion OBJECT-TYPE
    SYNTAX       SnmpAdminString
    MAX-ACCESS   read-only
    STATUS       current
    DESCRIPTION
        "Cisco Firepower storage:FlexFlashController:firmwareVersion
        managed object property"
    ::= { cfprApStorageFlexFlashControllerEntry 8 }

cfprApStorageFlexFlashControllerFlexFlashType OBJECT-TYPE
    SYNTAX       CfprApStorageFFType
    MAX-ACCESS   read-only
    STATUS       current
    DESCRIPTION
        "Cisco Firepower storage:FlexFlashController:flexFlashType
        managed object property"
    ::= { cfprApStorageFlexFlashControllerEntry 9 }

cfprApStorageFlexFlashControllerHasError OBJECT-TYPE
    SYNTAX       CfprApStorageFFHasError
    MAX-ACCESS   read-only
    STATUS       current
    DESCRIPTION
        "Cisco Firepower storage:FlexFlashController:hasError
        managed object property"
    ::= { cfprApStorageFlexFlashControllerEntry 10 }

cfprApStorageFlexFlashControllerId OBJECT-TYPE
    SYNTAX       CfprApStorageFlexFlashControllerId
    MAX-ACCESS   read-only
    STATUS       current
    DESCRIPTION
        "Cisco Firepower storage:FlexFlashController:id
        managed object property"
    ::= { cfprApStorageFlexFlashControllerEntry 11 }

cfprApStorageFlexFlashControllerIsCardMismatch OBJECT-TYPE
    SYNTAX       CfprApStorageFFCardSizeMismatch
    MAX-ACCESS   read-only
    STATUS       current
    DESCRIPTION
        "Cisco Firepower storage:FlexFlashController:isCardMismatch
        managed object property"
    ::= { cfprApStorageFlexFlashControllerEntry 12 }

cfprApStorageFlexFlashControllerIsFormatFSMRunning OBJECT-TYPE
    SYNTAX       CfprApStorageFFFormatRunning
    MAX-ACCESS   read-only
    STATUS       current
    DESCRIPTION
        "Cisco Firepower storage:FlexFlashController:isFormatFSMRunning
        managed object property"
    ::= { cfprApStorageFlexFlashControllerEntry 13 }

cfprApStorageFlexFlashControllerLocationDn OBJECT-TYPE
    SYNTAX       SnmpAdminString
    MAX-ACCESS   read-only
    STATUS       current
    DESCRIPTION
        "Cisco Firepower storage:FlexFlashController:locationDn
        managed object property"
    ::= { cfprApStorageFlexFlashControllerEntry 14 }

cfprApStorageFlexFlashControllerModel OBJECT-TYPE
    SYNTAX       SnmpAdminString
    MAX-ACCESS   read-only
    STATUS       current
    DESCRIPTION
        "Cisco Firepower storage:FlexFlashController:model
        managed object property"
    ::= { cfprApStorageFlexFlashControllerEntry 15 }

cfprApStorageFlexFlashControllerOperQualifierReason OBJECT-TYPE
    SYNTAX       SnmpAdminString
    MAX-ACCESS   read-only
    STATUS       current
    DESCRIPTION
        "Cisco Firepower storage:FlexFlashController:operQualifierReason
        managed object property"
    ::= { cfprApStorageFlexFlashControllerEntry 16 }

cfprApStorageFlexFlashControllerOperState OBJECT-TYPE
    SYNTAX       CfprApEquipmentOperability
    MAX-ACCESS   read-only
    STATUS       current
    DESCRIPTION
        "Cisco Firepower storage:FlexFlashController:operState
        managed object property"
    ::= { cfprApStorageFlexFlashControllerEntry 17 }

cfprApStorageFlexFlashControllerOperability OBJECT-TYPE
    SYNTAX       CfprApEquipmentOperability
    MAX-ACCESS   read-only
    STATUS       current
    DESCRIPTION
        "Cisco Firepower storage:FlexFlashController:operability
        managed object property"
    ::= { cfprApStorageFlexFlashControllerEntry 18 }

cfprApStorageFlexFlashControllerOperatingMode OBJECT-TYPE
    SYNTAX       CfprApStorageOperatingModeType
    MAX-ACCESS   read-only
    STATUS       current
    DESCRIPTION
        "Cisco Firepower storage:FlexFlashController:operatingMode
        managed object property"
    ::= { cfprApStorageFlexFlashControllerEntry 19 }

cfprApStorageFlexFlashControllerOperationRequest OBJECT-TYPE
    SYNTAX       CfprApStorageOperationRequestType
    MAX-ACCESS   read-only
    STATUS       current
    DESCRIPTION
        "Cisco Firepower storage:FlexFlashController:operationRequest
        managed object property"
    ::= { cfprApStorageFlexFlashControllerEntry 20 }

cfprApStorageFlexFlashControllerPciAddr OBJECT-TYPE
    SYNTAX       SnmpAdminString
    MAX-ACCESS   read-only
    STATUS       current
    DESCRIPTION
        "Cisco Firepower storage:FlexFlashController:pciAddr
        managed object property"
    ::= { cfprApStorageFlexFlashControllerEntry 21 }

cfprApStorageFlexFlashControllerPciSlot OBJECT-TYPE
    SYNTAX       SnmpAdminString
    MAX-ACCESS   read-only
    STATUS       current
    DESCRIPTION
        "Cisco Firepower storage:FlexFlashController:pciSlot
        managed object property"
    ::= { cfprApStorageFlexFlashControllerEntry 22 }

cfprApStorageFlexFlashControllerPerf OBJECT-TYPE
    SYNTAX       CfprApEquipmentSensorThresholdStatus
    MAX-ACCESS   read-only
    STATUS       current
    DESCRIPTION
        "Cisco Firepower storage:FlexFlashController:perf
        managed object property"
    ::= { cfprApStorageFlexFlashControllerEntry 23 }

cfprApStorageFlexFlashControllerPhysicalDriveCount OBJECT-TYPE
    SYNTAX       Gauge32
    MAX-ACCESS   read-only
    STATUS       current
    DESCRIPTION
        "Cisco Firepower storage:FlexFlashController:physicalDriveCount
        managed object property"
    ::= { cfprApStorageFlexFlashControllerEntry 24 }

cfprApStorageFlexFlashControllerPower OBJECT-TYPE
    SYNTAX       CfprApEquipmentPowerState
    MAX-ACCESS   read-only
    STATUS       current
    DESCRIPTION
        "Cisco Firepower storage:FlexFlashController:power
        managed object property"
    ::= { cfprApStorageFlexFlashControllerEntry 25 }

cfprApStorageFlexFlashControllerPresence OBJECT-TYPE
    SYNTAX       CfprApEquipmentPresence
    MAX-ACCESS   read-only
    STATUS       current
    DESCRIPTION
        "Cisco Firepower storage:FlexFlashController:presence
        managed object property"
    ::= { cfprApStorageFlexFlashControllerEntry 26 }

cfprApStorageFlexFlashControllerPrimarySlotNumber OBJECT-TYPE
    SYNTAX       Gauge32
    MAX-ACCESS   read-only
    STATUS       current
    DESCRIPTION
        "Cisco Firepower storage:FlexFlashController:primarySlotNumber
        managed object property"
    ::= { cfprApStorageFlexFlashControllerEntry 27 }

cfprApStorageFlexFlashControllerRaidSyncSupport OBJECT-TYPE
    SYNTAX       CfprApStorageFFRaidSyncSupport
    MAX-ACCESS   read-only
    STATUS       current
    DESCRIPTION
        "Cisco Firepower storage:FlexFlashController:raidSyncSupport
        managed object property"
    ::= { cfprApStorageFlexFlashControllerEntry 28 }

cfprApStorageFlexFlashControllerReadErrorThreshold OBJECT-TYPE
    SYNTAX       Gauge32
    MAX-ACCESS   read-only
    STATUS       current
    DESCRIPTION
        "Cisco Firepower storage:FlexFlashController:readErrorThreshold
        managed object property"
    ::= { cfprApStorageFlexFlashControllerEntry 29 }

cfprApStorageFlexFlashControllerRevision OBJECT-TYPE
    SYNTAX       SnmpAdminString
    MAX-ACCESS   read-only
    STATUS       current
    DESCRIPTION
        "Cisco Firepower storage:FlexFlashController:revision
        managed object property"
    ::= { cfprApStorageFlexFlashControllerEntry 30 }

cfprApStorageFlexFlashControllerSerial OBJECT-TYPE
    SYNTAX       SnmpAdminString
    MAX-ACCESS   read-only
    STATUS       current
    DESCRIPTION
        "Cisco Firepower storage:FlexFlashController:serial
        managed object property"
    ::= { cfprApStorageFlexFlashControllerEntry 31 }

cfprApStorageFlexFlashControllerThermal OBJECT-TYPE
    SYNTAX       CfprApEquipmentSensorThresholdStatus
    MAX-ACCESS   read-only
    STATUS       current
    DESCRIPTION
        "Cisco Firepower storage:FlexFlashController:thermal
        managed object property"
    ::= { cfprApStorageFlexFlashControllerEntry 32 }

cfprApStorageFlexFlashControllerType OBJECT-TYPE
    SYNTAX       CfprApStorageControllerType
    MAX-ACCESS   read-only
    STATUS       current
    DESCRIPTION
        "Cisco Firepower storage:FlexFlashController:type
        managed object property"
    ::= { cfprApStorageFlexFlashControllerEntry 33 }

cfprApStorageFlexFlashControllerVendor OBJECT-TYPE
    SYNTAX       SnmpAdminString
    MAX-ACCESS   read-only
    STATUS       current
    DESCRIPTION
        "Cisco Firepower storage:FlexFlashController:vendor
        managed object property"
    ::= { cfprApStorageFlexFlashControllerEntry 34 }

cfprApStorageFlexFlashControllerVirtualDriveCount OBJECT-TYPE
    SYNTAX       Gauge32
    MAX-ACCESS   read-only
    STATUS       current
    DESCRIPTION
        "Cisco Firepower storage:FlexFlashController:virtualDriveCount
        managed object property"
    ::= { cfprApStorageFlexFlashControllerEntry 35 }

cfprApStorageFlexFlashControllerVoltage OBJECT-TYPE
    SYNTAX       CfprApEquipmentSensorThresholdStatus
    MAX-ACCESS   read-only
    STATUS       current
    DESCRIPTION
        "Cisco Firepower storage:FlexFlashController:voltage
        managed object property"
    ::= { cfprApStorageFlexFlashControllerEntry 36 }

cfprApStorageFlexFlashControllerWriteErrorThreshold OBJECT-TYPE
    SYNTAX       Gauge32
    MAX-ACCESS   read-only
    STATUS       current
    DESCRIPTION
        "Cisco Firepower storage:FlexFlashController:writeErrorThreshold
        managed object property"
    ::= { cfprApStorageFlexFlashControllerEntry 37 }

cfprApStorageFlexFlashDriveTable OBJECT-TYPE
    SYNTAX           SEQUENCE OF CfprApStorageFlexFlashDriveEntry
    MAX-ACCESS       not-accessible
    STATUS           current
    DESCRIPTION
        "Cisco Firepower storage:FlexFlashDrive managed object table"
    ::= { cfprApStorageObjects 15 }

cfprApStorageFlexFlashDriveEntry OBJECT-TYPE
    SYNTAX           CfprApStorageFlexFlashDriveEntry
    MAX-ACCESS       not-accessible
    STATUS           current
    DESCRIPTION
        "Entry for the cfprApStorageFlexFlashDriveTable table."
    INDEX { cfprApStorageFlexFlashDriveInstanceId }
    ::= { cfprApStorageFlexFlashDriveTable 1 }

CfprApStorageFlexFlashDriveEntry ::= SEQUENCE {
    cfprApStorageFlexFlashDriveInstanceId                            CfprApManagedObjectId,
    cfprApStorageFlexFlashDriveDn                                    CfprApManagedObjectDn,
    cfprApStorageFlexFlashDriveRn                                    SnmpAdminString,
    cfprApStorageFlexFlashDriveRWType                                CfprApStorageFFRWType,
    cfprApStorageFlexFlashDriveBlockSize                             Gauge32,
    cfprApStorageFlexFlashDriveConnectionProtocol                    CfprApStorageConnectionProtocol,
    cfprApStorageFlexFlashDriveControllerIndex                       Gauge32,
    cfprApStorageFlexFlashDriveDriveState                            CfprApStorageFFDriveState,
    cfprApStorageFlexFlashDriveDriveType                             CfprApStorageFFDriveType,
    cfprApStorageFlexFlashDriveId                                    Gauge32,
    cfprApStorageFlexFlashDriveLastOperation                         CfprApStorageOperationStateType,
    cfprApStorageFlexFlashDriveModel                                 SnmpAdminString,
    cfprApStorageFlexFlashDriveName                                  SnmpAdminString,
    cfprApStorageFlexFlashDriveNumberOfBlocks                        Unsigned64,
    cfprApStorageFlexFlashDriveOperQualifierReason                   SnmpAdminString,
    cfprApStorageFlexFlashDriveOperability                           CfprApEquipmentOperability,
    cfprApStorageFlexFlashDriveOperationState                        CfprApStorageOperationStateType,
    cfprApStorageFlexFlashDrivePresence                              CfprApEquipmentPresence,
    cfprApStorageFlexFlashDriveRemovable                             CfprApStorageFFDriveRemovable,
    cfprApStorageFlexFlashDriveRevision                              SnmpAdminString,
    cfprApStorageFlexFlashDriveSerial                                SnmpAdminString,
    cfprApStorageFlexFlashDriveSize                                  Unsigned64,
    cfprApStorageFlexFlashDriveSlotNumber                            Gauge32,
    cfprApStorageFlexFlashDriveVendor                                SnmpAdminString,
    cfprApStorageFlexFlashDriveVisible                               CfprApStorageFFDriveVisible
}

cfprApStorageFlexFlashDriveInstanceId OBJECT-TYPE
    SYNTAX       CfprApManagedObjectId
    MAX-ACCESS   not-accessible
    STATUS       current
    DESCRIPTION
        "Instance identifier of the managed object."
    ::= { cfprApStorageFlexFlashDriveEntry 1 }

cfprApStorageFlexFlashDriveDn OBJECT-TYPE
    SYNTAX       CfprApManagedObjectDn
    MAX-ACCESS   read-only
    STATUS       current
    DESCRIPTION
        "Cisco Firepower storage:FlexFlashDrive:dn managed
        object property"
    ::= { cfprApStorageFlexFlashDriveEntry 2 }

cfprApStorageFlexFlashDriveRn OBJECT-TYPE
    SYNTAX       SnmpAdminString
    MAX-ACCESS   read-only
    STATUS       current
    DESCRIPTION
        "Cisco Firepower storage:FlexFlashDrive:rn managed
        object property"
    ::= { cfprApStorageFlexFlashDriveEntry 3 }

cfprApStorageFlexFlashDriveRWType OBJECT-TYPE
    SYNTAX       CfprApStorageFFRWType
    MAX-ACCESS   read-only
    STATUS       current
    DESCRIPTION
        "Cisco Firepower storage:FlexFlashDrive:RWType
        managed object property"
    ::= { cfprApStorageFlexFlashDriveEntry 4 }

cfprApStorageFlexFlashDriveBlockSize OBJECT-TYPE
    SYNTAX       Gauge32
    MAX-ACCESS   read-only
    STATUS       current
    DESCRIPTION
        "Cisco Firepower storage:FlexFlashDrive:blockSize
        managed object property"
    ::= { cfprApStorageFlexFlashDriveEntry 5 }

cfprApStorageFlexFlashDriveConnectionProtocol OBJECT-TYPE
    SYNTAX       CfprApStorageConnectionProtocol
    MAX-ACCESS   read-only
    STATUS       current
    DESCRIPTION
        "Cisco Firepower storage:FlexFlashDrive:connectionProtocol
        managed object property"
    ::= { cfprApStorageFlexFlashDriveEntry 6 }

cfprApStorageFlexFlashDriveControllerIndex OBJECT-TYPE
    SYNTAX       Gauge32
    MAX-ACCESS   read-only
    STATUS       current
    DESCRIPTION
        "Cisco Firepower storage:FlexFlashDrive:controllerIndex
        managed object property"
    ::= { cfprApStorageFlexFlashDriveEntry 7 }

cfprApStorageFlexFlashDriveDriveState OBJECT-TYPE
    SYNTAX       CfprApStorageFFDriveState
    MAX-ACCESS   read-only
    STATUS       current
    DESCRIPTION
        "Cisco Firepower storage:FlexFlashDrive:driveState
        managed object property"
    ::= { cfprApStorageFlexFlashDriveEntry 8 }

cfprApStorageFlexFlashDriveDriveType OBJECT-TYPE
    SYNTAX       CfprApStorageFFDriveType
    MAX-ACCESS   read-only
    STATUS       current
    DESCRIPTION
        "Cisco Firepower storage:FlexFlashDrive:driveType
        managed object property"
    ::= { cfprApStorageFlexFlashDriveEntry 9 }

cfprApStorageFlexFlashDriveId OBJECT-TYPE
    SYNTAX       Gauge32
    MAX-ACCESS   read-only
    STATUS       current
    DESCRIPTION
        "Cisco Firepower storage:FlexFlashDrive:id managed
        object property"
    ::= { cfprApStorageFlexFlashDriveEntry 10 }

cfprApStorageFlexFlashDriveLastOperation OBJECT-TYPE
    SYNTAX       CfprApStorageOperationStateType
    MAX-ACCESS   read-only
    STATUS       current
    DESCRIPTION
        "Cisco Firepower storage:FlexFlashDrive:lastOperation
        managed object property"
    ::= { cfprApStorageFlexFlashDriveEntry 11 }

cfprApStorageFlexFlashDriveModel OBJECT-TYPE
    SYNTAX       SnmpAdminString
    MAX-ACCESS   read-only
    STATUS       current
    DESCRIPTION
        "Cisco Firepower storage:FlexFlashDrive:model managed
        object property"
    ::= { cfprApStorageFlexFlashDriveEntry 12 }

cfprApStorageFlexFlashDriveName OBJECT-TYPE
    SYNTAX       SnmpAdminString
    MAX-ACCESS   read-only
    STATUS       current
    DESCRIPTION
        "Cisco Firepower storage:FlexFlashDrive:name managed
        object property"
    ::= { cfprApStorageFlexFlashDriveEntry 13 }

cfprApStorageFlexFlashDriveNumberOfBlocks OBJECT-TYPE
    SYNTAX       Unsigned64
    MAX-ACCESS   read-only
    STATUS       current
    DESCRIPTION
        "Cisco Firepower storage:FlexFlashDrive:numberOfBlocks
        managed object property"
    ::= { cfprApStorageFlexFlashDriveEntry 14 }

cfprApStorageFlexFlashDriveOperQualifierReason OBJECT-TYPE
    SYNTAX       SnmpAdminString
    MAX-ACCESS   read-only
    STATUS       current
    DESCRIPTION
        "Cisco Firepower storage:FlexFlashDrive:operQualifierReason
        managed object property"
    ::= { cfprApStorageFlexFlashDriveEntry 15 }

cfprApStorageFlexFlashDriveOperability OBJECT-TYPE
    SYNTAX       CfprApEquipmentOperability
    MAX-ACCESS   read-only
    STATUS       current
    DESCRIPTION
        "Cisco Firepower storage:FlexFlashDrive:operability
        managed object property"
    ::= { cfprApStorageFlexFlashDriveEntry 16 }

cfprApStorageFlexFlashDriveOperationState OBJECT-TYPE
    SYNTAX       CfprApStorageOperationStateType
    MAX-ACCESS   read-only
    STATUS       current
    DESCRIPTION
        "Cisco Firepower storage:FlexFlashDrive:operationState
        managed object property"
    ::= { cfprApStorageFlexFlashDriveEntry 17 }

cfprApStorageFlexFlashDrivePresence OBJECT-TYPE
    SYNTAX       CfprApEquipmentPresence
    MAX-ACCESS   read-only
    STATUS       current
    DESCRIPTION
        "Cisco Firepower storage:FlexFlashDrive:presence
        managed object property"
    ::= { cfprApStorageFlexFlashDriveEntry 18 }

cfprApStorageFlexFlashDriveRemovable OBJECT-TYPE
    SYNTAX       CfprApStorageFFDriveRemovable
    MAX-ACCESS   read-only
    STATUS       current
    DESCRIPTION
        "Cisco Firepower storage:FlexFlashDrive:removable
        managed object property"
    ::= { cfprApStorageFlexFlashDriveEntry 19 }

cfprApStorageFlexFlashDriveRevision OBJECT-TYPE
    SYNTAX       SnmpAdminString
    MAX-ACCESS   read-only
    STATUS       current
    DESCRIPTION
        "Cisco Firepower storage:FlexFlashDrive:revision
        managed object property"
    ::= { cfprApStorageFlexFlashDriveEntry 20 }

cfprApStorageFlexFlashDriveSerial OBJECT-TYPE
    SYNTAX       SnmpAdminString
    MAX-ACCESS   read-only
    STATUS       current
    DESCRIPTION
        "Cisco Firepower storage:FlexFlashDrive:serial
        managed object property"
    ::= { cfprApStorageFlexFlashDriveEntry 21 }

cfprApStorageFlexFlashDriveSize OBJECT-TYPE
    SYNTAX       Unsigned64
    MAX-ACCESS   read-only
    STATUS       current
    DESCRIPTION
        "Cisco Firepower storage:FlexFlashDrive:size managed
        object property"
    ::= { cfprApStorageFlexFlashDriveEntry 22 }

cfprApStorageFlexFlashDriveSlotNumber OBJECT-TYPE
    SYNTAX       Gauge32
    MAX-ACCESS   read-only
    STATUS       current
    DESCRIPTION
        "Cisco Firepower storage:FlexFlashDrive:slotNumber
        managed object property"
    ::= { cfprApStorageFlexFlashDriveEntry 23 }

cfprApStorageFlexFlashDriveVendor OBJECT-TYPE
    SYNTAX       SnmpAdminString
    MAX-ACCESS   read-only
    STATUS       current
    DESCRIPTION
        "Cisco Firepower storage:FlexFlashDrive:vendor
        managed object property"
    ::= { cfprApStorageFlexFlashDriveEntry 24 }

cfprApStorageFlexFlashDriveVisible OBJECT-TYPE
    SYNTAX       CfprApStorageFFDriveVisible
    MAX-ACCESS   read-only
    STATUS       current
    DESCRIPTION
        "Cisco Firepower storage:FlexFlashDrive:visible
        managed object property"
    ::= { cfprApStorageFlexFlashDriveEntry 25 }

cfprApStorageFlexFlashVirtualDriveTable OBJECT-TYPE
    SYNTAX           SEQUENCE OF CfprApStorageFlexFlashVirtualDriveEntry
    MAX-ACCESS       not-accessible
    STATUS           current
    DESCRIPTION
        "Cisco Firepower storage:FlexFlashVirtualDrive
        managed object table"
    ::= { cfprApStorageObjects 16 }

cfprApStorageFlexFlashVirtualDriveEntry OBJECT-TYPE
    SYNTAX           CfprApStorageFlexFlashVirtualDriveEntry
    MAX-ACCESS       not-accessible
    STATUS           current
    DESCRIPTION
        "Entry for the cfprApStorageFlexFlashVirtualDriveTable table."
    INDEX { cfprApStorageFlexFlashVirtualDriveInstanceId }
    ::= { cfprApStorageFlexFlashVirtualDriveTable 1 }

CfprApStorageFlexFlashVirtualDriveEntry ::= SEQUENCE {
    cfprApStorageFlexFlashVirtualDriveInstanceId                     CfprApManagedObjectId,
    cfprApStorageFlexFlashVirtualDriveDn                             CfprApManagedObjectDn,
    cfprApStorageFlexFlashVirtualDriveRn                             SnmpAdminString,
    cfprApStorageFlexFlashVirtualDriveBlockSize                      Gauge32,
    cfprApStorageFlexFlashVirtualDriveConnectionProtocol             CfprApStorageConnectionProtocol,
    cfprApStorageFlexFlashVirtualDriveId                             Gauge32,
    cfprApStorageFlexFlashVirtualDriveModel                          SnmpAdminString,
    cfprApStorageFlexFlashVirtualDriveNumberOfBlocks                 Unsigned64,
    cfprApStorageFlexFlashVirtualDriveOperQualifierReason            SnmpAdminString,
    cfprApStorageFlexFlashVirtualDriveOperability                    CfprApEquipmentOperability,
    cfprApStorageFlexFlashVirtualDrivePresence                       CfprApEquipmentPresence,
    cfprApStorageFlexFlashVirtualDriveRaidHealth                     CfprApStorageFFRAIDHealth,
    cfprApStorageFlexFlashVirtualDriveRaidState                      CfprApStorageFFRAIDState,
    cfprApStorageFlexFlashVirtualDriveRevision                       SnmpAdminString,
    cfprApStorageFlexFlashVirtualDriveSerial                         SnmpAdminString,
    cfprApStorageFlexFlashVirtualDriveSize                           Unsigned64,
    cfprApStorageFlexFlashVirtualDriveType                           CfprApStorageLunType,
    cfprApStorageFlexFlashVirtualDriveVendor                         SnmpAdminString
}

cfprApStorageFlexFlashVirtualDriveInstanceId OBJECT-TYPE
    SYNTAX       CfprApManagedObjectId
    MAX-ACCESS   not-accessible
    STATUS       current
    DESCRIPTION
        "Instance identifier of the managed object."
    ::= { cfprApStorageFlexFlashVirtualDriveEntry 1 }

cfprApStorageFlexFlashVirtualDriveDn OBJECT-TYPE
    SYNTAX       CfprApManagedObjectDn
    MAX-ACCESS   read-only
    STATUS       current
    DESCRIPTION
        "Cisco Firepower storage:FlexFlashVirtualDrive:dn
        managed object property"
    ::= { cfprApStorageFlexFlashVirtualDriveEntry 2 }

cfprApStorageFlexFlashVirtualDriveRn OBJECT-TYPE
    SYNTAX       SnmpAdminString
    MAX-ACCESS   read-only
    STATUS       current
    DESCRIPTION
        "Cisco Firepower storage:FlexFlashVirtualDrive:rn
        managed object property"
    ::= { cfprApStorageFlexFlashVirtualDriveEntry 3 }

cfprApStorageFlexFlashVirtualDriveBlockSize OBJECT-TYPE
    SYNTAX       Gauge32
    MAX-ACCESS   read-only
    STATUS       current
    DESCRIPTION
        "Cisco Firepower storage:FlexFlashVirtualDrive:blockSize
        managed object property"
    ::= { cfprApStorageFlexFlashVirtualDriveEntry 4 }

cfprApStorageFlexFlashVirtualDriveConnectionProtocol OBJECT-TYPE
    SYNTAX       CfprApStorageConnectionProtocol
    MAX-ACCESS   read-only
    STATUS       current
    DESCRIPTION
        "Cisco Firepower storage:FlexFlashVirtualDrive:connectionProtocol
        managed object property"
    ::= { cfprApStorageFlexFlashVirtualDriveEntry 5 }

cfprApStorageFlexFlashVirtualDriveId OBJECT-TYPE
    SYNTAX       Gauge32
    MAX-ACCESS   read-only
    STATUS       current
    DESCRIPTION
        "Cisco Firepower storage:FlexFlashVirtualDrive:id
        managed object property"
    ::= { cfprApStorageFlexFlashVirtualDriveEntry 6 }

cfprApStorageFlexFlashVirtualDriveModel OBJECT-TYPE
    SYNTAX       SnmpAdminString
    MAX-ACCESS   read-only
    STATUS       current
    DESCRIPTION
        "Cisco Firepower storage:FlexFlashVirtualDrive:model
        managed object property"
    ::= { cfprApStorageFlexFlashVirtualDriveEntry 7 }

cfprApStorageFlexFlashVirtualDriveNumberOfBlocks OBJECT-TYPE
    SYNTAX       Unsigned64
    MAX-ACCESS   read-only
    STATUS       current
    DESCRIPTION
        "Cisco Firepower storage:FlexFlashVirtualDrive:numberOfBlocks
        managed object property"
    ::= { cfprApStorageFlexFlashVirtualDriveEntry 8 }

cfprApStorageFlexFlashVirtualDriveOperQualifierReason OBJECT-TYPE
    SYNTAX       SnmpAdminString
    MAX-ACCESS   read-only
    STATUS       current
    DESCRIPTION
        "Cisco Firepower storage:FlexFlashVirtualDrive:operQualifierReason
         managed object property"
    ::= { cfprApStorageFlexFlashVirtualDriveEntry 9 }

cfprApStorageFlexFlashVirtualDriveOperability OBJECT-TYPE
    SYNTAX       CfprApEquipmentOperability
    MAX-ACCESS   read-only
    STATUS       current
    DESCRIPTION
        "Cisco Firepower storage:FlexFlashVirtualDrive:operability
        managed object property"
    ::= { cfprApStorageFlexFlashVirtualDriveEntry 10 }

cfprApStorageFlexFlashVirtualDrivePresence OBJECT-TYPE
    SYNTAX       CfprApEquipmentPresence
    MAX-ACCESS   read-only
    STATUS       current
    DESCRIPTION
        "Cisco Firepower storage:FlexFlashVirtualDrive:presence
        managed object property"
    ::= { cfprApStorageFlexFlashVirtualDriveEntry 11 }

cfprApStorageFlexFlashVirtualDriveRaidHealth OBJECT-TYPE
    SYNTAX       CfprApStorageFFRAIDHealth
    MAX-ACCESS   read-only
    STATUS       current
    DESCRIPTION
        "Cisco Firepower storage:FlexFlashVirtualDrive:raidHealth
        managed object property"
    ::= { cfprApStorageFlexFlashVirtualDriveEntry 12 }

cfprApStorageFlexFlashVirtualDriveRaidState OBJECT-TYPE
    SYNTAX       CfprApStorageFFRAIDState
    MAX-ACCESS   read-only
    STATUS       current
    DESCRIPTION
        "Cisco Firepower storage:FlexFlashVirtualDrive:raidState
        managed object property"
    ::= { cfprApStorageFlexFlashVirtualDriveEntry 13 }

cfprApStorageFlexFlashVirtualDriveRevision OBJECT-TYPE
    SYNTAX       SnmpAdminString
    MAX-ACCESS   read-only
    STATUS       current
    DESCRIPTION
        "Cisco Firepower storage:FlexFlashVirtualDrive:revision
        managed object property"
    ::= { cfprApStorageFlexFlashVirtualDriveEntry 14 }

cfprApStorageFlexFlashVirtualDriveSerial OBJECT-TYPE
    SYNTAX       SnmpAdminString
    MAX-ACCESS   read-only
    STATUS       current
    DESCRIPTION
        "Cisco Firepower storage:FlexFlashVirtualDrive:serial
        managed object property"
    ::= { cfprApStorageFlexFlashVirtualDriveEntry 15 }

cfprApStorageFlexFlashVirtualDriveSize OBJECT-TYPE
    SYNTAX       Unsigned64
    MAX-ACCESS   read-only
    STATUS       current
    DESCRIPTION
        "Cisco Firepower storage:FlexFlashVirtualDrive:size
        managed object property"
    ::= { cfprApStorageFlexFlashVirtualDriveEntry 16 }

cfprApStorageFlexFlashVirtualDriveType OBJECT-TYPE
    SYNTAX       CfprApStorageLunType
    MAX-ACCESS   read-only
    STATUS       current
    DESCRIPTION
        "Cisco Firepower storage:FlexFlashVirtualDrive:type
        managed object property"
    ::= { cfprApStorageFlexFlashVirtualDriveEntry 17 }

cfprApStorageFlexFlashVirtualDriveVendor OBJECT-TYPE
    SYNTAX       SnmpAdminString
    MAX-ACCESS   read-only
    STATUS       current
    DESCRIPTION
        "Cisco Firepower storage:FlexFlashVirtualDrive:vendor
        managed object property"
    ::= { cfprApStorageFlexFlashVirtualDriveEntry 18 }

cfprApStorageIScsiTargetIfTable OBJECT-TYPE
    SYNTAX           SEQUENCE OF CfprApStorageIScsiTargetIfEntry
    MAX-ACCESS       not-accessible
    STATUS           current
    DESCRIPTION
        "Cisco Firepower storage:IScsiTargetIf managed object table"
    ::= { cfprApStorageObjects 17 }

cfprApStorageIScsiTargetIfEntry OBJECT-TYPE
    SYNTAX           CfprApStorageIScsiTargetIfEntry
    MAX-ACCESS       not-accessible
    STATUS           current
    DESCRIPTION
        "Entry for the cfprApStorageIScsiTargetIfTable table."
    INDEX { cfprApStorageIScsiTargetIfInstanceId }
    ::= { cfprApStorageIScsiTargetIfTable 1 }

CfprApStorageIScsiTargetIfEntry ::= SEQUENCE {
    cfprApStorageIScsiTargetIfInstanceId                             CfprApManagedObjectId,
    cfprApStorageIScsiTargetIfDn                                     CfprApManagedObjectDn,
    cfprApStorageIScsiTargetIfRn                                     SnmpAdminString,
    cfprApStorageIScsiTargetIfName                                   SnmpAdminString,
    cfprApStorageIScsiTargetIfProt                                   CfprApStorageProtocol
}

cfprApStorageIScsiTargetIfInstanceId OBJECT-TYPE
    SYNTAX       CfprApManagedObjectId
    MAX-ACCESS   not-accessible
    STATUS       current
    DESCRIPTION
        "Instance identifier of the managed object."
    ::= { cfprApStorageIScsiTargetIfEntry 1 }

cfprApStorageIScsiTargetIfDn OBJECT-TYPE
    SYNTAX       CfprApManagedObjectDn
    MAX-ACCESS   read-only
    STATUS       current
    DESCRIPTION
        "Cisco Firepower storage:IScsiTargetIf:dn managed object property"
    ::= { cfprApStorageIScsiTargetIfEntry 2 }

cfprApStorageIScsiTargetIfRn OBJECT-TYPE
    SYNTAX       SnmpAdminString
    MAX-ACCESS   read-only
    STATUS       current
    DESCRIPTION
        "Cisco Firepower storage:IScsiTargetIf:rn managed object property"
    ::= { cfprApStorageIScsiTargetIfEntry 3 }

cfprApStorageIScsiTargetIfName OBJECT-TYPE
    SYNTAX       SnmpAdminString
    MAX-ACCESS   read-only
    STATUS       current
    DESCRIPTION
        "Cisco Firepower storage:IScsiTargetIf:name managed
        object property"
    ::= { cfprApStorageIScsiTargetIfEntry 4 }

cfprApStorageIScsiTargetIfProt OBJECT-TYPE
    SYNTAX       CfprApStorageProtocol
    MAX-ACCESS   read-only
    STATUS       current
    DESCRIPTION
        "Cisco Firepower storage:IScsiTargetIf:prot managed
        object property"
    ::= { cfprApStorageIScsiTargetIfEntry 5 }

cfprApStorageItemTable OBJECT-TYPE
    SYNTAX           SEQUENCE OF CfprApStorageItemEntry
    MAX-ACCESS       not-accessible
    STATUS           current
    DESCRIPTION
        "Cisco Firepower storage:Item managed object table"
    ::= { cfprApStorageObjects 20 }

cfprApStorageItemEntry OBJECT-TYPE
    SYNTAX           CfprApStorageItemEntry
    MAX-ACCESS       not-accessible
    STATUS           current
    DESCRIPTION
        "Entry for the cfprApStorageItemTable table."
    INDEX { cfprApStorageItemInstanceId }
    ::= { cfprApStorageItemTable 1 }

CfprApStorageItemEntry ::= SEQUENCE {
    cfprApStorageItemInstanceId                                      CfprApManagedObjectId,
    cfprApStorageItemDn                                              CfprApManagedObjectDn,
    cfprApStorageItemRn                                              SnmpAdminString,
    cfprApStorageItemName                                            SnmpAdminString,
    cfprApStorageItemOperState                                       CfprApStorageFileSystemStatus,
    cfprApStorageItemSize                                            Unsigned64,
    cfprApStorageItemUsed                                            Gauge32
}

cfprApStorageItemInstanceId OBJECT-TYPE
    SYNTAX       CfprApManagedObjectId
    MAX-ACCESS   not-accessible
    STATUS       current
    DESCRIPTION
        "Instance identifier of the managed object."
    ::= { cfprApStorageItemEntry 1 }

cfprApStorageItemDn OBJECT-TYPE
    SYNTAX       CfprApManagedObjectDn
    MAX-ACCESS   read-only
    STATUS       current
    DESCRIPTION
        "Cisco Firepower storage:Item:dn managed object property"
    ::= { cfprApStorageItemEntry 2 }

cfprApStorageItemRn OBJECT-TYPE
    SYNTAX       SnmpAdminString
    MAX-ACCESS   read-only
    STATUS       current
    DESCRIPTION
        "Cisco Firepower storage:Item:rn managed object property"
    ::= { cfprApStorageItemEntry 3 }

cfprApStorageItemName OBJECT-TYPE
    SYNTAX       SnmpAdminString
    MAX-ACCESS   read-only
    STATUS       current
    DESCRIPTION
        "Cisco Firepower storage:Item:name managed object property"
    ::= { cfprApStorageItemEntry 4 }

cfprApStorageItemOperState OBJECT-TYPE
    SYNTAX       CfprApStorageFileSystemStatus
    MAX-ACCESS   read-only
    STATUS       current
    DESCRIPTION
        "Cisco Firepower storage:Item:operState managed object property"
    ::= { cfprApStorageItemEntry 5 }

cfprApStorageItemSize OBJECT-TYPE
    SYNTAX       Unsigned64
    MAX-ACCESS   read-only
    STATUS       current
    DESCRIPTION
        "Cisco Firepower storage:Item:size managed object property"
    ::= { cfprApStorageItemEntry 6 }

cfprApStorageItemUsed OBJECT-TYPE
    SYNTAX       Gauge32
    MAX-ACCESS   read-only
    STATUS       current
    DESCRIPTION
        "Cisco Firepower storage:Item:used managed object property"
    ::= { cfprApStorageItemEntry 7 }

cfprApStorageLocalDiskTable OBJECT-TYPE
    SYNTAX           SEQUENCE OF CfprApStorageLocalDiskEntry
    MAX-ACCESS       not-accessible
    STATUS           current
    DESCRIPTION
        "Cisco Firepower storage:LocalDisk managed object table"
    ::= { cfprApStorageObjects 21 }

cfprApStorageLocalDiskEntry OBJECT-TYPE
    SYNTAX           CfprApStorageLocalDiskEntry
    MAX-ACCESS       not-accessible
    STATUS           current
    DESCRIPTION
        "Entry for the cfprApStorageLocalDiskTable table."
    INDEX { cfprApStorageLocalDiskInstanceId }
    ::= { cfprApStorageLocalDiskTable 1 }

CfprApStorageLocalDiskEntry ::= SEQUENCE {
    cfprApStorageLocalDiskInstanceId                                 CfprApManagedObjectId,
    cfprApStorageLocalDiskDn                                         CfprApManagedObjectDn,
    cfprApStorageLocalDiskRn                                         SnmpAdminString,
    cfprApStorageLocalDiskBlockSize                                  Gauge32,
    cfprApStorageLocalDiskConnectionProtocol                         CfprApStorageConnectionProtocol,
    cfprApStorageLocalDiskDeviceType                                 CfprApStorageTechnology,
    cfprApStorageLocalDiskDiskState                                  CfprApStoragePDriveStatus,
    cfprApStorageLocalDiskId                                         Gauge32,
    cfprApStorageLocalDiskLc                                         CfprApFsmLifecycle,
    cfprApStorageLocalDiskLinkSpeed                                  CfprApStorageLinkSpeed,
    cfprApStorageLocalDiskModel                                      SnmpAdminString,
    cfprApStorageLocalDiskNumberOfBlocks                             Unsigned64,
    cfprApStorageLocalDiskOperQualifierReason                        SnmpAdminString,
    cfprApStorageLocalDiskOperability                                CfprApEquipmentOperability,
    cfprApStorageLocalDiskPowerState                                 CfprApStoragePowerState,
    cfprApStorageLocalDiskPresence                                   CfprApEquipmentPresence,
    cfprApStorageLocalDiskRevision                                   SnmpAdminString,
    cfprApStorageLocalDiskSerial                                     SnmpAdminString,
    cfprApStorageLocalDiskSize                                       Unsigned64,
    cfprApStorageLocalDiskVendor                                     SnmpAdminString
}

cfprApStorageLocalDiskInstanceId OBJECT-TYPE
    SYNTAX       CfprApManagedObjectId
    MAX-ACCESS   not-accessible
    STATUS       current
    DESCRIPTION
        "Instance identifier of the managed object."
    ::= { cfprApStorageLocalDiskEntry 1 }

cfprApStorageLocalDiskDn OBJECT-TYPE
    SYNTAX       CfprApManagedObjectDn
    MAX-ACCESS   read-only
    STATUS       current
    DESCRIPTION
        "Cisco Firepower storage:LocalDisk:dn managed object property"
    ::= { cfprApStorageLocalDiskEntry 2 }

cfprApStorageLocalDiskRn OBJECT-TYPE
    SYNTAX       SnmpAdminString
    MAX-ACCESS   read-only
    STATUS       current
    DESCRIPTION
        "Cisco Firepower storage:LocalDisk:rn managed object property"
    ::= { cfprApStorageLocalDiskEntry 3 }

cfprApStorageLocalDiskBlockSize OBJECT-TYPE
    SYNTAX       Gauge32
    MAX-ACCESS   read-only
    STATUS       current
    DESCRIPTION
        "Cisco Firepower storage:LocalDisk:blockSize managed
        object property"
    ::= { cfprApStorageLocalDiskEntry 4 }

cfprApStorageLocalDiskConnectionProtocol OBJECT-TYPE
    SYNTAX       CfprApStorageConnectionProtocol
    MAX-ACCESS   read-only
    STATUS       current
    DESCRIPTION
        "Cisco Firepower storage:LocalDisk:connectionProtocol
        managed object property"
    ::= { cfprApStorageLocalDiskEntry 5 }

cfprApStorageLocalDiskDeviceType OBJECT-TYPE
    SYNTAX       CfprApStorageTechnology
    MAX-ACCESS   read-only
    STATUS       current
    DESCRIPTION
        "Cisco Firepower storage:LocalDisk:deviceType managed
        object property"
    ::= { cfprApStorageLocalDiskEntry 6 }

cfprApStorageLocalDiskDiskState OBJECT-TYPE
    SYNTAX       CfprApStoragePDriveStatus
    MAX-ACCESS   read-only
    STATUS       current
    DESCRIPTION
        "Cisco Firepower storage:LocalDisk:diskState managed
        object property"
    ::= { cfprApStorageLocalDiskEntry 7 }

cfprApStorageLocalDiskId OBJECT-TYPE
    SYNTAX       Gauge32
    MAX-ACCESS   read-only
    STATUS       current
    DESCRIPTION
        "Cisco Firepower storage:LocalDisk:id managed object property"
    ::= { cfprApStorageLocalDiskEntry 8 }

cfprApStorageLocalDiskLc OBJECT-TYPE
    SYNTAX       CfprApFsmLifecycle
    MAX-ACCESS   read-only
    STATUS       current
    DESCRIPTION
        "Cisco Firepower storage:LocalDisk:lc managed object property"
    ::= { cfprApStorageLocalDiskEntry 9 }

cfprApStorageLocalDiskLinkSpeed OBJECT-TYPE
    SYNTAX       CfprApStorageLinkSpeed
    MAX-ACCESS   read-only
    STATUS       current
    DESCRIPTION
        "Cisco Firepower storage:LocalDisk:linkSpeed managed
        object property"
    ::= { cfprApStorageLocalDiskEntry 10 }

cfprApStorageLocalDiskModel OBJECT-TYPE
    SYNTAX       SnmpAdminString
    MAX-ACCESS   read-only
    STATUS       current
    DESCRIPTION
        "Cisco Firepower storage:LocalDisk:model managed object property"
    ::= { cfprApStorageLocalDiskEntry 11 }

cfprApStorageLocalDiskNumberOfBlocks OBJECT-TYPE
    SYNTAX       Unsigned64
    MAX-ACCESS   read-only
    STATUS       current
    DESCRIPTION
        "Cisco Firepower storage:LocalDisk:numberOfBlocks
        managed object property"
    ::= { cfprApStorageLocalDiskEntry 12 }

cfprApStorageLocalDiskOperQualifierReason OBJECT-TYPE
    SYNTAX       SnmpAdminString
    MAX-ACCESS   read-only
    STATUS       current
    DESCRIPTION
        "Cisco Firepower storage:LocalDisk:operQualifierReason
        managed object property"
    ::= { cfprApStorageLocalDiskEntry 13 }

cfprApStorageLocalDiskOperability OBJECT-TYPE
    SYNTAX       CfprApEquipmentOperability
    MAX-ACCESS   read-only
    STATUS       current
    DESCRIPTION
        "Cisco Firepower storage:LocalDisk:operability
        managed object property"
    ::= { cfprApStorageLocalDiskEntry 14 }

cfprApStorageLocalDiskPowerState OBJECT-TYPE
    SYNTAX       CfprApStoragePowerState
    MAX-ACCESS   read-only
    STATUS       current
    DESCRIPTION
        "Cisco Firepower storage:LocalDisk:powerState managed
        object property"
    ::= { cfprApStorageLocalDiskEntry 15 }

cfprApStorageLocalDiskPresence OBJECT-TYPE
    SYNTAX       CfprApEquipmentPresence
    MAX-ACCESS   read-only
    STATUS       current
    DESCRIPTION
        "Cisco Firepower storage:LocalDisk:presence managed
        object property"
    ::= { cfprApStorageLocalDiskEntry 16 }

cfprApStorageLocalDiskRevision OBJECT-TYPE
    SYNTAX       SnmpAdminString
    MAX-ACCESS   read-only
    STATUS       current
    DESCRIPTION
        "Cisco Firepower storage:LocalDisk:revision managed
        object property"
    ::= { cfprApStorageLocalDiskEntry 17 }

cfprApStorageLocalDiskSerial OBJECT-TYPE
    SYNTAX       SnmpAdminString
    MAX-ACCESS   read-only
    STATUS       current
    DESCRIPTION
        "Cisco Firepower storage:LocalDisk:serial managed object property"
    ::= { cfprApStorageLocalDiskEntry 18 }

cfprApStorageLocalDiskSize OBJECT-TYPE
    SYNTAX       Unsigned64
    MAX-ACCESS   read-only
    STATUS       current
    DESCRIPTION
        "Cisco Firepower storage:LocalDisk:size managed object property"
    ::= { cfprApStorageLocalDiskEntry 19 }

cfprApStorageLocalDiskVendor OBJECT-TYPE
    SYNTAX       SnmpAdminString
    MAX-ACCESS   read-only
    STATUS       current
    DESCRIPTION
        "Cisco Firepower storage:LocalDisk:vendor managed object property"
    ::= { cfprApStorageLocalDiskEntry 20 }

cfprApStorageLocalDiskConfigDefTable OBJECT-TYPE
    SYNTAX           SEQUENCE OF CfprApStorageLocalDiskConfigDefEntry
    MAX-ACCESS       not-accessible
    STATUS           current
    DESCRIPTION
        "Cisco Firepower storage:LocalDiskConfigDef managed object table"
    ::= { cfprApStorageObjects 22 }

cfprApStorageLocalDiskConfigDefEntry OBJECT-TYPE
    SYNTAX           CfprApStorageLocalDiskConfigDefEntry
    MAX-ACCESS       not-accessible
    STATUS           current
    DESCRIPTION
        "Entry for the cfprApStorageLocalDiskConfigDefTable table."
    INDEX { cfprApStorageLocalDiskConfigDefInstanceId }
    ::= { cfprApStorageLocalDiskConfigDefTable 1 }

CfprApStorageLocalDiskConfigDefEntry ::= SEQUENCE {
    cfprApStorageLocalDiskConfigDefInstanceId                        CfprApManagedObjectId,
    cfprApStorageLocalDiskConfigDefDn                                CfprApManagedObjectDn,
    cfprApStorageLocalDiskConfigDefRn                                SnmpAdminString,
    cfprApStorageLocalDiskConfigDefDescr                             SnmpAdminString,
    cfprApStorageLocalDiskConfigDefFlexFlashRAIDReportingState       CfprApStorageLocalDiskConfigFlexFlashRAIDReportingState,
    cfprApStorageLocalDiskConfigDefFlexFlashState                    CfprApStorageLocalDiskConfigFlexFlashState,
    cfprApStorageLocalDiskConfigDefIntId                             SnmpAdminString,
    cfprApStorageLocalDiskConfigDefMode                              CfprApStorageLocalDiskMode,
    cfprApStorageLocalDiskConfigDefName                              SnmpAdminString,
    cfprApStorageLocalDiskConfigDefPolicyLevel                       Gauge32,
    cfprApStorageLocalDiskConfigDefPolicyOwner                       CfprApPolicyPolicyOwner,
    cfprApStorageLocalDiskConfigDefProtectConfig                     TruthValue
}

cfprApStorageLocalDiskConfigDefInstanceId OBJECT-TYPE
    SYNTAX       CfprApManagedObjectId
    MAX-ACCESS   not-accessible
    STATUS       current
    DESCRIPTION
        "Instance identifier of the managed object."
    ::= { cfprApStorageLocalDiskConfigDefEntry 1 }

cfprApStorageLocalDiskConfigDefDn OBJECT-TYPE
    SYNTAX       CfprApManagedObjectDn
    MAX-ACCESS   read-only
    STATUS       current
    DESCRIPTION
        "Cisco Firepower storage:LocalDiskConfigDef:dn
        managed object property"
    ::= { cfprApStorageLocalDiskConfigDefEntry 2 }

cfprApStorageLocalDiskConfigDefRn OBJECT-TYPE
    SYNTAX       SnmpAdminString
    MAX-ACCESS   read-only
    STATUS       current
    DESCRIPTION
        "Cisco Firepower storage:LocalDiskConfigDef:rn
        managed object property"
    ::= { cfprApStorageLocalDiskConfigDefEntry 3 }

cfprApStorageLocalDiskConfigDefDescr OBJECT-TYPE
    SYNTAX       SnmpAdminString
    MAX-ACCESS   read-only
    STATUS       current
    DESCRIPTION
        "Cisco Firepower storage:LocalDiskConfigDef:descr
        managed object property"
    ::= { cfprApStorageLocalDiskConfigDefEntry 4 }

cfprApStorageLocalDiskConfigDefFlexFlashRAIDReportingState OBJECT-TYPE
    SYNTAX       CfprApStorageLocalDiskConfigFlexFlashRAIDReportingState
    MAX-ACCESS   read-only
    STATUS       current
    DESCRIPTION
        "Cisco Firepower storage:LocalDiskConfigDef:flexFlashRAIDReporting
        State managed object property"
    ::= { cfprApStorageLocalDiskConfigDefEntry 5 }

cfprApStorageLocalDiskConfigDefFlexFlashState OBJECT-TYPE
    SYNTAX       CfprApStorageLocalDiskConfigFlexFlashState
    MAX-ACCESS   read-only
    STATUS       current
    DESCRIPTION
        "Cisco Firepower storage:LocalDiskConfigDef:flexFlashState
        managed object property"
    ::= { cfprApStorageLocalDiskConfigDefEntry 6 }

cfprApStorageLocalDiskConfigDefIntId OBJECT-TYPE
    SYNTAX       SnmpAdminString
    MAX-ACCESS   read-only
    STATUS       current
    DESCRIPTION
        "Cisco Firepower storage:LocalDiskConfigDef:intId
        managed object property"
    ::= { cfprApStorageLocalDiskConfigDefEntry 7 }

cfprApStorageLocalDiskConfigDefMode OBJECT-TYPE
    SYNTAX       CfprApStorageLocalDiskMode
    MAX-ACCESS   read-only
    STATUS       current
    DESCRIPTION
        "Cisco Firepower storage:LocalDiskConfigDef:mode
        managed object property"
    ::= { cfprApStorageLocalDiskConfigDefEntry 8 }

cfprApStorageLocalDiskConfigDefName OBJECT-TYPE
    SYNTAX       SnmpAdminString
    MAX-ACCESS   read-only
    STATUS       current
    DESCRIPTION
        "Cisco Firepower storage:LocalDiskConfigDef:name
        managed object property"
    ::= { cfprApStorageLocalDiskConfigDefEntry 9 }

cfprApStorageLocalDiskConfigDefPolicyLevel OBJECT-TYPE
    SYNTAX       Gauge32
    MAX-ACCESS   read-only
    STATUS       current
    DESCRIPTION
        "Cisco Firepower storage:LocalDiskConfigDef:policyLevel
        managed object property"
    ::= { cfprApStorageLocalDiskConfigDefEntry 10 }

cfprApStorageLocalDiskConfigDefPolicyOwner OBJECT-TYPE
    SYNTAX       CfprApPolicyPolicyOwner
    MAX-ACCESS   read-only
    STATUS       current
    DESCRIPTION
        "Cisco Firepower storage:LocalDiskConfigDef:policyOwner
        managed object property"
    ::= { cfprApStorageLocalDiskConfigDefEntry 11 }

cfprApStorageLocalDiskConfigDefProtectConfig OBJECT-TYPE
    SYNTAX       TruthValue
    MAX-ACCESS   read-only
    STATUS       current
    DESCRIPTION
        "Cisco Firepower storage:LocalDiskConfigDef:protectConfig
        managed object property"
    ::= { cfprApStorageLocalDiskConfigDefEntry 12 }

cfprApStorageLocalDiskConfigPolicyTable OBJECT-TYPE
    SYNTAX           SEQUENCE OF CfprApStorageLocalDiskConfigPolicyEntry
    MAX-ACCESS       not-accessible
    STATUS           current
    DESCRIPTION
        "Cisco Firepower storage:LocalDiskConfigPolicy
        managed object table"
    ::= { cfprApStorageObjects 23 }

cfprApStorageLocalDiskConfigPolicyEntry OBJECT-TYPE
    SYNTAX           CfprApStorageLocalDiskConfigPolicyEntry
    MAX-ACCESS       not-accessible
    STATUS           current
    DESCRIPTION
        "Entry for the cfprApStorageLocalDiskConfigPolicyTable table."
    INDEX { cfprApStorageLocalDiskConfigPolicyInstanceId }
    ::= { cfprApStorageLocalDiskConfigPolicyTable 1 }

CfprApStorageLocalDiskConfigPolicyEntry ::= SEQUENCE {
    cfprApStorageLocalDiskConfigPolicyInstanceId                     CfprApManagedObjectId,
    cfprApStorageLocalDiskConfigPolicyDn                             CfprApManagedObjectDn,
    cfprApStorageLocalDiskConfigPolicyRn                             SnmpAdminString,
    cfprApStorageLocalDiskConfigPolicyDescr                          SnmpAdminString,
    cfprApStorageLocalDiskConfigPolicyFlexFlashRAIDReportingState    CfprApStorageLocalDiskConfigFlexFlashRAIDReportingState,
    cfprApStorageLocalDiskConfigPolicyFlexFlashState                 CfprApStorageLocalDiskConfigFlexFlashState,
    cfprApStorageLocalDiskConfigPolicyIntId                          SnmpAdminString,
    cfprApStorageLocalDiskConfigPolicyMode                           CfprApStorageLocalDiskMode,
    cfprApStorageLocalDiskConfigPolicyName                           SnmpAdminString,
    cfprApStorageLocalDiskConfigPolicyPolicyLevel                    Gauge32,
    cfprApStorageLocalDiskConfigPolicyPolicyOwner                    CfprApPolicyPolicyOwner,
    cfprApStorageLocalDiskConfigPolicyProtectConfig                  TruthValue
}

cfprApStorageLocalDiskConfigPolicyInstanceId OBJECT-TYPE
    SYNTAX       CfprApManagedObjectId
    MAX-ACCESS   not-accessible
    STATUS       current
    DESCRIPTION
        "Instance identifier of the managed object."
    ::= { cfprApStorageLocalDiskConfigPolicyEntry 1 }

cfprApStorageLocalDiskConfigPolicyDn OBJECT-TYPE
    SYNTAX       CfprApManagedObjectDn
    MAX-ACCESS   read-only
    STATUS       current
    DESCRIPTION
        "Cisco Firepower storage:LocalDiskConfigPolicy:dn
        managed object property"
    ::= { cfprApStorageLocalDiskConfigPolicyEntry 2 }

cfprApStorageLocalDiskConfigPolicyRn OBJECT-TYPE
    SYNTAX       SnmpAdminString
    MAX-ACCESS   read-only
    STATUS       current
    DESCRIPTION
        "Cisco Firepower storage:LocalDiskConfigPolicy:rn
        managed object property"
    ::= { cfprApStorageLocalDiskConfigPolicyEntry 3 }

cfprApStorageLocalDiskConfigPolicyDescr OBJECT-TYPE
    SYNTAX       SnmpAdminString
    MAX-ACCESS   read-only
    STATUS       current
    DESCRIPTION
        "Cisco Firepower storage:LocalDiskConfigPolicy:descr
        managed object property"
    ::= { cfprApStorageLocalDiskConfigPolicyEntry 4 }

cfprApStorageLocalDiskConfigPolicyFlexFlashRAIDReportingState OBJECT-TYPE
    SYNTAX       CfprApStorageLocalDiskConfigFlexFlashRAIDReportingState
    MAX-ACCESS   read-only
    STATUS       current
    DESCRIPTION
        "Cisco Firepower storage:LocalDiskConfigPolicy:flexFlashRAIDReport
        ingState managed object property"
    ::= { cfprApStorageLocalDiskConfigPolicyEntry 5 }

cfprApStorageLocalDiskConfigPolicyFlexFlashState OBJECT-TYPE
    SYNTAX       CfprApStorageLocalDiskConfigFlexFlashState
    MAX-ACCESS   read-only
    STATUS       current
    DESCRIPTION
        "Cisco Firepower storage:LocalDiskConfigPolicy:flexFlashState
        managed object property"
    ::= { cfprApStorageLocalDiskConfigPolicyEntry 6 }

cfprApStorageLocalDiskConfigPolicyIntId OBJECT-TYPE
    SYNTAX       SnmpAdminString
    MAX-ACCESS   read-only
    STATUS       current
    DESCRIPTION
        "Cisco Firepower storage:LocalDiskConfigPolicy:intId
        managed object property"
    ::= { cfprApStorageLocalDiskConfigPolicyEntry 7 }

cfprApStorageLocalDiskConfigPolicyMode OBJECT-TYPE
    SYNTAX       CfprApStorageLocalDiskMode
    MAX-ACCESS   read-only
    STATUS       current
    DESCRIPTION
        "Cisco Firepower storage:LocalDiskConfigPolicy:mode
        managed object property"
    ::= { cfprApStorageLocalDiskConfigPolicyEntry 8 }

cfprApStorageLocalDiskConfigPolicyName OBJECT-TYPE
    SYNTAX       SnmpAdminString
    MAX-ACCESS   read-only
    STATUS       current
    DESCRIPTION
        "Cisco Firepower storage:LocalDiskConfigPolicy:name
        managed object property"
    ::= { cfprApStorageLocalDiskConfigPolicyEntry 9 }

cfprApStorageLocalDiskConfigPolicyPolicyLevel OBJECT-TYPE
    SYNTAX       Gauge32
    MAX-ACCESS   read-only
    STATUS       current
    DESCRIPTION
        "Cisco Firepower storage:LocalDiskConfigPolicy:policyLevel
        managed object property"
    ::= { cfprApStorageLocalDiskConfigPolicyEntry 10 }

cfprApStorageLocalDiskConfigPolicyPolicyOwner OBJECT-TYPE
    SYNTAX       CfprApPolicyPolicyOwner
    MAX-ACCESS   read-only
    STATUS       current
    DESCRIPTION
        "Cisco Firepower storage:LocalDiskConfigPolicy:policyOwner
        managed object property"
    ::= { cfprApStorageLocalDiskConfigPolicyEntry 11 }

cfprApStorageLocalDiskConfigPolicyProtectConfig OBJECT-TYPE
    SYNTAX       TruthValue
    MAX-ACCESS   read-only
    STATUS       current
    DESCRIPTION
        "Cisco Firepower storage:LocalDiskConfigPolicy:protectConfig
        managed object property"
    ::= { cfprApStorageLocalDiskConfigPolicyEntry 12 }

cfprApStorageLocalDiskPartitionTable OBJECT-TYPE
    SYNTAX           SEQUENCE OF CfprApStorageLocalDiskPartitionEntry
    MAX-ACCESS       not-accessible
    STATUS           current
    DESCRIPTION
        "Cisco Firepower storage:LocalDiskPartition managed object table"
    ::= { cfprApStorageObjects 24 }

cfprApStorageLocalDiskPartitionEntry OBJECT-TYPE
    SYNTAX           CfprApStorageLocalDiskPartitionEntry
    MAX-ACCESS       not-accessible
    STATUS           current
    DESCRIPTION
        "Entry for the cfprApStorageLocalDiskPartitionTable table."
    INDEX { cfprApStorageLocalDiskPartitionInstanceId }
    ::= { cfprApStorageLocalDiskPartitionTable 1 }

CfprApStorageLocalDiskPartitionEntry ::= SEQUENCE {
    cfprApStorageLocalDiskPartitionInstanceId                        CfprApManagedObjectId,
    cfprApStorageLocalDiskPartitionDn                                CfprApManagedObjectDn,
    cfprApStorageLocalDiskPartitionRn                                SnmpAdminString,
    cfprApStorageLocalDiskPartitionDescr                             SnmpAdminString,
    cfprApStorageLocalDiskPartitionIntId                             SnmpAdminString,
    cfprApStorageLocalDiskPartitionName                              SnmpAdminString,
    cfprApStorageLocalDiskPartitionOrder                             Gauge32,
    cfprApStorageLocalDiskPartitionPolicyLevel                       Gauge32,
    cfprApStorageLocalDiskPartitionPolicyOwner                       CfprApPolicyPolicyOwner,
    cfprApStorageLocalDiskPartitionSize                              Unsigned64,
    cfprApStorageLocalDiskPartitionType                              CfprApStorageLocalDiskPartitionType
}

cfprApStorageLocalDiskPartitionInstanceId OBJECT-TYPE
    SYNTAX       CfprApManagedObjectId
    MAX-ACCESS   not-accessible
    STATUS       current
    DESCRIPTION
        "Instance identifier of the managed object."
    ::= { cfprApStorageLocalDiskPartitionEntry 1 }

cfprApStorageLocalDiskPartitionDn OBJECT-TYPE
    SYNTAX       CfprApManagedObjectDn
    MAX-ACCESS   read-only
    STATUS       current
    DESCRIPTION
        "Cisco Firepower storage:LocalDiskPartition:dn
        managed object property"
    ::= { cfprApStorageLocalDiskPartitionEntry 2 }

cfprApStorageLocalDiskPartitionRn OBJECT-TYPE
    SYNTAX       SnmpAdminString
    MAX-ACCESS   read-only
    STATUS       current
    DESCRIPTION
        "Cisco Firepower storage:LocalDiskPartition:rn
        managed object property"
    ::= { cfprApStorageLocalDiskPartitionEntry 3 }

cfprApStorageLocalDiskPartitionDescr OBJECT-TYPE
    SYNTAX       SnmpAdminString
    MAX-ACCESS   read-only
    STATUS       current
    DESCRIPTION
        "Cisco Firepower storage:LocalDiskPartition:descr
        managed object property"
    ::= { cfprApStorageLocalDiskPartitionEntry 4 }

cfprApStorageLocalDiskPartitionIntId OBJECT-TYPE
    SYNTAX       SnmpAdminString
    MAX-ACCESS   read-only
    STATUS       current
    DESCRIPTION
        "Cisco Firepower storage:LocalDiskPartition:intId
        managed object property"
    ::= { cfprApStorageLocalDiskPartitionEntry 5 }

cfprApStorageLocalDiskPartitionName OBJECT-TYPE
    SYNTAX       SnmpAdminString
    MAX-ACCESS   read-only
    STATUS       current
    DESCRIPTION
        "Cisco Firepower storage:LocalDiskPartition:name
        managed object property"
    ::= { cfprApStorageLocalDiskPartitionEntry 6 }

cfprApStorageLocalDiskPartitionOrder OBJECT-TYPE
    SYNTAX       Gauge32
    MAX-ACCESS   read-only
    STATUS       current
    DESCRIPTION
        "Cisco Firepower storage:LocalDiskPartition:order
        managed object property"
    ::= { cfprApStorageLocalDiskPartitionEntry 7 }

cfprApStorageLocalDiskPartitionPolicyLevel OBJECT-TYPE
    SYNTAX       Gauge32
    MAX-ACCESS   read-only
    STATUS       current
    DESCRIPTION
        "Cisco Firepower storage:LocalDiskPartition:policyLevel
        managed object property"
    ::= { cfprApStorageLocalDiskPartitionEntry 8 }

cfprApStorageLocalDiskPartitionPolicyOwner OBJECT-TYPE
    SYNTAX       CfprApPolicyPolicyOwner
    MAX-ACCESS   read-only
    STATUS       current
    DESCRIPTION
        "Cisco Firepower storage:LocalDiskPartition:policyOwner
        managed object property"
    ::= { cfprApStorageLocalDiskPartitionEntry 9 }

cfprApStorageLocalDiskPartitionSize OBJECT-TYPE
    SYNTAX       Unsigned64
    MAX-ACCESS   read-only
    STATUS       current
    DESCRIPTION
        "Cisco Firepower storage:LocalDiskPartition:size
        managed object property"
    ::= { cfprApStorageLocalDiskPartitionEntry 10 }

cfprApStorageLocalDiskPartitionType OBJECT-TYPE
    SYNTAX       CfprApStorageLocalDiskPartitionType
    MAX-ACCESS   read-only
    STATUS       current
    DESCRIPTION
        "Cisco Firepower storage:LocalDiskPartition:type
        managed object property"
    ::= { cfprApStorageLocalDiskPartitionEntry 11 }

cfprApStorageLocalDiskSlotEpTable OBJECT-TYPE
    SYNTAX           SEQUENCE OF CfprApStorageLocalDiskSlotEpEntry
    MAX-ACCESS       not-accessible
    STATUS           current
    DESCRIPTION
        "Cisco Firepower storage:LocalDiskSlotEp managed object table"
    ::= { cfprApStorageObjects 25 }

cfprApStorageLocalDiskSlotEpEntry OBJECT-TYPE
    SYNTAX           CfprApStorageLocalDiskSlotEpEntry
    MAX-ACCESS       not-accessible
    STATUS           current
    DESCRIPTION
        "Entry for the cfprApStorageLocalDiskSlotEpTable table."
    INDEX { cfprApStorageLocalDiskSlotEpInstanceId }
    ::= { cfprApStorageLocalDiskSlotEpTable 1 }

CfprApStorageLocalDiskSlotEpEntry ::= SEQUENCE {
    cfprApStorageLocalDiskSlotEpInstanceId                           CfprApManagedObjectId,
    cfprApStorageLocalDiskSlotEpDn                                   CfprApManagedObjectDn,
    cfprApStorageLocalDiskSlotEpRn                                   SnmpAdminString,
    cfprApStorageLocalDiskSlotEpConfiguration                        CfprApStorageConfiguration,
    cfprApStorageLocalDiskSlotEpId                                   Gauge32,
    cfprApStorageLocalDiskSlotEpOperQualifierReason                  SnmpAdminString,
    cfprApStorageLocalDiskSlotEpOperability                          CfprApEquipmentOperability,
    cfprApStorageLocalDiskSlotEpPeerDn                               SnmpAdminString,
    cfprApStorageLocalDiskSlotEpPresence                             CfprApEquipmentPresence
}

cfprApStorageLocalDiskSlotEpInstanceId OBJECT-TYPE
    SYNTAX       CfprApManagedObjectId
    MAX-ACCESS   not-accessible
    STATUS       current
    DESCRIPTION
        "Instance identifier of the managed object."
    ::= { cfprApStorageLocalDiskSlotEpEntry 1 }

cfprApStorageLocalDiskSlotEpDn OBJECT-TYPE
    SYNTAX       CfprApManagedObjectDn
    MAX-ACCESS   read-only
    STATUS       current
    DESCRIPTION
        "Cisco Firepower storage:LocalDiskSlotEp:dn managed
        object property"
    ::= { cfprApStorageLocalDiskSlotEpEntry 2 }

cfprApStorageLocalDiskSlotEpRn OBJECT-TYPE
    SYNTAX       SnmpAdminString
    MAX-ACCESS   read-only
    STATUS       current
    DESCRIPTION
        "Cisco Firepower storage:LocalDiskSlotEp:rn managed
        object property"
    ::= { cfprApStorageLocalDiskSlotEpEntry 3 }

cfprApStorageLocalDiskSlotEpConfiguration OBJECT-TYPE
    SYNTAX       CfprApStorageConfiguration
    MAX-ACCESS   read-only
    STATUS       current
    DESCRIPTION
        "Cisco Firepower storage:LocalDiskSlotEp:configuration
        managed object property"
    ::= { cfprApStorageLocalDiskSlotEpEntry 4 }

cfprApStorageLocalDiskSlotEpId OBJECT-TYPE
    SYNTAX       Gauge32
    MAX-ACCESS   read-only
    STATUS       current
    DESCRIPTION
        "Cisco Firepower storage:LocalDiskSlotEp:id managed
        object property"
    ::= { cfprApStorageLocalDiskSlotEpEntry 5 }

cfprApStorageLocalDiskSlotEpOperQualifierReason OBJECT-TYPE
    SYNTAX       SnmpAdminString
    MAX-ACCESS   read-only
    STATUS       current
    DESCRIPTION
        "Cisco Firepower storage:LocalDiskSlotEp:operQualifierReason
        managed object property"
    ::= { cfprApStorageLocalDiskSlotEpEntry 6 }

cfprApStorageLocalDiskSlotEpOperability OBJECT-TYPE
    SYNTAX       CfprApEquipmentOperability
    MAX-ACCESS   read-only
    STATUS       current
    DESCRIPTION
        "Cisco Firepower storage:LocalDiskSlotEp:operability
        managed object property"
    ::= { cfprApStorageLocalDiskSlotEpEntry 7 }

cfprApStorageLocalDiskSlotEpPeerDn OBJECT-TYPE
    SYNTAX       SnmpAdminString
    MAX-ACCESS   read-only
    STATUS       current
    DESCRIPTION
        "Cisco Firepower storage:LocalDiskSlotEp:peerDn
        managed object property"
    ::= { cfprApStorageLocalDiskSlotEpEntry 8 }

cfprApStorageLocalDiskSlotEpPresence OBJECT-TYPE
    SYNTAX       CfprApEquipmentPresence
    MAX-ACCESS   read-only
    STATUS       current
    DESCRIPTION
        "Cisco Firepower storage:LocalDiskSlotEp:presence
        managed object property"
    ::= { cfprApStorageLocalDiskSlotEpEntry 9 }

cfprApStorageLocalLunTable OBJECT-TYPE
    SYNTAX           SEQUENCE OF CfprApStorageLocalLunEntry
    MAX-ACCESS       not-accessible
    STATUS           current
    DESCRIPTION
        "Cisco Firepower storage:LocalLun managed object table"
    ::= { cfprApStorageObjects 26 }

cfprApStorageLocalLunEntry OBJECT-TYPE
    SYNTAX           CfprApStorageLocalLunEntry
    MAX-ACCESS       not-accessible
    STATUS           current
    DESCRIPTION
        "Entry for the cfprApStorageLocalLunTable table."
    INDEX { cfprApStorageLocalLunInstanceId }
    ::= { cfprApStorageLocalLunTable 1 }

CfprApStorageLocalLunEntry ::= SEQUENCE {
    cfprApStorageLocalLunInstanceId                                  CfprApManagedObjectId,
    cfprApStorageLocalLunDn                                          CfprApManagedObjectDn,
    cfprApStorageLocalLunRn                                          SnmpAdminString,
    cfprApStorageLocalLunBlockSize                                   Gauge32,
    cfprApStorageLocalLunConnectionProtocol                          CfprApStorageConnectionProtocol,
    cfprApStorageLocalLunId                                          Gauge32,
    cfprApStorageLocalLunLc                                          CfprApFsmLifecycle,
    cfprApStorageLocalLunModel                                       SnmpAdminString,
    cfprApStorageLocalLunNumberOfBlocks                              Unsigned64,
    cfprApStorageLocalLunOperQualifierReason                         SnmpAdminString,
    cfprApStorageLocalLunOperability                                 CfprApEquipmentOperability,
    cfprApStorageLocalLunPresence                                    CfprApEquipmentPresence,
    cfprApStorageLocalLunRevision                                    SnmpAdminString,
    cfprApStorageLocalLunSerial                                      SnmpAdminString,
    cfprApStorageLocalLunSize                                        Unsigned64,
    cfprApStorageLocalLunType                                        CfprApStorageLunType,
    cfprApStorageLocalLunVendor                                      SnmpAdminString
}

cfprApStorageLocalLunInstanceId OBJECT-TYPE
    SYNTAX       CfprApManagedObjectId
    MAX-ACCESS   not-accessible
    STATUS       current
    DESCRIPTION
        "Instance identifier of the managed object."
    ::= { cfprApStorageLocalLunEntry 1 }

cfprApStorageLocalLunDn OBJECT-TYPE
    SYNTAX       CfprApManagedObjectDn
    MAX-ACCESS   read-only
    STATUS       current
    DESCRIPTION
        "Cisco Firepower storage:LocalLun:dn managed object property"
    ::= { cfprApStorageLocalLunEntry 2 }

cfprApStorageLocalLunRn OBJECT-TYPE
    SYNTAX       SnmpAdminString
    MAX-ACCESS   read-only
    STATUS       current
    DESCRIPTION
        "Cisco Firepower storage:LocalLun:rn managed object property"
    ::= { cfprApStorageLocalLunEntry 3 }

cfprApStorageLocalLunBlockSize OBJECT-TYPE
    SYNTAX       Gauge32
    MAX-ACCESS   read-only
    STATUS       current
    DESCRIPTION
        "Cisco Firepower storage:LocalLun:blockSize managed
        object property"
    ::= { cfprApStorageLocalLunEntry 4 }

cfprApStorageLocalLunConnectionProtocol OBJECT-TYPE
    SYNTAX       CfprApStorageConnectionProtocol
    MAX-ACCESS   read-only
    STATUS       current
    DESCRIPTION
        "Cisco Firepower storage:LocalLun:connectionProtocol
        managed object property"
    ::= { cfprApStorageLocalLunEntry 5 }

cfprApStorageLocalLunId OBJECT-TYPE
    SYNTAX       Gauge32
    MAX-ACCESS   read-only
    STATUS       current
    DESCRIPTION
        "Cisco Firepower storage:LocalLun:id managed object property"
    ::= { cfprApStorageLocalLunEntry 6 }

cfprApStorageLocalLunLc OBJECT-TYPE
    SYNTAX       CfprApFsmLifecycle
    MAX-ACCESS   read-only
    STATUS       current
    DESCRIPTION
        "Cisco Firepower storage:LocalLun:lc managed object property"
    ::= { cfprApStorageLocalLunEntry 7 }

cfprApStorageLocalLunModel OBJECT-TYPE
    SYNTAX       SnmpAdminString
    MAX-ACCESS   read-only
    STATUS       current
    DESCRIPTION
        "Cisco Firepower storage:LocalLun:model managed object property"
    ::= { cfprApStorageLocalLunEntry 8 }

cfprApStorageLocalLunNumberOfBlocks OBJECT-TYPE
    SYNTAX       Unsigned64
    MAX-ACCESS   read-only
    STATUS       current
    DESCRIPTION
        "Cisco Firepower storage:LocalLun:numberOfBlocks
        managed object property"
    ::= { cfprApStorageLocalLunEntry 9 }

cfprApStorageLocalLunOperQualifierReason OBJECT-TYPE
    SYNTAX       SnmpAdminString
    MAX-ACCESS   read-only
    STATUS       current
    DESCRIPTION
        "Cisco Firepower storage:LocalLun:operQualifierReason
        managed object property"
    ::= { cfprApStorageLocalLunEntry 10 }

cfprApStorageLocalLunOperability OBJECT-TYPE
    SYNTAX       CfprApEquipmentOperability
    MAX-ACCESS   read-only
    STATUS       current
    DESCRIPTION
        "Cisco Firepower storage:LocalLun:operability managed
        object property"
    ::= { cfprApStorageLocalLunEntry 11 }

cfprApStorageLocalLunPresence OBJECT-TYPE
    SYNTAX       CfprApEquipmentPresence
    MAX-ACCESS   read-only
    STATUS       current
    DESCRIPTION
        "Cisco Firepower storage:LocalLun:presence managed
        object property"
    ::= { cfprApStorageLocalLunEntry 12 }

cfprApStorageLocalLunRevision OBJECT-TYPE
    SYNTAX       SnmpAdminString
    MAX-ACCESS   read-only
    STATUS       current
    DESCRIPTION
        "Cisco Firepower storage:LocalLun:revision managed
        object property"
    ::= { cfprApStorageLocalLunEntry 13 }

cfprApStorageLocalLunSerial OBJECT-TYPE
    SYNTAX       SnmpAdminString
    MAX-ACCESS   read-only
    STATUS       current
    DESCRIPTION
        "Cisco Firepower storage:LocalLun:serial managed object property"
    ::= { cfprApStorageLocalLunEntry 14 }

cfprApStorageLocalLunSize OBJECT-TYPE
    SYNTAX       Unsigned64
    MAX-ACCESS   read-only
    STATUS       current
    DESCRIPTION
        "Cisco Firepower storage:LocalLun:size managed object property"
    ::= { cfprApStorageLocalLunEntry 15 }

cfprApStorageLocalLunType OBJECT-TYPE
    SYNTAX       CfprApStorageLunType
    MAX-ACCESS   read-only
    STATUS       current
    DESCRIPTION
        "Cisco Firepower storage:LocalLun:type managed object property"
    ::= { cfprApStorageLocalLunEntry 16 }

cfprApStorageLocalLunVendor OBJECT-TYPE
    SYNTAX       SnmpAdminString
    MAX-ACCESS   read-only
    STATUS       current
    DESCRIPTION
        "Cisco Firepower storage:LocalLun:vendor managed object property"
    ::= { cfprApStorageLocalLunEntry 17 }

cfprApStorageLunDiskTable OBJECT-TYPE
    SYNTAX           SEQUENCE OF CfprApStorageLunDiskEntry
    MAX-ACCESS       not-accessible
    STATUS           current
    DESCRIPTION
        "Cisco Firepower storage:LunDisk managed object table"
    ::= { cfprApStorageObjects 27 }

cfprApStorageLunDiskEntry OBJECT-TYPE
    SYNTAX           CfprApStorageLunDiskEntry
    MAX-ACCESS       not-accessible
    STATUS           current
    DESCRIPTION
        "Entry for the cfprApStorageLunDiskTable table."
    INDEX { cfprApStorageLunDiskInstanceId }
    ::= { cfprApStorageLunDiskTable 1 }

CfprApStorageLunDiskEntry ::= SEQUENCE {
    cfprApStorageLunDiskInstanceId                                   CfprApManagedObjectId,
    cfprApStorageLunDiskDn                                           CfprApManagedObjectDn,
    cfprApStorageLunDiskRn                                           SnmpAdminString,
    cfprApStorageLunDiskId                                           Gauge32
}

cfprApStorageLunDiskInstanceId OBJECT-TYPE
    SYNTAX       CfprApManagedObjectId
    MAX-ACCESS   not-accessible
    STATUS       current
    DESCRIPTION
        "Instance identifier of the managed object."
    ::= { cfprApStorageLunDiskEntry 1 }

cfprApStorageLunDiskDn OBJECT-TYPE
    SYNTAX       CfprApManagedObjectDn
    MAX-ACCESS   read-only
    STATUS       current
    DESCRIPTION
        "Cisco Firepower storage:LunDisk:dn managed object property"
    ::= { cfprApStorageLunDiskEntry 2 }

cfprApStorageLunDiskRn OBJECT-TYPE
    SYNTAX       SnmpAdminString
    MAX-ACCESS   read-only
    STATUS       current
    DESCRIPTION
        "Cisco Firepower storage:LunDisk:rn managed object property"
    ::= { cfprApStorageLunDiskEntry 3 }

cfprApStorageLunDiskId OBJECT-TYPE
    SYNTAX       Gauge32
    MAX-ACCESS   read-only
    STATUS       current
    DESCRIPTION
        "Cisco Firepower storage:LunDisk:id managed object property"
    ::= { cfprApStorageLunDiskEntry 4 }

cfprApStorageMezzFlashLifeTable OBJECT-TYPE
    SYNTAX           SEQUENCE OF CfprApStorageMezzFlashLifeEntry
    MAX-ACCESS       not-accessible
    STATUS           current
    DESCRIPTION
        "Cisco Firepower storage:MezzFlashLife managed object table"
    ::= { cfprApStorageObjects 28 }

cfprApStorageMezzFlashLifeEntry OBJECT-TYPE
    SYNTAX           CfprApStorageMezzFlashLifeEntry
    MAX-ACCESS       not-accessible
    STATUS           current
    DESCRIPTION
        "Entry for the cfprApStorageMezzFlashLifeTable table."
    INDEX { cfprApStorageMezzFlashLifeInstanceId }
    ::= { cfprApStorageMezzFlashLifeTable 1 }

CfprApStorageMezzFlashLifeEntry ::= SEQUENCE {
    cfprApStorageMezzFlashLifeInstanceId                             CfprApManagedObjectId,
    cfprApStorageMezzFlashLifeDn                                     CfprApManagedObjectDn,
    cfprApStorageMezzFlashLifeRn                                     SnmpAdminString,
    cfprApStorageMezzFlashLifeBlockSize                              Gauge32,
    cfprApStorageMezzFlashLifeConnectionProtocol                     CfprApStorageConnectionProtocol,
    cfprApStorageMezzFlashLifeFlashPercentage                        SnmpAdminString,
    cfprApStorageMezzFlashLifeFlashStatus                            SnmpAdminString,
    cfprApStorageMezzFlashLifeId                                     Gauge32,
    cfprApStorageMezzFlashLifeModel                                  SnmpAdminString,
    cfprApStorageMezzFlashLifeNumberOfBlocks                         Unsigned64,
    cfprApStorageMezzFlashLifeOperQualifierReason                    SnmpAdminString,
    cfprApStorageMezzFlashLifeOperability                            CfprApEquipmentOperability,
    cfprApStorageMezzFlashLifePresence                               CfprApEquipmentPresence,
    cfprApStorageMezzFlashLifeRevision                               SnmpAdminString,
    cfprApStorageMezzFlashLifeSerial                                 SnmpAdminString,
    cfprApStorageMezzFlashLifeSize                                   Unsigned64,
    cfprApStorageMezzFlashLifeVendor                                 SnmpAdminString
}

cfprApStorageMezzFlashLifeInstanceId OBJECT-TYPE
    SYNTAX       CfprApManagedObjectId
    MAX-ACCESS   not-accessible
    STATUS       current
    DESCRIPTION
        "Instance identifier of the managed object."
    ::= { cfprApStorageMezzFlashLifeEntry 1 }

cfprApStorageMezzFlashLifeDn OBJECT-TYPE
    SYNTAX       CfprApManagedObjectDn
    MAX-ACCESS   read-only
    STATUS       current
    DESCRIPTION
        "Cisco Firepower storage:MezzFlashLife:dn managed object property"
    ::= { cfprApStorageMezzFlashLifeEntry 2 }

cfprApStorageMezzFlashLifeRn OBJECT-TYPE
    SYNTAX       SnmpAdminString
    MAX-ACCESS   read-only
    STATUS       current
    DESCRIPTION
        "Cisco Firepower storage:MezzFlashLife:rn managed object property"
    ::= { cfprApStorageMezzFlashLifeEntry 3 }

cfprApStorageMezzFlashLifeBlockSize OBJECT-TYPE
    SYNTAX       Gauge32
    MAX-ACCESS   read-only
    STATUS       current
    DESCRIPTION
        "Cisco Firepower storage:MezzFlashLife:blockSize
        managed object property"
    ::= { cfprApStorageMezzFlashLifeEntry 4 }

cfprApStorageMezzFlashLifeConnectionProtocol OBJECT-TYPE
    SYNTAX       CfprApStorageConnectionProtocol
    MAX-ACCESS   read-only
    STATUS       current
    DESCRIPTION
        "Cisco Firepower storage:MezzFlashLife:connectionProtocol
        managed object property"
    ::= { cfprApStorageMezzFlashLifeEntry 5 }

cfprApStorageMezzFlashLifeFlashPercentage OBJECT-TYPE
    SYNTAX       SnmpAdminString
    MAX-ACCESS   read-only
    STATUS       current
    DESCRIPTION
        "Cisco Firepower storage:MezzFlashLife:flashPercentage
        managed object property"
    ::= { cfprApStorageMezzFlashLifeEntry 6 }

cfprApStorageMezzFlashLifeFlashStatus OBJECT-TYPE
    SYNTAX       SnmpAdminString
    MAX-ACCESS   read-only
    STATUS       current
    DESCRIPTION
        "Cisco Firepower storage:MezzFlashLife:flashStatus
        managed object property"
    ::= { cfprApStorageMezzFlashLifeEntry 7 }

cfprApStorageMezzFlashLifeId OBJECT-TYPE
    SYNTAX       Gauge32
    MAX-ACCESS   read-only
    STATUS       current
    DESCRIPTION
        "Cisco Firepower storage:MezzFlashLife:id managed object property"
    ::= { cfprApStorageMezzFlashLifeEntry 8 }

cfprApStorageMezzFlashLifeModel OBJECT-TYPE
    SYNTAX       SnmpAdminString
    MAX-ACCESS   read-only
    STATUS       current
    DESCRIPTION
        "Cisco Firepower storage:MezzFlashLife:model managed
        object property"
    ::= { cfprApStorageMezzFlashLifeEntry 9 }

cfprApStorageMezzFlashLifeNumberOfBlocks OBJECT-TYPE
    SYNTAX       Unsigned64
    MAX-ACCESS   read-only
    STATUS       current
    DESCRIPTION
        "Cisco Firepower storage:MezzFlashLife:numberOfBlocks
        managed object property"
    ::= { cfprApStorageMezzFlashLifeEntry 10 }

cfprApStorageMezzFlashLifeOperQualifierReason OBJECT-TYPE
    SYNTAX       SnmpAdminString
    MAX-ACCESS   read-only
    STATUS       current
    DESCRIPTION
        "Cisco Firepower storage:MezzFlashLife:operQualifierReason
        managed object property"
    ::= { cfprApStorageMezzFlashLifeEntry 11 }

cfprApStorageMezzFlashLifeOperability OBJECT-TYPE
    SYNTAX       CfprApEquipmentOperability
    MAX-ACCESS   read-only
    STATUS       current
    DESCRIPTION
        "Cisco Firepower storage:MezzFlashLife:operability
        managed object property"
    ::= { cfprApStorageMezzFlashLifeEntry 12 }

cfprApStorageMezzFlashLifePresence OBJECT-TYPE
    SYNTAX       CfprApEquipmentPresence
    MAX-ACCESS   read-only
    STATUS       current
    DESCRIPTION
        "Cisco Firepower storage:MezzFlashLife:presence
        managed object property"
    ::= { cfprApStorageMezzFlashLifeEntry 13 }

cfprApStorageMezzFlashLifeRevision OBJECT-TYPE
    SYNTAX       SnmpAdminString
    MAX-ACCESS   read-only
    STATUS       current
    DESCRIPTION
        "Cisco Firepower storage:MezzFlashLife:revision
        managed object property"
    ::= { cfprApStorageMezzFlashLifeEntry 14 }

cfprApStorageMezzFlashLifeSerial OBJECT-TYPE
    SYNTAX       SnmpAdminString
    MAX-ACCESS   read-only
    STATUS       current
    DESCRIPTION
        "Cisco Firepower storage:MezzFlashLife:serial managed
        object property"
    ::= { cfprApStorageMezzFlashLifeEntry 15 }

cfprApStorageMezzFlashLifeSize OBJECT-TYPE
    SYNTAX       Unsigned64
    MAX-ACCESS   read-only
    STATUS       current
    DESCRIPTION
        "Cisco Firepower storage:MezzFlashLife:size managed
        object property"
    ::= { cfprApStorageMezzFlashLifeEntry 16 }

cfprApStorageMezzFlashLifeVendor OBJECT-TYPE
    SYNTAX       SnmpAdminString
    MAX-ACCESS   read-only
    STATUS       current
    DESCRIPTION
        "Cisco Firepower storage:MezzFlashLife:vendor managed
        object property"
    ::= { cfprApStorageMezzFlashLifeEntry 17 }

cfprApStorageNodeEpTable OBJECT-TYPE
    SYNTAX           SEQUENCE OF CfprApStorageNodeEpEntry
    MAX-ACCESS       not-accessible
    STATUS           current
    DESCRIPTION
        "Cisco Firepower storage:NodeEp managed object table"
    ::= { cfprApStorageObjects 29 }

cfprApStorageNodeEpEntry OBJECT-TYPE
    SYNTAX           CfprApStorageNodeEpEntry
    MAX-ACCESS       not-accessible
    STATUS           current
    DESCRIPTION
        "Entry for the cfprApStorageNodeEpTable table."
    INDEX { cfprApStorageNodeEpInstanceId }
    ::= { cfprApStorageNodeEpTable 1 }

CfprApStorageNodeEpEntry ::= SEQUENCE {
    cfprApStorageNodeEpInstanceId                                    CfprApManagedObjectId,
    cfprApStorageNodeEpDn                                            CfprApManagedObjectDn,
    cfprApStorageNodeEpRn                                            SnmpAdminString,
    cfprApStorageNodeEpEpDn                                          SnmpAdminString,
    cfprApStorageNodeEpId                                            Gauge32
}

cfprApStorageNodeEpInstanceId OBJECT-TYPE
    SYNTAX       CfprApManagedObjectId
    MAX-ACCESS   not-accessible
    STATUS       current
    DESCRIPTION
        "Instance identifier of the managed object."
    ::= { cfprApStorageNodeEpEntry 1 }

cfprApStorageNodeEpDn OBJECT-TYPE
    SYNTAX       CfprApManagedObjectDn
    MAX-ACCESS   read-only
    STATUS       current
    DESCRIPTION
        "Cisco Firepower storage:NodeEp:dn managed object property"
    ::= { cfprApStorageNodeEpEntry 2 }

cfprApStorageNodeEpRn OBJECT-TYPE
    SYNTAX       SnmpAdminString
    MAX-ACCESS   read-only
    STATUS       current
    DESCRIPTION
        "Cisco Firepower storage:NodeEp:rn managed object property"
    ::= { cfprApStorageNodeEpEntry 3 }

cfprApStorageNodeEpEpDn OBJECT-TYPE
    SYNTAX       SnmpAdminString
    MAX-ACCESS   read-only
    STATUS       current
    DESCRIPTION
        "Cisco Firepower storage:NodeEp:epDn managed object property"
    ::= { cfprApStorageNodeEpEntry 4 }

cfprApStorageNodeEpId OBJECT-TYPE
    SYNTAX       Gauge32
    MAX-ACCESS   read-only
    STATUS       current
    DESCRIPTION
        "Cisco Firepower storage:NodeEp:id managed object property"
    ::= { cfprApStorageNodeEpEntry 5 }

cfprApStorageOperationTable OBJECT-TYPE
    SYNTAX           SEQUENCE OF CfprApStorageOperationEntry
    MAX-ACCESS       not-accessible
    STATUS           current
    DESCRIPTION
        "Cisco Firepower storage:Operation managed object table"
    ::= { cfprApStorageObjects 30 }

cfprApStorageOperationEntry OBJECT-TYPE
    SYNTAX           CfprApStorageOperationEntry
    MAX-ACCESS       not-accessible
    STATUS           current
    DESCRIPTION
        "Entry for the cfprApStorageOperationTable table."
    INDEX { cfprApStorageOperationInstanceId }
    ::= { cfprApStorageOperationTable 1 }

CfprApStorageOperationEntry ::= SEQUENCE {
    cfprApStorageOperationInstanceId                                 CfprApManagedObjectId,
    cfprApStorageOperationDn                                         CfprApManagedObjectDn,
    cfprApStorageOperationRn                                         SnmpAdminString,
    cfprApStorageOperationEndTime                                    DateAndTime,
    cfprApStorageOperationName                                       CfprApStorageOperationType,
    cfprApStorageOperationOperState                                  CfprApStorageOperationState,
    cfprApStorageOperationProgress                                   Gauge32,
    cfprApStorageOperationStartTime                                  DateAndTime,
    cfprApStorageOperationStatusDescr                                SnmpAdminString
}

cfprApStorageOperationInstanceId OBJECT-TYPE
    SYNTAX       CfprApManagedObjectId
    MAX-ACCESS   not-accessible
    STATUS       current
    DESCRIPTION
        "Instance identifier of the managed object."
    ::= { cfprApStorageOperationEntry 1 }

cfprApStorageOperationDn OBJECT-TYPE
    SYNTAX       CfprApManagedObjectDn
    MAX-ACCESS   read-only
    STATUS       current
    DESCRIPTION
        "Cisco Firepower storage:Operation:dn managed object property"
    ::= { cfprApStorageOperationEntry 2 }

cfprApStorageOperationRn OBJECT-TYPE
    SYNTAX       SnmpAdminString
    MAX-ACCESS   read-only
    STATUS       current
    DESCRIPTION
        "Cisco Firepower storage:Operation:rn managed object property"
    ::= { cfprApStorageOperationEntry 3 }

cfprApStorageOperationEndTime OBJECT-TYPE
    SYNTAX       DateAndTime
    MAX-ACCESS   read-only
    STATUS       current
    DESCRIPTION
        "Cisco Firepower storage:Operation:endTime managed
        object property"
    ::= { cfprApStorageOperationEntry 4 }

cfprApStorageOperationName OBJECT-TYPE
    SYNTAX       CfprApStorageOperationType
    MAX-ACCESS   read-only
    STATUS       current
    DESCRIPTION
        "Cisco Firepower storage:Operation:name managed object property"
    ::= { cfprApStorageOperationEntry 5 }

cfprApStorageOperationOperState OBJECT-TYPE
    SYNTAX       CfprApStorageOperationState
    MAX-ACCESS   read-only
    STATUS       current
    DESCRIPTION
        "Cisco Firepower storage:Operation:operState managed
        object property"
    ::= { cfprApStorageOperationEntry 6 }

cfprApStorageOperationProgress OBJECT-TYPE
    SYNTAX       Gauge32
    MAX-ACCESS   read-only
    STATUS       current
    DESCRIPTION
        "Cisco Firepower storage:Operation:progress managed
        object property"
    ::= { cfprApStorageOperationEntry 7 }

cfprApStorageOperationStartTime OBJECT-TYPE
    SYNTAX       DateAndTime
    MAX-ACCESS   read-only
    STATUS       current
    DESCRIPTION
        "Cisco Firepower storage:Operation:startTime managed
        object property"
    ::= { cfprApStorageOperationEntry 8 }

cfprApStorageOperationStatusDescr OBJECT-TYPE
    SYNTAX       SnmpAdminString
    MAX-ACCESS   read-only
    STATUS       current
    DESCRIPTION
        "Cisco Firepower storage:Operation:statusDescr
        managed object property"
    ::= { cfprApStorageOperationEntry 9 }

cfprApStorageQualTable OBJECT-TYPE
    SYNTAX           SEQUENCE OF CfprApStorageQualEntry
    MAX-ACCESS       not-accessible
    STATUS           current
    DESCRIPTION
        "Cisco Firepower storage:Qual managed object table"
    ::= { cfprApStorageObjects 31 }

cfprApStorageQualEntry OBJECT-TYPE
    SYNTAX           CfprApStorageQualEntry
    MAX-ACCESS       not-accessible
    STATUS           current
    DESCRIPTION
        "Entry for the cfprApStorageQualTable table."
    INDEX { cfprApStorageQualInstanceId }
    ::= { cfprApStorageQualTable 1 }

CfprApStorageQualEntry ::= SEQUENCE {
    cfprApStorageQualInstanceId                                      CfprApManagedObjectId,
    cfprApStorageQualDn                                              CfprApManagedObjectDn,
    cfprApStorageQualRn                                              SnmpAdminString,
    cfprApStorageQualBlockSize                                       Gauge32,
    cfprApStorageQualDiskless                                        CfprApStorageDisklessAction,
    cfprApStorageQualMaxCap                                          Unsigned64,
    cfprApStorageQualMinCap                                          Unsigned64,
    cfprApStorageQualNumberOfBlocks                                  Unsigned64,
    cfprApStorageQualNumberOfFlexFlashCards                          INTEGER,
    cfprApStorageQualPerDiskCap                                      Unsigned64,
    cfprApStorageQualUnits                                           Gauge32
}

cfprApStorageQualInstanceId OBJECT-TYPE
    SYNTAX       CfprApManagedObjectId
    MAX-ACCESS   not-accessible
    STATUS       current
    DESCRIPTION
        "Instance identifier of the managed object."
    ::= { cfprApStorageQualEntry 1 }

cfprApStorageQualDn OBJECT-TYPE
    SYNTAX       CfprApManagedObjectDn
    MAX-ACCESS   read-only
    STATUS       current
    DESCRIPTION
        "Cisco Firepower storage:Qual:dn managed object property"
    ::= { cfprApStorageQualEntry 2 }

cfprApStorageQualRn OBJECT-TYPE
    SYNTAX       SnmpAdminString
    MAX-ACCESS   read-only
    STATUS       current
    DESCRIPTION
        "Cisco Firepower storage:Qual:rn managed object property"
    ::= { cfprApStorageQualEntry 3 }

cfprApStorageQualBlockSize OBJECT-TYPE
    SYNTAX       Gauge32
    MAX-ACCESS   read-only
    STATUS       current
    DESCRIPTION
        "Cisco Firepower storage:Qual:blockSize managed object property"
    ::= { cfprApStorageQualEntry 4 }

cfprApStorageQualDiskless OBJECT-TYPE
    SYNTAX       CfprApStorageDisklessAction
    MAX-ACCESS   read-only
    STATUS       current
    DESCRIPTION
        "Cisco Firepower storage:Qual:diskless managed object property"
    ::= { cfprApStorageQualEntry 5 }

cfprApStorageQualMaxCap OBJECT-TYPE
    SYNTAX       Unsigned64
    MAX-ACCESS   read-only
    STATUS       current
    DESCRIPTION
        "Cisco Firepower storage:Qual:maxCap managed object property"
    ::= { cfprApStorageQualEntry 6 }

cfprApStorageQualMinCap OBJECT-TYPE
    SYNTAX       Unsigned64
    MAX-ACCESS   read-only
    STATUS       current
    DESCRIPTION
        "Cisco Firepower storage:Qual:minCap managed object property"
    ::= { cfprApStorageQualEntry 7 }

cfprApStorageQualNumberOfBlocks OBJECT-TYPE
    SYNTAX       Unsigned64
    MAX-ACCESS   read-only
    STATUS       current
    DESCRIPTION
        "Cisco Firepower storage:Qual:numberOfBlocks managed
        object property"
    ::= { cfprApStorageQualEntry 8 }

cfprApStorageQualNumberOfFlexFlashCards OBJECT-TYPE
    SYNTAX       INTEGER
    MAX-ACCESS   read-only
    STATUS       current
    DESCRIPTION
        "Cisco Firepower storage:Qual:numberOfFlexFlashCards
        managed object property"
    ::= { cfprApStorageQualEntry 9 }

cfprApStorageQualPerDiskCap OBJECT-TYPE
    SYNTAX       Unsigned64
    MAX-ACCESS   read-only
    STATUS       current
    DESCRIPTION
        "Cisco Firepower storage:Qual:perDiskCap managed object property"
    ::= { cfprApStorageQualEntry 10 }

cfprApStorageQualUnits OBJECT-TYPE
    SYNTAX       Gauge32
    MAX-ACCESS   read-only
    STATUS       current
    DESCRIPTION
        "Cisco Firepower storage:Qual:units managed object property"
    ::= { cfprApStorageQualEntry 11 }

cfprApStorageRaidBatteryTable OBJECT-TYPE
    SYNTAX           SEQUENCE OF CfprApStorageRaidBatteryEntry
    MAX-ACCESS       not-accessible
    STATUS           current
    DESCRIPTION
        "Cisco Firepower storage:RaidBattery managed object table"
    ::= { cfprApStorageObjects 32 }

cfprApStorageRaidBatteryEntry OBJECT-TYPE
    SYNTAX           CfprApStorageRaidBatteryEntry
    MAX-ACCESS       not-accessible
    STATUS           current
    DESCRIPTION
        "Entry for the cfprApStorageRaidBatteryTable table."
    INDEX { cfprApStorageRaidBatteryInstanceId }
    ::= { cfprApStorageRaidBatteryTable 1 }

CfprApStorageRaidBatteryEntry ::= SEQUENCE {
    cfprApStorageRaidBatteryInstanceId                               CfprApManagedObjectId,
    cfprApStorageRaidBatteryDn                                       CfprApManagedObjectDn,
    cfprApStorageRaidBatteryRn                                       SnmpAdminString,
    cfprApStorageRaidBatteryBatteryType                              CfprApStorageBatteryType,
    cfprApStorageRaidBatteryBbuStatus                                CfprApStorageBbuStatus,
    cfprApStorageRaidBatteryBlockSize                                Gauge32,
    cfprApStorageRaidBatteryCapacityPercentage                       Gauge32,
    cfprApStorageRaidBatteryConnectionProtocol                       CfprApStorageConnectionProtocol,
    cfprApStorageRaidBatteryId                                       Gauge32,
    cfprApStorageRaidBatteryLc                                       CfprApFsmLifecycle,
    cfprApStorageRaidBatteryLearnCycleRequested                      CfprApStorageLearnCycleRequested,
    cfprApStorageRaidBatteryLearnMode                                CfprApStorageLearnMode,
    cfprApStorageRaidBatteryModel                                    SnmpAdminString,
    cfprApStorageRaidBatteryNextLearnCycleTs                         DateAndTime,
    cfprApStorageRaidBatteryNumberOfBlocks                           Unsigned64,
    cfprApStorageRaidBatteryOperQualifierReason                      SnmpAdminString,
    cfprApStorageRaidBatteryOperability                              CfprApEquipmentOperability,
    cfprApStorageRaidBatteryOperabilityQualifier                     CfprApStorageRaidBatteryOperabilityQualifier,
    cfprApStorageRaidBatteryOperabilityQualifierReason               SnmpAdminString,
    cfprApStorageRaidBatteryPresence                                 CfprApEquipmentPresence,
    cfprApStorageRaidBatteryRevision                                 SnmpAdminString,
    cfprApStorageRaidBatterySerial                                   SnmpAdminString,
    cfprApStorageRaidBatterySize                                     Unsigned64,
    cfprApStorageRaidBatteryTemperature                              INTEGER,
    cfprApStorageRaidBatteryVendor                                   SnmpAdminString
}

cfprApStorageRaidBatteryInstanceId OBJECT-TYPE
    SYNTAX       CfprApManagedObjectId
    MAX-ACCESS   not-accessible
    STATUS       current
    DESCRIPTION
        "Instance identifier of the managed object."
    ::= { cfprApStorageRaidBatteryEntry 1 }

cfprApStorageRaidBatteryDn OBJECT-TYPE
    SYNTAX       CfprApManagedObjectDn
    MAX-ACCESS   read-only
    STATUS       current
    DESCRIPTION
        "Cisco Firepower storage:RaidBattery:dn managed object property"
    ::= { cfprApStorageRaidBatteryEntry 2 }

cfprApStorageRaidBatteryRn OBJECT-TYPE
    SYNTAX       SnmpAdminString
    MAX-ACCESS   read-only
    STATUS       current
    DESCRIPTION
        "Cisco Firepower storage:RaidBattery:rn managed object property"
    ::= { cfprApStorageRaidBatteryEntry 3 }

cfprApStorageRaidBatteryBatteryType OBJECT-TYPE
    SYNTAX       CfprApStorageBatteryType
    MAX-ACCESS   read-only
    STATUS       current
    DESCRIPTION
        "Cisco Firepower storage:RaidBattery:batteryType
        managed object property"
    ::= { cfprApStorageRaidBatteryEntry 4 }

cfprApStorageRaidBatteryBbuStatus OBJECT-TYPE
    SYNTAX       CfprApStorageBbuStatus
    MAX-ACCESS   read-only
    STATUS       current
    DESCRIPTION
        "Cisco Firepower storage:RaidBattery:bbuStatus
        managed object property"
    ::= { cfprApStorageRaidBatteryEntry 5 }

cfprApStorageRaidBatteryBlockSize OBJECT-TYPE
    SYNTAX       Gauge32
    MAX-ACCESS   read-only
    STATUS       current
    DESCRIPTION
        "Cisco Firepower storage:RaidBattery:blockSize
        managed object property"
    ::= { cfprApStorageRaidBatteryEntry 6 }

cfprApStorageRaidBatteryCapacityPercentage OBJECT-TYPE
    SYNTAX       Gauge32
    MAX-ACCESS   read-only
    STATUS       current
    DESCRIPTION
        "Cisco Firepower storage:RaidBattery:capacityPercentage
        managed object property"
    ::= { cfprApStorageRaidBatteryEntry 7 }

cfprApStorageRaidBatteryConnectionProtocol OBJECT-TYPE
    SYNTAX       CfprApStorageConnectionProtocol
    MAX-ACCESS   read-only
    STATUS       current
    DESCRIPTION
        "Cisco Firepower storage:RaidBattery:connectionProtocol
        managed object property"
    ::= { cfprApStorageRaidBatteryEntry 8 }

cfprApStorageRaidBatteryId OBJECT-TYPE
    SYNTAX       Gauge32
    MAX-ACCESS   read-only
    STATUS       current
    DESCRIPTION
        "Cisco Firepower storage:RaidBattery:id managed object property"
    ::= { cfprApStorageRaidBatteryEntry 9 }

cfprApStorageRaidBatteryLc OBJECT-TYPE
    SYNTAX       CfprApFsmLifecycle
    MAX-ACCESS   read-only
    STATUS       current
    DESCRIPTION
        "Cisco Firepower storage:RaidBattery:lc managed object property"
    ::= { cfprApStorageRaidBatteryEntry 10 }

cfprApStorageRaidBatteryLearnCycleRequested OBJECT-TYPE
    SYNTAX       CfprApStorageLearnCycleRequested
    MAX-ACCESS   read-only
    STATUS       current
    DESCRIPTION
        "Cisco Firepower storage:RaidBattery:learnCycleRequested
        managed object property"
    ::= { cfprApStorageRaidBatteryEntry 11 }

cfprApStorageRaidBatteryLearnMode OBJECT-TYPE
    SYNTAX       CfprApStorageLearnMode
    MAX-ACCESS   read-only
    STATUS       current
    DESCRIPTION
        "Cisco Firepower storage:RaidBattery:learnMode
        managed object property"
    ::= { cfprApStorageRaidBatteryEntry 12 }

cfprApStorageRaidBatteryModel OBJECT-TYPE
    SYNTAX       SnmpAdminString
    MAX-ACCESS   read-only
    STATUS       current
    DESCRIPTION
        "Cisco Firepower storage:RaidBattery:model managed
        object property"
    ::= { cfprApStorageRaidBatteryEntry 13 }

cfprApStorageRaidBatteryNextLearnCycleTs OBJECT-TYPE
    SYNTAX       DateAndTime
    MAX-ACCESS   read-only
    STATUS       current
    DESCRIPTION
        "Cisco Firepower storage:RaidBattery:nextLearnCycleTs
        managed object property"
    ::= { cfprApStorageRaidBatteryEntry 14 }

cfprApStorageRaidBatteryNumberOfBlocks OBJECT-TYPE
    SYNTAX       Unsigned64
    MAX-ACCESS   read-only
    STATUS       current
    DESCRIPTION
        "Cisco Firepower storage:RaidBattery:numberOfBlocks
        managed object property"
    ::= { cfprApStorageRaidBatteryEntry 15 }

cfprApStorageRaidBatteryOperQualifierReason OBJECT-TYPE
    SYNTAX       SnmpAdminString
    MAX-ACCESS   read-only
    STATUS       current
    DESCRIPTION
        "Cisco Firepower storage:RaidBattery:operQualifierReason
        managed object property"
    ::= { cfprApStorageRaidBatteryEntry 16 }

cfprApStorageRaidBatteryOperability OBJECT-TYPE
    SYNTAX       CfprApEquipmentOperability
    MAX-ACCESS   read-only
    STATUS       current
    DESCRIPTION
        "Cisco Firepower storage:RaidBattery:operability
        managed object property"
    ::= { cfprApStorageRaidBatteryEntry 17 }

cfprApStorageRaidBatteryOperabilityQualifier OBJECT-TYPE
    SYNTAX       CfprApStorageRaidBatteryOperabilityQualifier
    MAX-ACCESS   read-only
    STATUS       current
    DESCRIPTION
        "Cisco Firepower storage:RaidBattery:operabilityQualifier
        managed object property"
    ::= { cfprApStorageRaidBatteryEntry 18 }

cfprApStorageRaidBatteryOperabilityQualifierReason OBJECT-TYPE
    SYNTAX       SnmpAdminString
    MAX-ACCESS   read-only
    STATUS       current
    DESCRIPTION
        "Cisco Firepower storage:RaidBattery:operabilityQualifierReason
        managed object property"
    ::= { cfprApStorageRaidBatteryEntry 19 }

cfprApStorageRaidBatteryPresence OBJECT-TYPE
    SYNTAX       CfprApEquipmentPresence
    MAX-ACCESS   read-only
    STATUS       current
    DESCRIPTION
        "Cisco Firepower storage:RaidBattery:presence managed
        object property"
    ::= { cfprApStorageRaidBatteryEntry 20 }

cfprApStorageRaidBatteryRevision OBJECT-TYPE
    SYNTAX       SnmpAdminString
    MAX-ACCESS   read-only
    STATUS       current
    DESCRIPTION
        "Cisco Firepower storage:RaidBattery:revision managed
        object property"
    ::= { cfprApStorageRaidBatteryEntry 21 }

cfprApStorageRaidBatterySerial OBJECT-TYPE
    SYNTAX       SnmpAdminString
    MAX-ACCESS   read-only
    STATUS       current
    DESCRIPTION
        "Cisco Firepower storage:RaidBattery:serial managed
        object property"
    ::= { cfprApStorageRaidBatteryEntry 22 }

cfprApStorageRaidBatterySize OBJECT-TYPE
    SYNTAX       Unsigned64
    MAX-ACCESS   read-only
    STATUS       current
    DESCRIPTION
        "Cisco Firepower storage:RaidBattery:size managed object property"
    ::= { cfprApStorageRaidBatteryEntry 23 }

cfprApStorageRaidBatteryTemperature OBJECT-TYPE
    SYNTAX       INTEGER
    MAX-ACCESS   read-only
    STATUS       current
    DESCRIPTION
        "Cisco Firepower storage:RaidBattery:temperature
        managed object property"
    ::= { cfprApStorageRaidBatteryEntry 24 }

cfprApStorageRaidBatteryVendor OBJECT-TYPE
    SYNTAX       SnmpAdminString
    MAX-ACCESS   read-only
    STATUS       current
    DESCRIPTION
        "Cisco Firepower storage:RaidBattery:vendor managed
        object property"
    ::= { cfprApStorageRaidBatteryEntry 25 }

cfprApStorageSystemTable OBJECT-TYPE
    SYNTAX           SEQUENCE OF CfprApStorageSystemEntry
    MAX-ACCESS       not-accessible
    STATUS           current
    DESCRIPTION
        "Cisco Firepower storage:System managed object table"
    ::= { cfprApStorageObjects 33 }

cfprApStorageSystemEntry OBJECT-TYPE
    SYNTAX           CfprApStorageSystemEntry
    MAX-ACCESS       not-accessible
    STATUS           current
    DESCRIPTION
        "Entry for the cfprApStorageSystemTable table."
    INDEX { cfprApStorageSystemInstanceId }
    ::= { cfprApStorageSystemTable 1 }

CfprApStorageSystemEntry ::= SEQUENCE {
    cfprApStorageSystemInstanceId                                    CfprApManagedObjectId,
    cfprApStorageSystemDn                                            CfprApManagedObjectDn,
    cfprApStorageSystemRn                                            SnmpAdminString,
    cfprApStorageSystemFsmDescr                                      SnmpAdminString,
    cfprApStorageSystemFsmPrev                                       SnmpAdminString,
    cfprApStorageSystemFsmProgr                                      Gauge32,
    cfprApStorageSystemFsmRmtInvErrCode                              Gauge32,
    cfprApStorageSystemFsmRmtInvErrDescr                             SnmpAdminString,
    cfprApStorageSystemFsmRmtInvRslt                                 CfprApConditionRemoteInvRslt,
    cfprApStorageSystemFsmStageDescr                                 SnmpAdminString,
    cfprApStorageSystemFsmStamp                                      DateAndTime,
    cfprApStorageSystemFsmStatus                                     SnmpAdminString,
    cfprApStorageSystemFsmTry                                        Gauge32,
    cfprApStorageSystemId                                            SnmpAdminString,
    cfprApStorageSystemName                                          SnmpAdminString
}

cfprApStorageSystemInstanceId OBJECT-TYPE
    SYNTAX       CfprApManagedObjectId
    MAX-ACCESS   not-accessible
    STATUS       current
    DESCRIPTION
        "Instance identifier of the managed object."
    ::= { cfprApStorageSystemEntry 1 }

cfprApStorageSystemDn OBJECT-TYPE
    SYNTAX       CfprApManagedObjectDn
    MAX-ACCESS   read-only
    STATUS       current
    DESCRIPTION
        "Cisco Firepower storage:System:dn managed object property"
    ::= { cfprApStorageSystemEntry 2 }

cfprApStorageSystemRn OBJECT-TYPE
    SYNTAX       SnmpAdminString
    MAX-ACCESS   read-only
    STATUS       current
    DESCRIPTION
        "Cisco Firepower storage:System:rn managed object property"
    ::= { cfprApStorageSystemEntry 3 }

cfprApStorageSystemFsmDescr OBJECT-TYPE
    SYNTAX       SnmpAdminString
    MAX-ACCESS   read-only
    STATUS       current
    DESCRIPTION
        "Cisco Firepower storage:System:fsmDescr managed object property"
    ::= { cfprApStorageSystemEntry 4 }

cfprApStorageSystemFsmPrev OBJECT-TYPE
    SYNTAX       SnmpAdminString
    MAX-ACCESS   read-only
    STATUS       current
    DESCRIPTION
        "Cisco Firepower storage:System:fsmPrev managed object property"
    ::= { cfprApStorageSystemEntry 5 }

cfprApStorageSystemFsmProgr OBJECT-TYPE
    SYNTAX       Gauge32
    MAX-ACCESS   read-only
    STATUS       current
    DESCRIPTION
        "Cisco Firepower storage:System:fsmProgr managed object property"
    ::= { cfprApStorageSystemEntry 6 }

cfprApStorageSystemFsmRmtInvErrCode OBJECT-TYPE
    SYNTAX       Gauge32
    MAX-ACCESS   read-only
    STATUS       current
    DESCRIPTION
        "Cisco Firepower storage:System:fsmRmtInvErrCode
        managed object property"
    ::= { cfprApStorageSystemEntry 7 }

cfprApStorageSystemFsmRmtInvErrDescr OBJECT-TYPE
    SYNTAX       SnmpAdminString
    MAX-ACCESS   read-only
    STATUS       current
    DESCRIPTION
        "Cisco Firepower storage:System:fsmRmtInvErrDescr
        managed object property"
    ::= { cfprApStorageSystemEntry 8 }

cfprApStorageSystemFsmRmtInvRslt OBJECT-TYPE
    SYNTAX       CfprApConditionRemoteInvRslt
    MAX-ACCESS   read-only
    STATUS       current
    DESCRIPTION
        "Cisco Firepower storage:System:fsmRmtInvRslt managed
        object property"
    ::= { cfprApStorageSystemEntry 9 }

cfprApStorageSystemFsmStageDescr OBJECT-TYPE
    SYNTAX       SnmpAdminString
    MAX-ACCESS   read-only
    STATUS       current
    DESCRIPTION
        "Cisco Firepower storage:System:fsmStageDescr managed
        object property"
    ::= { cfprApStorageSystemEntry 10 }

cfprApStorageSystemFsmStamp OBJECT-TYPE
    SYNTAX       DateAndTime
    MAX-ACCESS   read-only
    STATUS       current
    DESCRIPTION
        "Cisco Firepower storage:System:fsmStamp managed object property"
    ::= { cfprApStorageSystemEntry 11 }

cfprApStorageSystemFsmStatus OBJECT-TYPE
    SYNTAX       SnmpAdminString
    MAX-ACCESS   read-only
    STATUS       current
    DESCRIPTION
        "Cisco Firepower storage:System:fsmStatus managed object property"
    ::= { cfprApStorageSystemEntry 12 }

cfprApStorageSystemFsmTry OBJECT-TYPE
    SYNTAX       Gauge32
    MAX-ACCESS   read-only
    STATUS       current
    DESCRIPTION
        "Cisco Firepower storage:System:fsmTry managed object property"
    ::= { cfprApStorageSystemEntry 13 }

cfprApStorageSystemId OBJECT-TYPE
    SYNTAX       SnmpAdminString
    MAX-ACCESS   read-only
    STATUS       current
    DESCRIPTION
        "Cisco Firepower storage:System:id managed object property"
    ::= { cfprApStorageSystemEntry 14 }

cfprApStorageSystemName OBJECT-TYPE
    SYNTAX       SnmpAdminString
    MAX-ACCESS   read-only
    STATUS       current
    DESCRIPTION
        "Cisco Firepower storage:System:name managed object property"
    ::= { cfprApStorageSystemEntry 15 }

cfprApStorageSystemFsmTable OBJECT-TYPE
    SYNTAX           SEQUENCE OF CfprApStorageSystemFsmEntry
    MAX-ACCESS       not-accessible
    STATUS           current
    DESCRIPTION
        "Cisco Firepower storage:SystemFsm managed object table"
    ::= { cfprApStorageObjects 34 }

cfprApStorageSystemFsmEntry OBJECT-TYPE
    SYNTAX           CfprApStorageSystemFsmEntry
    MAX-ACCESS       not-accessible
    STATUS           current
    DESCRIPTION
        "Entry for the cfprApStorageSystemFsmTable table."
    INDEX { cfprApStorageSystemFsmInstanceId }
    ::= { cfprApStorageSystemFsmTable 1 }

CfprApStorageSystemFsmEntry ::= SEQUENCE {
    cfprApStorageSystemFsmInstanceId                                 CfprApManagedObjectId,
    cfprApStorageSystemFsmDn                                         CfprApManagedObjectDn,
    cfprApStorageSystemFsmRn                                         SnmpAdminString,
    cfprApStorageSystemFsmCompletionTime                             DateAndTime,
    cfprApStorageSystemFsmCurrentFsm                                 CfprApStorageSystemFsmCurrentFsm,
    cfprApStorageSystemFsmDescrData                                  SnmpAdminString,
    cfprApStorageSystemFsmFsmStatus                                  CfprApFsmFsmStageStatus,
    cfprApStorageSystemFsmProgress                                   Gauge32,
    cfprApStorageSystemFsmRmtErrCode                                 Gauge32,
    cfprApStorageSystemFsmRmtErrDescr                                SnmpAdminString,
    cfprApStorageSystemFsmRmtRslt                                    CfprApConditionRemoteInvRslt
}

cfprApStorageSystemFsmInstanceId OBJECT-TYPE
    SYNTAX       CfprApManagedObjectId
    MAX-ACCESS   not-accessible
    STATUS       current
    DESCRIPTION
        "Instance identifier of the managed object."
    ::= { cfprApStorageSystemFsmEntry 1 }

cfprApStorageSystemFsmDn OBJECT-TYPE
    SYNTAX       CfprApManagedObjectDn
    MAX-ACCESS   read-only
    STATUS       current
    DESCRIPTION
        "Cisco Firepower storage:SystemFsm:dn managed object property"
    ::= { cfprApStorageSystemFsmEntry 2 }

cfprApStorageSystemFsmRn OBJECT-TYPE
    SYNTAX       SnmpAdminString
    MAX-ACCESS   read-only
    STATUS       current
    DESCRIPTION
        "Cisco Firepower storage:SystemFsm:rn managed object property"
    ::= { cfprApStorageSystemFsmEntry 3 }

cfprApStorageSystemFsmCompletionTime OBJECT-TYPE
    SYNTAX       DateAndTime
    MAX-ACCESS   read-only
    STATUS       current
    DESCRIPTION
        "Cisco Firepower storage:SystemFsm:completionTime
        managed object property"
    ::= { cfprApStorageSystemFsmEntry 4 }

cfprApStorageSystemFsmCurrentFsm OBJECT-TYPE
    SYNTAX       CfprApStorageSystemFsmCurrentFsm
    MAX-ACCESS   read-only
    STATUS       current
    DESCRIPTION
        "Cisco Firepower storage:SystemFsm:currentFsm managed
        object property"
    ::= { cfprApStorageSystemFsmEntry 5 }

cfprApStorageSystemFsmDescrData OBJECT-TYPE
    SYNTAX       SnmpAdminString
    MAX-ACCESS   read-only
    STATUS       current
    DESCRIPTION
        "Cisco Firepower storage:SystemFsm:descr managed object property"
    ::= { cfprApStorageSystemFsmEntry 6 }

cfprApStorageSystemFsmFsmStatus OBJECT-TYPE
    SYNTAX       CfprApFsmFsmStageStatus
    MAX-ACCESS   read-only
    STATUS       current
    DESCRIPTION
        "Cisco Firepower storage:SystemFsm:fsmStatus managed
        object property"
    ::= { cfprApStorageSystemFsmEntry 7 }

cfprApStorageSystemFsmProgress OBJECT-TYPE
    SYNTAX       Gauge32
    MAX-ACCESS   read-only
    STATUS       current
    DESCRIPTION
        "Cisco Firepower storage:SystemFsm:progress managed
        object property"
    ::= { cfprApStorageSystemFsmEntry 8 }

cfprApStorageSystemFsmRmtErrCode OBJECT-TYPE
    SYNTAX       Gauge32
    MAX-ACCESS   read-only
    STATUS       current
    DESCRIPTION
        "Cisco Firepower storage:SystemFsm:rmtErrCode managed
        object property"
    ::= { cfprApStorageSystemFsmEntry 9 }

cfprApStorageSystemFsmRmtErrDescr OBJECT-TYPE
    SYNTAX       SnmpAdminString
    MAX-ACCESS   read-only
    STATUS       current
    DESCRIPTION
        "Cisco Firepower storage:SystemFsm:rmtErrDescr
        managed object property"
    ::= { cfprApStorageSystemFsmEntry 10 }

cfprApStorageSystemFsmRmtRslt OBJECT-TYPE
    SYNTAX       CfprApConditionRemoteInvRslt
    MAX-ACCESS   read-only
    STATUS       current
    DESCRIPTION
        "Cisco Firepower storage:SystemFsm:rmtRslt managed
        object property"
    ::= { cfprApStorageSystemFsmEntry 11 }

cfprApStorageSystemFsmStageTable OBJECT-TYPE
    SYNTAX           SEQUENCE OF CfprApStorageSystemFsmStageEntry
    MAX-ACCESS       not-accessible
    STATUS           current
    DESCRIPTION
        "Cisco Firepower storage:SystemFsmStage managed object table"
    ::= { cfprApStorageObjects 35 }

cfprApStorageSystemFsmStageEntry OBJECT-TYPE
    SYNTAX           CfprApStorageSystemFsmStageEntry
    MAX-ACCESS       not-accessible
    STATUS           current
    DESCRIPTION
        "Entry for the cfprApStorageSystemFsmStageTable table."
    INDEX { cfprApStorageSystemFsmStageInstanceId }
    ::= { cfprApStorageSystemFsmStageTable 1 }

CfprApStorageSystemFsmStageEntry ::= SEQUENCE {
    cfprApStorageSystemFsmStageInstanceId                            CfprApManagedObjectId,
    cfprApStorageSystemFsmStageDn                                    CfprApManagedObjectDn,
    cfprApStorageSystemFsmStageRn                                    SnmpAdminString,
    cfprApStorageSystemFsmStageDescrData                             SnmpAdminString,
    cfprApStorageSystemFsmStageLastUpdateTime                        DateAndTime,
    cfprApStorageSystemFsmStageName                                  CfprApStorageSystemFsmStageName,
    cfprApStorageSystemFsmStageOrder                                 Gauge32,
    cfprApStorageSystemFsmStageRetry                                 Gauge32,
    cfprApStorageSystemFsmStageStageStatus                           CfprApFsmFsmStageStatus
}

cfprApStorageSystemFsmStageInstanceId OBJECT-TYPE
    SYNTAX       CfprApManagedObjectId
    MAX-ACCESS   not-accessible
    STATUS       current
    DESCRIPTION
        "Instance identifier of the managed object."
    ::= { cfprApStorageSystemFsmStageEntry 1 }

cfprApStorageSystemFsmStageDn OBJECT-TYPE
    SYNTAX       CfprApManagedObjectDn
    MAX-ACCESS   read-only
    STATUS       current
    DESCRIPTION
        "Cisco Firepower storage:SystemFsmStage:dn managed
        object property"
    ::= { cfprApStorageSystemFsmStageEntry 2 }

cfprApStorageSystemFsmStageRn OBJECT-TYPE
    SYNTAX       SnmpAdminString
    MAX-ACCESS   read-only
    STATUS       current
    DESCRIPTION
        "Cisco Firepower storage:SystemFsmStage:rn managed
        object property"
    ::= { cfprApStorageSystemFsmStageEntry 3 }

cfprApStorageSystemFsmStageDescrData OBJECT-TYPE
    SYNTAX       SnmpAdminString
    MAX-ACCESS   read-only
    STATUS       current
    DESCRIPTION
        "Cisco Firepower storage:SystemFsmStage:descr managed
        object property"
    ::= { cfprApStorageSystemFsmStageEntry 4 }

cfprApStorageSystemFsmStageLastUpdateTime OBJECT-TYPE
    SYNTAX       DateAndTime
    MAX-ACCESS   read-only
    STATUS       current
    DESCRIPTION
        "Cisco Firepower storage:SystemFsmStage:lastUpdateTime
        managed object property"
    ::= { cfprApStorageSystemFsmStageEntry 5 }

cfprApStorageSystemFsmStageName OBJECT-TYPE
    SYNTAX       CfprApStorageSystemFsmStageName
    MAX-ACCESS   read-only
    STATUS       current
    DESCRIPTION
        "Cisco Firepower storage:SystemFsmStage:name managed
        object property"
    ::= { cfprApStorageSystemFsmStageEntry 6 }

cfprApStorageSystemFsmStageOrder OBJECT-TYPE
    SYNTAX       Gauge32
    MAX-ACCESS   read-only
    STATUS       current
    DESCRIPTION
        "Cisco Firepower storage:SystemFsmStage:order managed
        object property"
    ::= { cfprApStorageSystemFsmStageEntry 7 }

cfprApStorageSystemFsmStageRetry OBJECT-TYPE
    SYNTAX       Gauge32
    MAX-ACCESS   read-only
    STATUS       current
    DESCRIPTION
        "Cisco Firepower storage:SystemFsmStage:retry managed
        object property"
    ::= { cfprApStorageSystemFsmStageEntry 8 }

cfprApStorageSystemFsmStageStageStatus OBJECT-TYPE
    SYNTAX       CfprApFsmFsmStageStatus
    MAX-ACCESS   read-only
    STATUS       current
    DESCRIPTION
        "Cisco Firepower storage:SystemFsmStage:stageStatus
        managed object property"
    ::= { cfprApStorageSystemFsmStageEntry 9 }

cfprApStorageSystemFsmTaskTable OBJECT-TYPE
    SYNTAX           SEQUENCE OF CfprApStorageSystemFsmTaskEntry
    MAX-ACCESS       not-accessible
    STATUS           current
    DESCRIPTION
        "Cisco Firepower storage:SystemFsmTask managed object table"
    ::= { cfprApStorageObjects 36 }

cfprApStorageSystemFsmTaskEntry OBJECT-TYPE
    SYNTAX           CfprApStorageSystemFsmTaskEntry
    MAX-ACCESS       not-accessible
    STATUS           current
    DESCRIPTION
        "Entry for the cfprApStorageSystemFsmTaskTable table."
    INDEX { cfprApStorageSystemFsmTaskInstanceId }
    ::= { cfprApStorageSystemFsmTaskTable 1 }

CfprApStorageSystemFsmTaskEntry ::= SEQUENCE {
    cfprApStorageSystemFsmTaskInstanceId                             CfprApManagedObjectId,
    cfprApStorageSystemFsmTaskDn                                     CfprApManagedObjectDn,
    cfprApStorageSystemFsmTaskRn                                     SnmpAdminString,
    cfprApStorageSystemFsmTaskCompletion                             CfprApFsmCompletion,
    cfprApStorageSystemFsmTaskFlags                                  CfprApFsmFlags,
    cfprApStorageSystemFsmTaskItem                                   CfprApStorageSystemFsmTaskItem,
    cfprApStorageSystemFsmTaskSeqId                                  Gauge32
}

cfprApStorageSystemFsmTaskInstanceId OBJECT-TYPE
    SYNTAX       CfprApManagedObjectId
    MAX-ACCESS   not-accessible
    STATUS       current
    DESCRIPTION
        "Instance identifier of the managed object."
    ::= { cfprApStorageSystemFsmTaskEntry 1 }

cfprApStorageSystemFsmTaskDn OBJECT-TYPE
    SYNTAX       CfprApManagedObjectDn
    MAX-ACCESS   read-only
    STATUS       current
    DESCRIPTION
        "Cisco Firepower storage:SystemFsmTask:dn managed object property"
    ::= { cfprApStorageSystemFsmTaskEntry 2 }

cfprApStorageSystemFsmTaskRn OBJECT-TYPE
    SYNTAX       SnmpAdminString
    MAX-ACCESS   read-only
    STATUS       current
    DESCRIPTION
        "Cisco Firepower storage:SystemFsmTask:rn managed object property"
    ::= { cfprApStorageSystemFsmTaskEntry 3 }

cfprApStorageSystemFsmTaskCompletion OBJECT-TYPE
    SYNTAX       CfprApFsmCompletion
    MAX-ACCESS   read-only
    STATUS       current
    DESCRIPTION
        "Cisco Firepower storage:SystemFsmTask:completion
        managed object property"
    ::= { cfprApStorageSystemFsmTaskEntry 4 }

cfprApStorageSystemFsmTaskFlags OBJECT-TYPE
    SYNTAX       CfprApFsmFlags
    MAX-ACCESS   read-only
    STATUS       current
    DESCRIPTION
        "Cisco Firepower storage:SystemFsmTask:flags managed
        object property"
    ::= { cfprApStorageSystemFsmTaskEntry 5 }

cfprApStorageSystemFsmTaskItem OBJECT-TYPE
    SYNTAX       CfprApStorageSystemFsmTaskItem
    MAX-ACCESS   read-only
    STATUS       current
    DESCRIPTION
        "Cisco Firepower storage:SystemFsmTask:item managed
        object property"
    ::= { cfprApStorageSystemFsmTaskEntry 6 }

cfprApStorageSystemFsmTaskSeqId OBJECT-TYPE
    SYNTAX       Gauge32
    MAX-ACCESS   read-only
    STATUS       current
    DESCRIPTION
        "Cisco Firepower storage:SystemFsmTask:seqId managed
        object property"
    ::= { cfprApStorageSystemFsmTaskEntry 7 }

cfprApStorageTransportableFlashModuleTable OBJECT-TYPE
    SYNTAX           SEQUENCE OF CfprApStorageTransportableFlashModuleEntry
    MAX-ACCESS       not-accessible
    STATUS           current
    DESCRIPTION
        "Cisco Firepower storage:TransportableFlashModule
        managed object table"
    ::= { cfprApStorageObjects 37 }

cfprApStorageTransportableFlashModuleEntry OBJECT-TYPE
    SYNTAX           CfprApStorageTransportableFlashModuleEntry
    MAX-ACCESS       not-accessible
    STATUS           current
    DESCRIPTION
        "Entry for the cfprApStorageTransportableFlashModuleTable table."
    INDEX { cfprApStorageTransportableFlashModuleInstanceId }
    ::= { cfprApStorageTransportableFlashModuleTable 1 }

CfprApStorageTransportableFlashModuleEntry ::= SEQUENCE {
    cfprApStorageTransportableFlashModuleInstanceId                  CfprApManagedObjectId,
    cfprApStorageTransportableFlashModuleDn                          CfprApManagedObjectDn,
    cfprApStorageTransportableFlashModuleRn                          SnmpAdminString,
    cfprApStorageTransportableFlashModuleBlockSize                   Gauge32,
    cfprApStorageTransportableFlashModuleConnectionProtocol          CfprApStorageConnectionProtocol,
    cfprApStorageTransportableFlashModuleId                          Gauge32,
    cfprApStorageTransportableFlashModuleModel                       SnmpAdminString,
    cfprApStorageTransportableFlashModuleNumberOfBlocks              Unsigned64,
    cfprApStorageTransportableFlashModuleOperQualifierReason         SnmpAdminString,
    cfprApStorageTransportableFlashModuleOperability                 CfprApEquipmentOperability,
    cfprApStorageTransportableFlashModulePresence                    CfprApEquipmentPresence,
    cfprApStorageTransportableFlashModuleRevision                    SnmpAdminString,
    cfprApStorageTransportableFlashModuleSerial                      SnmpAdminString,
    cfprApStorageTransportableFlashModuleSize                        Unsigned64,
    cfprApStorageTransportableFlashModuleVendor                      SnmpAdminString
}

cfprApStorageTransportableFlashModuleInstanceId OBJECT-TYPE
    SYNTAX       CfprApManagedObjectId
    MAX-ACCESS   not-accessible
    STATUS       current
    DESCRIPTION
        "Instance identifier of the managed object."
    ::= { cfprApStorageTransportableFlashModuleEntry 1 }

cfprApStorageTransportableFlashModuleDn OBJECT-TYPE
    SYNTAX       CfprApManagedObjectDn
    MAX-ACCESS   read-only
    STATUS       current
    DESCRIPTION
        "Cisco Firepower storage:TransportableFlashModule:dn
        managed object property"
    ::= { cfprApStorageTransportableFlashModuleEntry 2 }

cfprApStorageTransportableFlashModuleRn OBJECT-TYPE
    SYNTAX       SnmpAdminString
    MAX-ACCESS   read-only
    STATUS       current
    DESCRIPTION
        "Cisco Firepower storage:TransportableFlashModule:rn
        managed object property"
    ::= { cfprApStorageTransportableFlashModuleEntry 3 }

cfprApStorageTransportableFlashModuleBlockSize OBJECT-TYPE
    SYNTAX       Gauge32
    MAX-ACCESS   read-only
    STATUS       current
    DESCRIPTION
        "Cisco Firepower storage:TransportableFlashModule:blockSize
        managed object property"
    ::= { cfprApStorageTransportableFlashModuleEntry 4 }

cfprApStorageTransportableFlashModuleConnectionProtocol OBJECT-TYPE
    SYNTAX       CfprApStorageConnectionProtocol
    MAX-ACCESS   read-only
    STATUS       current
    DESCRIPTION
        "Cisco Firepower storage:TransportableFlashModule:connectionProtoc
        ol managed object property"
    ::= { cfprApStorageTransportableFlashModuleEntry 5 }

cfprApStorageTransportableFlashModuleId OBJECT-TYPE
    SYNTAX       Gauge32
    MAX-ACCESS   read-only
    STATUS       current
    DESCRIPTION
        "Cisco Firepower storage:TransportableFlashModule:id
        managed object property"
    ::= { cfprApStorageTransportableFlashModuleEntry 6 }

cfprApStorageTransportableFlashModuleModel OBJECT-TYPE
    SYNTAX       SnmpAdminString
    MAX-ACCESS   read-only
    STATUS       current
    DESCRIPTION
        "Cisco Firepower storage:TransportableFlashModule:model
        managed object property"
    ::= { cfprApStorageTransportableFlashModuleEntry 7 }

cfprApStorageTransportableFlashModuleNumberOfBlocks OBJECT-TYPE
    SYNTAX       Unsigned64
    MAX-ACCESS   read-only
    STATUS       current
    DESCRIPTION
        "Cisco Firepower storage:TransportableFlashModule:numberOfBlocks
        managed object property"
    ::= { cfprApStorageTransportableFlashModuleEntry 8 }

cfprApStorageTransportableFlashModuleOperQualifierReason OBJECT-TYPE
    SYNTAX       SnmpAdminString
    MAX-ACCESS   read-only
    STATUS       current
    DESCRIPTION
        "Cisco Firepower storage:TransportableFlashModule:operQualifierRea
        son managed object property"
    ::= { cfprApStorageTransportableFlashModuleEntry 9 }

cfprApStorageTransportableFlashModuleOperability OBJECT-TYPE
    SYNTAX       CfprApEquipmentOperability
    MAX-ACCESS   read-only
    STATUS       current
    DESCRIPTION
        "Cisco Firepower storage:TransportableFlashModule:operability
        managed object property"
    ::= { cfprApStorageTransportableFlashModuleEntry 10 }

cfprApStorageTransportableFlashModulePresence OBJECT-TYPE
    SYNTAX       CfprApEquipmentPresence
    MAX-ACCESS   read-only
    STATUS       current
    DESCRIPTION
        "Cisco Firepower storage:TransportableFlashModule:presence
        managed object property"
    ::= { cfprApStorageTransportableFlashModuleEntry 11 }

cfprApStorageTransportableFlashModuleRevision OBJECT-TYPE
    SYNTAX       SnmpAdminString
    MAX-ACCESS   read-only
    STATUS       current
    DESCRIPTION
        "Cisco Firepower storage:TransportableFlashModule:revision
        managed object property"
    ::= { cfprApStorageTransportableFlashModuleEntry 12 }

cfprApStorageTransportableFlashModuleSerial OBJECT-TYPE
    SYNTAX       SnmpAdminString
    MAX-ACCESS   read-only
    STATUS       current
    DESCRIPTION
        "Cisco Firepower storage:TransportableFlashModule:serial
        managed object property"
    ::= { cfprApStorageTransportableFlashModuleEntry 13 }

cfprApStorageTransportableFlashModuleSize OBJECT-TYPE
    SYNTAX       Unsigned64
    MAX-ACCESS   read-only
    STATUS       current
    DESCRIPTION
        "Cisco Firepower storage:TransportableFlashModule:size
        managed object property"
    ::= { cfprApStorageTransportableFlashModuleEntry 14 }

cfprApStorageTransportableFlashModuleVendor OBJECT-TYPE
    SYNTAX       SnmpAdminString
    MAX-ACCESS   read-only
    STATUS       current
    DESCRIPTION
        "Cisco Firepower storage:TransportableFlashModule:vendor
        managed object property"
    ::= { cfprApStorageTransportableFlashModuleEntry 15 }

cfprApStorageVirtualDriveTable OBJECT-TYPE
    SYNTAX           SEQUENCE OF CfprApStorageVirtualDriveEntry
    MAX-ACCESS       not-accessible
    STATUS           current
    DESCRIPTION
        "Cisco Firepower storage:VirtualDrive managed object table"
    ::= { cfprApStorageObjects 38 }

cfprApStorageVirtualDriveEntry OBJECT-TYPE
    SYNTAX           CfprApStorageVirtualDriveEntry
    MAX-ACCESS       not-accessible
    STATUS           current
    DESCRIPTION
        "Entry for the cfprApStorageVirtualDriveTable table."
    INDEX { cfprApStorageVirtualDriveInstanceId }
    ::= { cfprApStorageVirtualDriveTable 1 }

CfprApStorageVirtualDriveEntry ::= SEQUENCE {
    cfprApStorageVirtualDriveInstanceId                              CfprApManagedObjectId,
    cfprApStorageVirtualDriveDn                                      CfprApManagedObjectDn,
    cfprApStorageVirtualDriveRn                                      SnmpAdminString,
    cfprApStorageVirtualDriveAccessPolicy                            CfprApStorageAccessType,
    cfprApStorageVirtualDriveActualWriteCachePolicy                  CfprApStorageActualWriteType,
    cfprApStorageVirtualDriveBlockSize                               Gauge32,
    cfprApStorageVirtualDriveBootable                                CfprApStorageBootableType,
    cfprApStorageVirtualDriveConfiguredWriteCachePolicy              CfprApStorageConfiguredWriteType,
    cfprApStorageVirtualDriveConnectionProtocol                      CfprApStorageConnectionProtocol,
    cfprApStorageVirtualDriveDriveCache                              CfprApStorageCacheType,
    cfprApStorageVirtualDriveDriveState                              CfprApStorageVDriveState,
    cfprApStorageVirtualDriveId                                      Gauge32,
    cfprApStorageVirtualDriveIoPolicy                                CfprApStorageIOType,
    cfprApStorageVirtualDriveLc                                      CfprApFsmLifecycle,
    cfprApStorageVirtualDriveModel                                   SnmpAdminString,
    cfprApStorageVirtualDriveNumberOfBlocks                          Unsigned64,
    cfprApStorageVirtualDriveOperQualifierReason                     SnmpAdminString,
    cfprApStorageVirtualDriveOperability                             CfprApEquipmentOperability,
    cfprApStorageVirtualDrivePresence                                CfprApEquipmentPresence,
    cfprApStorageVirtualDriveReadPolicy                              CfprApStorageReadType,
    cfprApStorageVirtualDriveRevision                                SnmpAdminString,
    cfprApStorageVirtualDriveSerial                                  SnmpAdminString,
    cfprApStorageVirtualDriveSize                                    Unsigned64,
    cfprApStorageVirtualDriveStripSize                               Unsigned64,
    cfprApStorageVirtualDriveType                                    CfprApStorageLunType,
    cfprApStorageVirtualDriveVendor                                  SnmpAdminString
}

cfprApStorageVirtualDriveInstanceId OBJECT-TYPE
    SYNTAX       CfprApManagedObjectId
    MAX-ACCESS   not-accessible
    STATUS       current
    DESCRIPTION
        "Instance identifier of the managed object."
    ::= { cfprApStorageVirtualDriveEntry 1 }

cfprApStorageVirtualDriveDn OBJECT-TYPE
    SYNTAX       CfprApManagedObjectDn
    MAX-ACCESS   read-only
    STATUS       current
    DESCRIPTION
        "Cisco Firepower storage:VirtualDrive:dn managed object property"
    ::= { cfprApStorageVirtualDriveEntry 2 }

cfprApStorageVirtualDriveRn OBJECT-TYPE
    SYNTAX       SnmpAdminString
    MAX-ACCESS   read-only
    STATUS       current
    DESCRIPTION
        "Cisco Firepower storage:VirtualDrive:rn managed object property"
    ::= { cfprApStorageVirtualDriveEntry 3 }

cfprApStorageVirtualDriveAccessPolicy OBJECT-TYPE
    SYNTAX       CfprApStorageAccessType
    MAX-ACCESS   read-only
    STATUS       current
    DESCRIPTION
        "Cisco Firepower storage:VirtualDrive:accessPolicy
        managed object property"
    ::= { cfprApStorageVirtualDriveEntry 4 }

cfprApStorageVirtualDriveActualWriteCachePolicy OBJECT-TYPE
    SYNTAX       CfprApStorageActualWriteType
    MAX-ACCESS   read-only
    STATUS       current
    DESCRIPTION
        "Cisco Firepower storage:VirtualDrive:actualWriteCachePolicy
        managed object property"
    ::= { cfprApStorageVirtualDriveEntry 5 }

cfprApStorageVirtualDriveBlockSize OBJECT-TYPE
    SYNTAX       Gauge32
    MAX-ACCESS   read-only
    STATUS       current
    DESCRIPTION
        "Cisco Firepower storage:VirtualDrive:blockSize
        managed object property"
    ::= { cfprApStorageVirtualDriveEntry 6 }

cfprApStorageVirtualDriveBootable OBJECT-TYPE
    SYNTAX       CfprApStorageBootableType
    MAX-ACCESS   read-only
    STATUS       current
    DESCRIPTION
        "Cisco Firepower storage:VirtualDrive:bootable
        managed object property"
    ::= { cfprApStorageVirtualDriveEntry 7 }

cfprApStorageVirtualDriveConfiguredWriteCachePolicy OBJECT-TYPE
    SYNTAX       CfprApStorageConfiguredWriteType
    MAX-ACCESS   read-only
    STATUS       current
    DESCRIPTION
        "Cisco Firepower storage:VirtualDrive:configuredWriteCachePolicy
        managed object property"
    ::= { cfprApStorageVirtualDriveEntry 8 }

cfprApStorageVirtualDriveConnectionProtocol OBJECT-TYPE
    SYNTAX       CfprApStorageConnectionProtocol
    MAX-ACCESS   read-only
    STATUS       current
    DESCRIPTION
        "Cisco Firepower storage:VirtualDrive:connectionProtocol
        managed object property"
    ::= { cfprApStorageVirtualDriveEntry 9 }

cfprApStorageVirtualDriveDriveCache OBJECT-TYPE
    SYNTAX       CfprApStorageCacheType
    MAX-ACCESS   read-only
    STATUS       current
    DESCRIPTION
        "Cisco Firepower storage:VirtualDrive:driveCache
        managed object property"
    ::= { cfprApStorageVirtualDriveEntry 10 }

cfprApStorageVirtualDriveDriveState OBJECT-TYPE
    SYNTAX       CfprApStorageVDriveState
    MAX-ACCESS   read-only
    STATUS       current
    DESCRIPTION
        "Cisco Firepower storage:VirtualDrive:driveState
        managed object property"
    ::= { cfprApStorageVirtualDriveEntry 11 }

cfprApStorageVirtualDriveId OBJECT-TYPE
    SYNTAX       Gauge32
    MAX-ACCESS   read-only
    STATUS       current
    DESCRIPTION
        "Cisco Firepower storage:VirtualDrive:id managed object property"
    ::= { cfprApStorageVirtualDriveEntry 12 }

cfprApStorageVirtualDriveIoPolicy OBJECT-TYPE
    SYNTAX       CfprApStorageIOType
    MAX-ACCESS   read-only
    STATUS       current
    DESCRIPTION
        "Cisco Firepower storage:VirtualDrive:ioPolicy
        managed object property"
    ::= { cfprApStorageVirtualDriveEntry 13 }

cfprApStorageVirtualDriveLc OBJECT-TYPE
    SYNTAX       CfprApFsmLifecycle
    MAX-ACCESS   read-only
    STATUS       current
    DESCRIPTION
        "Cisco Firepower storage:VirtualDrive:lc managed object property"
    ::= { cfprApStorageVirtualDriveEntry 14 }

cfprApStorageVirtualDriveModel OBJECT-TYPE
    SYNTAX       SnmpAdminString
    MAX-ACCESS   read-only
    STATUS       current
    DESCRIPTION
        "Cisco Firepower storage:VirtualDrive:model managed
        object property"
    ::= { cfprApStorageVirtualDriveEntry 15 }

cfprApStorageVirtualDriveNumberOfBlocks OBJECT-TYPE
    SYNTAX       Unsigned64
    MAX-ACCESS   read-only
    STATUS       current
    DESCRIPTION
        "Cisco Firepower storage:VirtualDrive:numberOfBlocks
        managed object property"
    ::= { cfprApStorageVirtualDriveEntry 16 }

cfprApStorageVirtualDriveOperQualifierReason OBJECT-TYPE
    SYNTAX       SnmpAdminString
    MAX-ACCESS   read-only
    STATUS       current
    DESCRIPTION
        "Cisco Firepower storage:VirtualDrive:operQualifierReason
        managed object property"
    ::= { cfprApStorageVirtualDriveEntry 17 }

cfprApStorageVirtualDriveOperability OBJECT-TYPE
    SYNTAX       CfprApEquipmentOperability
    MAX-ACCESS   read-only
    STATUS       current
    DESCRIPTION
        "Cisco Firepower storage:VirtualDrive:operability
        managed object property"
    ::= { cfprApStorageVirtualDriveEntry 18 }

cfprApStorageVirtualDrivePresence OBJECT-TYPE
    SYNTAX       CfprApEquipmentPresence
    MAX-ACCESS   read-only
    STATUS       current
    DESCRIPTION
        "Cisco Firepower storage:VirtualDrive:presence
        managed object property"
    ::= { cfprApStorageVirtualDriveEntry 19 }

cfprApStorageVirtualDriveReadPolicy OBJECT-TYPE
    SYNTAX       CfprApStorageReadType
    MAX-ACCESS   read-only
    STATUS       current
    DESCRIPTION
        "Cisco Firepower storage:VirtualDrive:readPolicy
        managed object property"
    ::= { cfprApStorageVirtualDriveEntry 20 }

cfprApStorageVirtualDriveRevision OBJECT-TYPE
    SYNTAX       SnmpAdminString
    MAX-ACCESS   read-only
    STATUS       current
    DESCRIPTION
        "Cisco Firepower storage:VirtualDrive:revision
        managed object property"
    ::= { cfprApStorageVirtualDriveEntry 21 }

cfprApStorageVirtualDriveSerial OBJECT-TYPE
    SYNTAX       SnmpAdminString
    MAX-ACCESS   read-only
    STATUS       current
    DESCRIPTION
        "Cisco Firepower storage:VirtualDrive:serial managed
        object property"
    ::= { cfprApStorageVirtualDriveEntry 22 }

cfprApStorageVirtualDriveSize OBJECT-TYPE
    SYNTAX       Unsigned64
    MAX-ACCESS   read-only
    STATUS       current
    DESCRIPTION
        "Cisco Firepower storage:VirtualDrive:size managed
        object property"
    ::= { cfprApStorageVirtualDriveEntry 23 }

cfprApStorageVirtualDriveStripSize OBJECT-TYPE
    SYNTAX       Unsigned64
    MAX-ACCESS   read-only
    STATUS       current
    DESCRIPTION
        "Cisco Firepower storage:VirtualDrive:stripSize
        managed object property"
    ::= { cfprApStorageVirtualDriveEntry 24 }

cfprApStorageVirtualDriveType OBJECT-TYPE
    SYNTAX       CfprApStorageLunType
    MAX-ACCESS   read-only
    STATUS       current
    DESCRIPTION
        "Cisco Firepower storage:VirtualDrive:type managed
        object property"
    ::= { cfprApStorageVirtualDriveEntry 25 }

cfprApStorageVirtualDriveVendor OBJECT-TYPE
    SYNTAX       SnmpAdminString
    MAX-ACCESS   read-only
    STATUS       current
    DESCRIPTION
        "Cisco Firepower storage:VirtualDrive:vendor managed
        object property"
    ::= { cfprApStorageVirtualDriveEntry 26 }

cfprApStorageVsanRefTable OBJECT-TYPE
    SYNTAX           SEQUENCE OF CfprApStorageVsanRefEntry
    MAX-ACCESS       not-accessible
    STATUS           current
    DESCRIPTION
        "Cisco Firepower storage:VsanRef managed object table"
    ::= { cfprApStorageObjects 39 }

cfprApStorageVsanRefEntry OBJECT-TYPE
    SYNTAX           CfprApStorageVsanRefEntry
    MAX-ACCESS       not-accessible
    STATUS           current
    DESCRIPTION
        "Entry for the cfprApStorageVsanRefTable table."
    INDEX { cfprApStorageVsanRefInstanceId }
    ::= { cfprApStorageVsanRefTable 1 }

CfprApStorageVsanRefEntry ::= SEQUENCE {
    cfprApStorageVsanRefInstanceId                                   CfprApManagedObjectId,
    cfprApStorageVsanRefDn                                           CfprApManagedObjectDn,
    cfprApStorageVsanRefRn                                           SnmpAdminString,
    cfprApStorageVsanRefConfigQualifier                              CfprApVnicConfigIssues,
    cfprApStorageVsanRefName                                         SnmpAdminString,
    cfprApStorageVsanRefOperVnetDn                                   SnmpAdminString,
    cfprApStorageVsanRefOperVnetName                                 SnmpAdminString,
    cfprApStorageVsanRefSwitchId                                     CfprApStorageVsanRefSwitchId,
    cfprApStorageVsanRefVnet                                         Gauge32,
    cfprApStorageVsanRefZoningState                                  CfprApFabricZoningState
}

cfprApStorageVsanRefInstanceId OBJECT-TYPE
    SYNTAX       CfprApManagedObjectId
    MAX-ACCESS   not-accessible
    STATUS       current
    DESCRIPTION
        "Instance identifier of the managed object."
    ::= { cfprApStorageVsanRefEntry 1 }

cfprApStorageVsanRefDn OBJECT-TYPE
    SYNTAX       CfprApManagedObjectDn
    MAX-ACCESS   read-only
    STATUS       current
    DESCRIPTION
        "Cisco Firepower storage:VsanRef:dn managed object property"
    ::= { cfprApStorageVsanRefEntry 2 }

cfprApStorageVsanRefRn OBJECT-TYPE
    SYNTAX       SnmpAdminString
    MAX-ACCESS   read-only
    STATUS       current
    DESCRIPTION
        "Cisco Firepower storage:VsanRef:rn managed object property"
    ::= { cfprApStorageVsanRefEntry 3 }

cfprApStorageVsanRefConfigQualifier OBJECT-TYPE
    SYNTAX       CfprApVnicConfigIssues
    MAX-ACCESS   read-only
    STATUS       current
    DESCRIPTION
        "Cisco Firepower storage:VsanRef:configQualifier
        managed object property"
    ::= { cfprApStorageVsanRefEntry 4 }

cfprApStorageVsanRefName OBJECT-TYPE
    SYNTAX       SnmpAdminString
    MAX-ACCESS   read-only
    STATUS       current
    DESCRIPTION
        "Cisco Firepower storage:VsanRef:name managed object property"
    ::= { cfprApStorageVsanRefEntry 5 }

cfprApStorageVsanRefOperVnetDn OBJECT-TYPE
    SYNTAX       SnmpAdminString
    MAX-ACCESS   read-only
    STATUS       current
    DESCRIPTION
        "Cisco Firepower storage:VsanRef:operVnetDn managed
        object property"
    ::= { cfprApStorageVsanRefEntry 6 }

cfprApStorageVsanRefOperVnetName OBJECT-TYPE
    SYNTAX       SnmpAdminString
    MAX-ACCESS   read-only
    STATUS       current
    DESCRIPTION
        "Cisco Firepower storage:VsanRef:operVnetName managed
        object property"
    ::= { cfprApStorageVsanRefEntry 7 }

cfprApStorageVsanRefSwitchId OBJECT-TYPE
    SYNTAX       CfprApStorageVsanRefSwitchId
    MAX-ACCESS   read-only
    STATUS       current
    DESCRIPTION
        "Cisco Firepower storage:VsanRef:switchId managed object property"
    ::= { cfprApStorageVsanRefEntry 8 }

cfprApStorageVsanRefVnet OBJECT-TYPE
    SYNTAX       Gauge32
    MAX-ACCESS   read-only
    STATUS       current
    DESCRIPTION
        "Cisco Firepower storage:VsanRef:vnet managed object property"
    ::= { cfprApStorageVsanRefEntry 9 }

cfprApStorageVsanRefZoningState OBJECT-TYPE
    SYNTAX       CfprApFabricZoningState
    MAX-ACCESS   read-only
    STATUS       current
    DESCRIPTION
        "Cisco Firepower storage:VsanRef:zoningState managed
        object property"
    ::= { cfprApStorageVsanRefEntry 10 }

END
