-- *********************************************************************
-- CISCO-FIREPOWER-AP-CIMCVMEDIA-MIB.my
-- 
-- MIB representation of the Cisco Firepower
-- CIMCVMEDIA management information model package
-- 
-- Created July 2022 by Charles Bullis
-- 
-- Copyright (c) 2005-2022 Cisco Systems, Inc. All rights reserved.
-- 
-- *********************************************************************

CISCO-FIREPOWER-AP-CIMCVMEDIA-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApCimcvmediaDeviceType,
    CfprApCimcvmediaErrorType,
    CfprApCimcvmediaMountConfigRetryOnMountFail,
    CfprApCimcvmediaMountStatus,
    CfprApCimcvmediaTransport,
    CfprApPolicyPolicyOwner
        FROM CISCO-FIREPOWER-AP-TC-MIB;

cfprApCimcvmediaObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        CIMCVMEDIA management information model package"
    ::= { ciscoFirepowerApMIBObjects 10 }

cfprApCimcvmediaActualMountEntryTable OBJECT-TYPE
    SYNTAX           SEQUENCE OF CfprApCimcvmediaActualMountEntryEntry
    MAX-ACCESS       not-accessible
    STATUS           current
    DESCRIPTION
        "Cisco Firepower cimcvmedia:ActualMountEntry managed object table"
    ::= { cfprApCimcvmediaObjects 1 }

cfprApCimcvmediaActualMountEntryEntry OBJECT-TYPE
    SYNTAX           CfprApCimcvmediaActualMountEntryEntry
    MAX-ACCESS       not-accessible
    STATUS           current
    DESCRIPTION
        "Entry for the cfprApCimcvmediaActualMountEntryTable table."
    INDEX { cfprApCimcvmediaActualMountEntryInstanceId }
    ::= { cfprApCimcvmediaActualMountEntryTable 1 }

CfprApCimcvmediaActualMountEntryEntry ::= SEQUENCE {
    cfprApCimcvmediaActualMountEntryInstanceId                       CfprApManagedObjectId,
    cfprApCimcvmediaActualMountEntryDn                               CfprApManagedObjectDn,
    cfprApCimcvmediaActualMountEntryRn                               SnmpAdminString,
    cfprApCimcvmediaActualMountEntryDeviceType                       CfprApCimcvmediaDeviceType,
    cfprApCimcvmediaActualMountEntryEncPwd                           SnmpAdminString,
    cfprApCimcvmediaActualMountEntryErrorType                        CfprApCimcvmediaErrorType,
    cfprApCimcvmediaActualMountEntryImageFileName                    SnmpAdminString,
    cfprApCimcvmediaActualMountEntryImagePath                        SnmpAdminString,
    cfprApCimcvmediaActualMountEntryMappingName                      SnmpAdminString,
    cfprApCimcvmediaActualMountEntryMountProtocol                    CfprApCimcvmediaTransport,
    cfprApCimcvmediaActualMountEntryOperMountStatus                  CfprApCimcvmediaMountStatus,
    cfprApCimcvmediaActualMountEntryPassword                         SnmpAdminString,
    cfprApCimcvmediaActualMountEntryPwdSet                           TruthValue,
    cfprApCimcvmediaActualMountEntryRemoteHost                       SnmpAdminString,
    cfprApCimcvmediaActualMountEntryRemoteIpAddress                  SnmpAdminString,
    cfprApCimcvmediaActualMountEntryRemotePort                       Gauge32,
    cfprApCimcvmediaActualMountEntryUserId                           SnmpAdminString,
    cfprApCimcvmediaActualMountEntryVirtualDiskId                    Gauge32
}

cfprApCimcvmediaActualMountEntryInstanceId OBJECT-TYPE
    SYNTAX       CfprApManagedObjectId
    MAX-ACCESS   not-accessible
    STATUS       current
    DESCRIPTION
        "Instance identifier of the managed object."
    ::= { cfprApCimcvmediaActualMountEntryEntry 1 }

cfprApCimcvmediaActualMountEntryDn OBJECT-TYPE
    SYNTAX       CfprApManagedObjectDn
    MAX-ACCESS   read-only
    STATUS       current
    DESCRIPTION
        "Cisco Firepower cimcvmedia:ActualMountEntry:dn
        managed object property"
    ::= { cfprApCimcvmediaActualMountEntryEntry 2 }

cfprApCimcvmediaActualMountEntryRn OBJECT-TYPE
    SYNTAX       SnmpAdminString
    MAX-ACCESS   read-only
    STATUS       current
    DESCRIPTION
        "Cisco Firepower cimcvmedia:ActualMountEntry:rn
        managed object property"
    ::= { cfprApCimcvmediaActualMountEntryEntry 3 }

cfprApCimcvmediaActualMountEntryDeviceType OBJECT-TYPE
    SYNTAX       CfprApCimcvmediaDeviceType
    MAX-ACCESS   read-only
    STATUS       current
    DESCRIPTION
        "Cisco Firepower cimcvmedia:ActualMountEntry:deviceType
        managed object property"
    ::= { cfprApCimcvmediaActualMountEntryEntry 4 }

cfprApCimcvmediaActualMountEntryEncPwd OBJECT-TYPE
    SYNTAX       SnmpAdminString
    MAX-ACCESS   read-only
    STATUS       current
    DESCRIPTION
        "Cisco Firepower cimcvmedia:ActualMountEntry:encPwd
        managed object property"
    ::= { cfprApCimcvmediaActualMountEntryEntry 5 }

cfprApCimcvmediaActualMountEntryErrorType OBJECT-TYPE
    SYNTAX       CfprApCimcvmediaErrorType
    MAX-ACCESS   read-only
    STATUS       current
    DESCRIPTION
        "Cisco Firepower cimcvmedia:ActualMountEntry:errorType
        managed object property"
    ::= { cfprApCimcvmediaActualMountEntryEntry 6 }

cfprApCimcvmediaActualMountEntryImageFileName OBJECT-TYPE
    SYNTAX       SnmpAdminString
    MAX-ACCESS   read-only
    STATUS       current
    DESCRIPTION
        "Cisco Firepower cimcvmedia:ActualMountEntry:imageFileName
        managed object property"
    ::= { cfprApCimcvmediaActualMountEntryEntry 7 }

cfprApCimcvmediaActualMountEntryImagePath OBJECT-TYPE
    SYNTAX       SnmpAdminString
    MAX-ACCESS   read-only
    STATUS       current
    DESCRIPTION
        "Cisco Firepower cimcvmedia:ActualMountEntry:imagePath
        managed object property"
    ::= { cfprApCimcvmediaActualMountEntryEntry 8 }

cfprApCimcvmediaActualMountEntryMappingName OBJECT-TYPE
    SYNTAX       SnmpAdminString
    MAX-ACCESS   read-only
    STATUS       current
    DESCRIPTION
        "Cisco Firepower cimcvmedia:ActualMountEntry:mappingName
        managed object property"
    ::= { cfprApCimcvmediaActualMountEntryEntry 9 }

cfprApCimcvmediaActualMountEntryMountProtocol OBJECT-TYPE
    SYNTAX       CfprApCimcvmediaTransport
    MAX-ACCESS   read-only
    STATUS       current
    DESCRIPTION
        "Cisco Firepower cimcvmedia:ActualMountEntry:mountProtocol
        managed object property"
    ::= { cfprApCimcvmediaActualMountEntryEntry 10 }

cfprApCimcvmediaActualMountEntryOperMountStatus OBJECT-TYPE
    SYNTAX       CfprApCimcvmediaMountStatus
    MAX-ACCESS   read-only
    STATUS       current
    DESCRIPTION
        "Cisco Firepower cimcvmedia:ActualMountEntry:operMountStatus
        managed object property"
    ::= { cfprApCimcvmediaActualMountEntryEntry 11 }

cfprApCimcvmediaActualMountEntryPassword OBJECT-TYPE
    SYNTAX       SnmpAdminString
    MAX-ACCESS   read-only
    STATUS       current
    DESCRIPTION
        "Cisco Firepower cimcvmedia:ActualMountEntry:password
        managed object property"
    ::= { cfprApCimcvmediaActualMountEntryEntry 12 }

cfprApCimcvmediaActualMountEntryPwdSet OBJECT-TYPE
    SYNTAX       TruthValue
    MAX-ACCESS   read-only
    STATUS       current
    DESCRIPTION
        "Cisco Firepower cimcvmedia:ActualMountEntry:pwdSet
        managed object property"
    ::= { cfprApCimcvmediaActualMountEntryEntry 13 }

cfprApCimcvmediaActualMountEntryRemoteHost OBJECT-TYPE
    SYNTAX       SnmpAdminString
    MAX-ACCESS   read-only
    STATUS       current
    DESCRIPTION
        "Cisco Firepower cimcvmedia:ActualMountEntry:remoteHost
        managed object property"
    ::= { cfprApCimcvmediaActualMountEntryEntry 14 }

cfprApCimcvmediaActualMountEntryRemoteIpAddress OBJECT-TYPE
    SYNTAX       SnmpAdminString
    MAX-ACCESS   read-only
    STATUS       current
    DESCRIPTION
        "Cisco Firepower cimcvmedia:ActualMountEntry:remoteIpAddress
        managed object property"
    ::= { cfprApCimcvmediaActualMountEntryEntry 15 }

cfprApCimcvmediaActualMountEntryRemotePort OBJECT-TYPE
    SYNTAX       Gauge32
    MAX-ACCESS   read-only
    STATUS       current
    DESCRIPTION
        "Cisco Firepower cimcvmedia:ActualMountEntry:remotePort
        managed object property"
    ::= { cfprApCimcvmediaActualMountEntryEntry 16 }

cfprApCimcvmediaActualMountEntryUserId OBJECT-TYPE
    SYNTAX       SnmpAdminString
    MAX-ACCESS   read-only
    STATUS       current
    DESCRIPTION
        "Cisco Firepower cimcvmedia:ActualMountEntry:userId
        managed object property"
    ::= { cfprApCimcvmediaActualMountEntryEntry 17 }

cfprApCimcvmediaActualMountEntryVirtualDiskId OBJECT-TYPE
    SYNTAX       Gauge32
    MAX-ACCESS   read-only
    STATUS       current
    DESCRIPTION
        "Cisco Firepower cimcvmedia:ActualMountEntry:virtualDiskId
        managed object property"
    ::= { cfprApCimcvmediaActualMountEntryEntry 18 }

cfprApCimcvmediaActualMountListTable OBJECT-TYPE
    SYNTAX           SEQUENCE OF CfprApCimcvmediaActualMountListEntry
    MAX-ACCESS       not-accessible
    STATUS           current
    DESCRIPTION
        "Cisco Firepower cimcvmedia:ActualMountList managed object table"
    ::= { cfprApCimcvmediaObjects 2 }

cfprApCimcvmediaActualMountListEntry OBJECT-TYPE
    SYNTAX           CfprApCimcvmediaActualMountListEntry
    MAX-ACCESS       not-accessible
    STATUS           current
    DESCRIPTION
        "Entry for the cfprApCimcvmediaActualMountListTable table."
    INDEX { cfprApCimcvmediaActualMountListInstanceId }
    ::= { cfprApCimcvmediaActualMountListTable 1 }

CfprApCimcvmediaActualMountListEntry ::= SEQUENCE {
    cfprApCimcvmediaActualMountListInstanceId                        CfprApManagedObjectId,
    cfprApCimcvmediaActualMountListDn                                CfprApManagedObjectDn,
    cfprApCimcvmediaActualMountListRn                                SnmpAdminString
}

cfprApCimcvmediaActualMountListInstanceId OBJECT-TYPE
    SYNTAX       CfprApManagedObjectId
    MAX-ACCESS   not-accessible
    STATUS       current
    DESCRIPTION
        "Instance identifier of the managed object."
    ::= { cfprApCimcvmediaActualMountListEntry 1 }

cfprApCimcvmediaActualMountListDn OBJECT-TYPE
    SYNTAX       CfprApManagedObjectDn
    MAX-ACCESS   read-only
    STATUS       current
    DESCRIPTION
        "Cisco Firepower cimcvmedia:ActualMountList:dn
        managed object property"
    ::= { cfprApCimcvmediaActualMountListEntry 2 }

cfprApCimcvmediaActualMountListRn OBJECT-TYPE
    SYNTAX       SnmpAdminString
    MAX-ACCESS   read-only
    STATUS       current
    DESCRIPTION
        "Cisco Firepower cimcvmedia:ActualMountList:rn
        managed object property"
    ::= { cfprApCimcvmediaActualMountListEntry 3 }

cfprApCimcvmediaConfigMountEntryTable OBJECT-TYPE
    SYNTAX           SEQUENCE OF CfprApCimcvmediaConfigMountEntryEntry
    MAX-ACCESS       not-accessible
    STATUS           current
    DESCRIPTION
        "Cisco Firepower cimcvmedia:ConfigMountEntry managed object table"
    ::= { cfprApCimcvmediaObjects 3 }

cfprApCimcvmediaConfigMountEntryEntry OBJECT-TYPE
    SYNTAX           CfprApCimcvmediaConfigMountEntryEntry
    MAX-ACCESS       not-accessible
    STATUS           current
    DESCRIPTION
        "Entry for the cfprApCimcvmediaConfigMountEntryTable table."
    INDEX { cfprApCimcvmediaConfigMountEntryInstanceId }
    ::= { cfprApCimcvmediaConfigMountEntryTable 1 }

CfprApCimcvmediaConfigMountEntryEntry ::= SEQUENCE {
    cfprApCimcvmediaConfigMountEntryInstanceId                       CfprApManagedObjectId,
    cfprApCimcvmediaConfigMountEntryDn                               CfprApManagedObjectDn,
    cfprApCimcvmediaConfigMountEntryRn                               SnmpAdminString,
    cfprApCimcvmediaConfigMountEntryDescription                      SnmpAdminString,
    cfprApCimcvmediaConfigMountEntryDeviceType                       CfprApCimcvmediaDeviceType,
    cfprApCimcvmediaConfigMountEntryEncPwd                           SnmpAdminString,
    cfprApCimcvmediaConfigMountEntryImageFileName                    SnmpAdminString,
    cfprApCimcvmediaConfigMountEntryImagePath                        SnmpAdminString,
    cfprApCimcvmediaConfigMountEntryMappingName                      SnmpAdminString,
    cfprApCimcvmediaConfigMountEntryMountProtocol                    CfprApCimcvmediaTransport,
    cfprApCimcvmediaConfigMountEntryPassword                         SnmpAdminString,
    cfprApCimcvmediaConfigMountEntryPwdSet                           TruthValue,
    cfprApCimcvmediaConfigMountEntryRemoteHost                       SnmpAdminString,
    cfprApCimcvmediaConfigMountEntryRemoteIpAddress                  SnmpAdminString,
    cfprApCimcvmediaConfigMountEntryRemotePort                       Gauge32,
    cfprApCimcvmediaConfigMountEntryUserId                           SnmpAdminString
}

cfprApCimcvmediaConfigMountEntryInstanceId OBJECT-TYPE
    SYNTAX       CfprApManagedObjectId
    MAX-ACCESS   not-accessible
    STATUS       current
    DESCRIPTION
        "Instance identifier of the managed object."
    ::= { cfprApCimcvmediaConfigMountEntryEntry 1 }

cfprApCimcvmediaConfigMountEntryDn OBJECT-TYPE
    SYNTAX       CfprApManagedObjectDn
    MAX-ACCESS   read-only
    STATUS       current
    DESCRIPTION
        "Cisco Firepower cimcvmedia:ConfigMountEntry:dn
        managed object property"
    ::= { cfprApCimcvmediaConfigMountEntryEntry 2 }

cfprApCimcvmediaConfigMountEntryRn OBJECT-TYPE
    SYNTAX       SnmpAdminString
    MAX-ACCESS   read-only
    STATUS       current
    DESCRIPTION
        "Cisco Firepower cimcvmedia:ConfigMountEntry:rn
        managed object property"
    ::= { cfprApCimcvmediaConfigMountEntryEntry 3 }

cfprApCimcvmediaConfigMountEntryDescription OBJECT-TYPE
    SYNTAX       SnmpAdminString
    MAX-ACCESS   read-only
    STATUS       current
    DESCRIPTION
        "Cisco Firepower cimcvmedia:ConfigMountEntry:description
        managed object property"
    ::= { cfprApCimcvmediaConfigMountEntryEntry 4 }

cfprApCimcvmediaConfigMountEntryDeviceType OBJECT-TYPE
    SYNTAX       CfprApCimcvmediaDeviceType
    MAX-ACCESS   read-only
    STATUS       current
    DESCRIPTION
        "Cisco Firepower cimcvmedia:ConfigMountEntry:deviceType
        managed object property"
    ::= { cfprApCimcvmediaConfigMountEntryEntry 5 }

cfprApCimcvmediaConfigMountEntryEncPwd OBJECT-TYPE
    SYNTAX       SnmpAdminString
    MAX-ACCESS   read-only
    STATUS       current
    DESCRIPTION
        "Cisco Firepower cimcvmedia:ConfigMountEntry:encPwd
        managed object property"
    ::= { cfprApCimcvmediaConfigMountEntryEntry 6 }

cfprApCimcvmediaConfigMountEntryImageFileName OBJECT-TYPE
    SYNTAX       SnmpAdminString
    MAX-ACCESS   read-only
    STATUS       current
    DESCRIPTION
        "Cisco Firepower cimcvmedia:ConfigMountEntry:imageFileName
        managed object property"
    ::= { cfprApCimcvmediaConfigMountEntryEntry 7 }

cfprApCimcvmediaConfigMountEntryImagePath OBJECT-TYPE
    SYNTAX       SnmpAdminString
    MAX-ACCESS   read-only
    STATUS       current
    DESCRIPTION
        "Cisco Firepower cimcvmedia:ConfigMountEntry:imagePath
        managed object property"
    ::= { cfprApCimcvmediaConfigMountEntryEntry 8 }

cfprApCimcvmediaConfigMountEntryMappingName OBJECT-TYPE
    SYNTAX       SnmpAdminString
    MAX-ACCESS   read-only
    STATUS       current
    DESCRIPTION
        "Cisco Firepower cimcvmedia:ConfigMountEntry:mappingName
        managed object property"
    ::= { cfprApCimcvmediaConfigMountEntryEntry 9 }

cfprApCimcvmediaConfigMountEntryMountProtocol OBJECT-TYPE
    SYNTAX       CfprApCimcvmediaTransport
    MAX-ACCESS   read-only
    STATUS       current
    DESCRIPTION
        "Cisco Firepower cimcvmedia:ConfigMountEntry:mountProtocol
        managed object property"
    ::= { cfprApCimcvmediaConfigMountEntryEntry 10 }

cfprApCimcvmediaConfigMountEntryPassword OBJECT-TYPE
    SYNTAX       SnmpAdminString
    MAX-ACCESS   read-only
    STATUS       current
    DESCRIPTION
        "Cisco Firepower cimcvmedia:ConfigMountEntry:password
        managed object property"
    ::= { cfprApCimcvmediaConfigMountEntryEntry 11 }

cfprApCimcvmediaConfigMountEntryPwdSet OBJECT-TYPE
    SYNTAX       TruthValue
    MAX-ACCESS   read-only
    STATUS       current
    DESCRIPTION
        "Cisco Firepower cimcvmedia:ConfigMountEntry:pwdSet
        managed object property"
    ::= { cfprApCimcvmediaConfigMountEntryEntry 12 }

cfprApCimcvmediaConfigMountEntryRemoteHost OBJECT-TYPE
    SYNTAX       SnmpAdminString
    MAX-ACCESS   read-only
    STATUS       current
    DESCRIPTION
        "Cisco Firepower cimcvmedia:ConfigMountEntry:remoteHost
        managed object property"
    ::= { cfprApCimcvmediaConfigMountEntryEntry 13 }

cfprApCimcvmediaConfigMountEntryRemoteIpAddress OBJECT-TYPE
    SYNTAX       SnmpAdminString
    MAX-ACCESS   read-only
    STATUS       current
    DESCRIPTION
        "Cisco Firepower cimcvmedia:ConfigMountEntry:remoteIpAddress
        managed object property"
    ::= { cfprApCimcvmediaConfigMountEntryEntry 14 }

cfprApCimcvmediaConfigMountEntryRemotePort OBJECT-TYPE
    SYNTAX       Gauge32
    MAX-ACCESS   read-only
    STATUS       current
    DESCRIPTION
        "Cisco Firepower cimcvmedia:ConfigMountEntry:remotePort
        managed object property"
    ::= { cfprApCimcvmediaConfigMountEntryEntry 15 }

cfprApCimcvmediaConfigMountEntryUserId OBJECT-TYPE
    SYNTAX       SnmpAdminString
    MAX-ACCESS   read-only
    STATUS       current
    DESCRIPTION
        "Cisco Firepower cimcvmedia:ConfigMountEntry:userId
        managed object property"
    ::= { cfprApCimcvmediaConfigMountEntryEntry 16 }

cfprApCimcvmediaExtMgmtRuleEntryTable OBJECT-TYPE
    SYNTAX           SEQUENCE OF CfprApCimcvmediaExtMgmtRuleEntryEntry
    MAX-ACCESS       not-accessible
    STATUS           current
    DESCRIPTION
        "Cisco Firepower cimcvmedia:ExtMgmtRuleEntry managed object table"
    ::= { cfprApCimcvmediaObjects 4 }

cfprApCimcvmediaExtMgmtRuleEntryEntry OBJECT-TYPE
    SYNTAX           CfprApCimcvmediaExtMgmtRuleEntryEntry
    MAX-ACCESS       not-accessible
    STATUS           current
    DESCRIPTION
        "Entry for the cfprApCimcvmediaExtMgmtRuleEntryTable table."
    INDEX { cfprApCimcvmediaExtMgmtRuleEntryInstanceId }
    ::= { cfprApCimcvmediaExtMgmtRuleEntryTable 1 }

CfprApCimcvmediaExtMgmtRuleEntryEntry ::= SEQUENCE {
    cfprApCimcvmediaExtMgmtRuleEntryInstanceId                       CfprApManagedObjectId,
    cfprApCimcvmediaExtMgmtRuleEntryDn                               CfprApManagedObjectDn,
    cfprApCimcvmediaExtMgmtRuleEntryRn                               SnmpAdminString,
    cfprApCimcvmediaExtMgmtRuleEntryExtMgmtIpAddr                    InetAddressIPv4,
    cfprApCimcvmediaExtMgmtRuleEntryMappingName                      SnmpAdminString,
    cfprApCimcvmediaExtMgmtRuleEntryMgmtIfIpAddr                     InetAddressIPv4,
    cfprApCimcvmediaExtMgmtRuleEntryMountProtocol                    CfprApCimcvmediaTransport,
    cfprApCimcvmediaExtMgmtRuleEntryRemoteIpAddr                     InetAddressIPv4,
    cfprApCimcvmediaExtMgmtRuleEntryRemotePort                       Gauge32
}

cfprApCimcvmediaExtMgmtRuleEntryInstanceId OBJECT-TYPE
    SYNTAX       CfprApManagedObjectId
    MAX-ACCESS   not-accessible
    STATUS       current
    DESCRIPTION
        "Instance identifier of the managed object."
    ::= { cfprApCimcvmediaExtMgmtRuleEntryEntry 1 }

cfprApCimcvmediaExtMgmtRuleEntryDn OBJECT-TYPE
    SYNTAX       CfprApManagedObjectDn
    MAX-ACCESS   read-only
    STATUS       current
    DESCRIPTION
        "Cisco Firepower cimcvmedia:ExtMgmtRuleEntry:dn
        managed object property"
    ::= { cfprApCimcvmediaExtMgmtRuleEntryEntry 2 }

cfprApCimcvmediaExtMgmtRuleEntryRn OBJECT-TYPE
    SYNTAX       SnmpAdminString
    MAX-ACCESS   read-only
    STATUS       current
    DESCRIPTION
        "Cisco Firepower cimcvmedia:ExtMgmtRuleEntry:rn
        managed object property"
    ::= { cfprApCimcvmediaExtMgmtRuleEntryEntry 3 }

cfprApCimcvmediaExtMgmtRuleEntryExtMgmtIpAddr OBJECT-TYPE
    SYNTAX       InetAddressIPv4
    MAX-ACCESS   read-only
    STATUS       current
    DESCRIPTION
        "Cisco Firepower cimcvmedia:ExtMgmtRuleEntry:extMgmtIpAddr
        managed object property"
    ::= { cfprApCimcvmediaExtMgmtRuleEntryEntry 4 }

cfprApCimcvmediaExtMgmtRuleEntryMappingName OBJECT-TYPE
    SYNTAX       SnmpAdminString
    MAX-ACCESS   read-only
    STATUS       current
    DESCRIPTION
        "Cisco Firepower cimcvmedia:ExtMgmtRuleEntry:mappingName
        managed object property"
    ::= { cfprApCimcvmediaExtMgmtRuleEntryEntry 5 }

cfprApCimcvmediaExtMgmtRuleEntryMgmtIfIpAddr OBJECT-TYPE
    SYNTAX       InetAddressIPv4
    MAX-ACCESS   read-only
    STATUS       current
    DESCRIPTION
        "Cisco Firepower cimcvmedia:ExtMgmtRuleEntry:mgmtIfIpAddr
        managed object property"
    ::= { cfprApCimcvmediaExtMgmtRuleEntryEntry 6 }

cfprApCimcvmediaExtMgmtRuleEntryMountProtocol OBJECT-TYPE
    SYNTAX       CfprApCimcvmediaTransport
    MAX-ACCESS   read-only
    STATUS       current
    DESCRIPTION
        "Cisco Firepower cimcvmedia:ExtMgmtRuleEntry:mountProtocol
        managed object property"
    ::= { cfprApCimcvmediaExtMgmtRuleEntryEntry 7 }

cfprApCimcvmediaExtMgmtRuleEntryRemoteIpAddr OBJECT-TYPE
    SYNTAX       InetAddressIPv4
    MAX-ACCESS   read-only
    STATUS       current
    DESCRIPTION
        "Cisco Firepower cimcvmedia:ExtMgmtRuleEntry:remoteIpAddr
        managed object property"
    ::= { cfprApCimcvmediaExtMgmtRuleEntryEntry 8 }

cfprApCimcvmediaExtMgmtRuleEntryRemotePort OBJECT-TYPE
    SYNTAX       Gauge32
    MAX-ACCESS   read-only
    STATUS       current
    DESCRIPTION
        "Cisco Firepower cimcvmedia:ExtMgmtRuleEntry:remotePort
        managed object property"
    ::= { cfprApCimcvmediaExtMgmtRuleEntryEntry 9 }

cfprApCimcvmediaMountConfigDefTable OBJECT-TYPE
    SYNTAX           SEQUENCE OF CfprApCimcvmediaMountConfigDefEntry
    MAX-ACCESS       not-accessible
    STATUS           current
    DESCRIPTION
        "Cisco Firepower cimcvmedia:MountConfigDef managed object table"
    ::= { cfprApCimcvmediaObjects 5 }

cfprApCimcvmediaMountConfigDefEntry OBJECT-TYPE
    SYNTAX           CfprApCimcvmediaMountConfigDefEntry
    MAX-ACCESS       not-accessible
    STATUS           current
    DESCRIPTION
        "Entry for the cfprApCimcvmediaMountConfigDefTable table."
    INDEX { cfprApCimcvmediaMountConfigDefInstanceId }
    ::= { cfprApCimcvmediaMountConfigDefTable 1 }

CfprApCimcvmediaMountConfigDefEntry ::= SEQUENCE {
    cfprApCimcvmediaMountConfigDefInstanceId                         CfprApManagedObjectId,
    cfprApCimcvmediaMountConfigDefDn                                 CfprApManagedObjectDn,
    cfprApCimcvmediaMountConfigDefRn                                 SnmpAdminString,
    cfprApCimcvmediaMountConfigDefDescr                              SnmpAdminString,
    cfprApCimcvmediaMountConfigDefIntId                              SnmpAdminString,
    cfprApCimcvmediaMountConfigDefName                               SnmpAdminString,
    cfprApCimcvmediaMountConfigDefPolicyLevel                        Gauge32,
    cfprApCimcvmediaMountConfigDefPolicyOwner                        CfprApPolicyPolicyOwner,
    cfprApCimcvmediaMountConfigDefRetryOnMountFail                   CfprApCimcvmediaMountConfigRetryOnMountFail
}

cfprApCimcvmediaMountConfigDefInstanceId OBJECT-TYPE
    SYNTAX       CfprApManagedObjectId
    MAX-ACCESS   not-accessible
    STATUS       current
    DESCRIPTION
        "Instance identifier of the managed object."
    ::= { cfprApCimcvmediaMountConfigDefEntry 1 }

cfprApCimcvmediaMountConfigDefDn OBJECT-TYPE
    SYNTAX       CfprApManagedObjectDn
    MAX-ACCESS   read-only
    STATUS       current
    DESCRIPTION
        "Cisco Firepower cimcvmedia:MountConfigDef:dn managed
        object property"
    ::= { cfprApCimcvmediaMountConfigDefEntry 2 }

cfprApCimcvmediaMountConfigDefRn OBJECT-TYPE
    SYNTAX       SnmpAdminString
    MAX-ACCESS   read-only
    STATUS       current
    DESCRIPTION
        "Cisco Firepower cimcvmedia:MountConfigDef:rn managed
        object property"
    ::= { cfprApCimcvmediaMountConfigDefEntry 3 }

cfprApCimcvmediaMountConfigDefDescr OBJECT-TYPE
    SYNTAX       SnmpAdminString
    MAX-ACCESS   read-only
    STATUS       current
    DESCRIPTION
        "Cisco Firepower cimcvmedia:MountConfigDef:descr
        managed object property"
    ::= { cfprApCimcvmediaMountConfigDefEntry 4 }

cfprApCimcvmediaMountConfigDefIntId OBJECT-TYPE
    SYNTAX       SnmpAdminString
    MAX-ACCESS   read-only
    STATUS       current
    DESCRIPTION
        "Cisco Firepower cimcvmedia:MountConfigDef:intId
        managed object property"
    ::= { cfprApCimcvmediaMountConfigDefEntry 5 }

cfprApCimcvmediaMountConfigDefName OBJECT-TYPE
    SYNTAX       SnmpAdminString
    MAX-ACCESS   read-only
    STATUS       current
    DESCRIPTION
        "Cisco Firepower cimcvmedia:MountConfigDef:name
        managed object property"
    ::= { cfprApCimcvmediaMountConfigDefEntry 6 }

cfprApCimcvmediaMountConfigDefPolicyLevel OBJECT-TYPE
    SYNTAX       Gauge32
    MAX-ACCESS   read-only
    STATUS       current
    DESCRIPTION
        "Cisco Firepower cimcvmedia:MountConfigDef:policyLevel
        managed object property"
    ::= { cfprApCimcvmediaMountConfigDefEntry 7 }

cfprApCimcvmediaMountConfigDefPolicyOwner OBJECT-TYPE
    SYNTAX       CfprApPolicyPolicyOwner
    MAX-ACCESS   read-only
    STATUS       current
    DESCRIPTION
        "Cisco Firepower cimcvmedia:MountConfigDef:policyOwner
        managed object property"
    ::= { cfprApCimcvmediaMountConfigDefEntry 8 }

cfprApCimcvmediaMountConfigDefRetryOnMountFail OBJECT-TYPE
    SYNTAX       CfprApCimcvmediaMountConfigRetryOnMountFail
    MAX-ACCESS   read-only
    STATUS       current
    DESCRIPTION
        "Cisco Firepower cimcvmedia:MountConfigDef:retryOnMountFail
        managed object property"
    ::= { cfprApCimcvmediaMountConfigDefEntry 9 }

END
