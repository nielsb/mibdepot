-- *********************************************************************
-- CISCO-FIREPOWER-AP-MGMT-MIB.my
-- 
-- MIB representation of the Cisco Firepower
-- MGMT management information model package
-- 
-- Created July 2022 by Charles Bullis
-- 
-- Copyright (c) 2005-2022 Cisco Systems, Inc. All rights reserved.
-- 
-- *********************************************************************

CISCO-FIREPOWER-AP-MGMT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApCommClientAdminState,
    CfprApConditionRemoteInvRslt,
    CfprApEtherSatelliteConnectionDisc,
    CfprApFsmCompletion,
    CfprApFsmFlags,
    CfprApFsmFsmStageStatus,
    CfprApIpProtocol,
    CfprApMgmtAccess,
    CfprApMgmtAdminState,
    CfprApMgmtBackupFsmCurrentFsm,
    CfprApMgmtBackupFsmStageName,
    CfprApMgmtBackupFsmTaskItem,
    CfprApMgmtBackupInterval,
    CfprApMgmtBackupIssue,
    CfprApMgmtBackupJob,
    CfprApMgmtBackupPolicyFsmCurrentFsm,
    CfprApMgmtBackupPolicyFsmStageName,
    CfprApMgmtBackupPostAction,
    CfprApMgmtBackupProto,
    CfprApMgmtBackupStatus,
    CfprApMgmtBackupType,
    CfprApMgmtCfgExportPolicyFsmCurrentFsm,
    CfprApMgmtCfgExportPolicyFsmStageName,
    CfprApMgmtCimcSecureBootAdminState,
    CfprApMgmtConfigState,
    CfprApMgmtConnectionState,
    CfprApMgmtControllerFsmCurrentFsm,
    CfprApMgmtControllerFsmStageName,
    CfprApMgmtControllerFsmTaskFlags,
    CfprApMgmtControllerFsmTaskItem,
    CfprApMgmtDimmBlacklistingOperState,
    CfprApMgmtEntityChassisDeviceIoState1,
    CfprApMgmtEntityChassisDeviceIoState2,
    CfprApMgmtEntityChassisDeviceIoState3,
    CfprApMgmtEntityHaFailureReason,
    CfprApMgmtEntityHaReadiness,
    CfprApMgmtEntityLeadership,
    CfprApMgmtEntityMgmtServicesState,
    CfprApMgmtEntityProblems,
    CfprApMgmtEntityState,
    CfprApMgmtEntityUmbilicalState,
    CfprApMgmtExportPolicyAdminState,
    CfprApMgmtExportPolicyFsmCurrentFsm,
    CfprApMgmtExportPolicyFsmStageName,
    CfprApMgmtExportPolicyFsmTaskItem,
    CfprApMgmtExportPolicyProto,
    CfprApMgmtIPv6IfAddrFsmCurrentFsm,
    CfprApMgmtIPv6IfAddrFsmStageName,
    CfprApMgmtIPv6IfAddrFsmTaskItem,
    CfprApMgmtIfFsmCurrentFsm,
    CfprApMgmtIfFsmStageName,
    CfprApMgmtIfFsmTaskItem,
    CfprApMgmtImportAction,
    CfprApMgmtImportStatus,
    CfprApMgmtImporterFsmCurrentFsm,
    CfprApMgmtImporterFsmStageName,
    CfprApMgmtImporterFsmTaskItem,
    CfprApMgmtImporterPostAction,
    CfprApMgmtImporterProto,
    CfprApMgmtIntAuthPolicyMethod,
    CfprApMgmtMode,
    CfprApMgmtOperState,
    CfprApMgmtPmonEntryState,
    CfprApMgmtSecureBootOperState,
    CfprApMgmtSource,
    CfprApMgmtStateQual,
    CfprApMgmtStorageSubsystemState,
    CfprApMgmtSubject,
    CfprApNetworkConnectionType,
    CfprApNetworkLocale,
    CfprApNetworkPhysEpIfType,
    CfprApNetworkPortRole,
    CfprApNetworkSwitchId,
    CfprApNetworkTransport,
    CfprApPolicyPolicyOwner,
    CfprApTrigAdminState,
    CfprApTrigTrigOperState,
    CfprApVnicExternalMgmtIPMode
        FROM CISCO-FIREPOWER-AP-TC-MIB;

cfprApMgmtObjects MODULE-IDENTITY
    LAST-UPDATED    "202207270000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        MGMT management information model package"
    ::= { ciscoFirepowerApMIBObjects 51 }

cfprApMgmtAccessPolicyTable OBJECT-TYPE
    SYNTAX           SEQUENCE OF CfprApMgmtAccessPolicyEntry
    MAX-ACCESS       not-accessible
    STATUS           current
    DESCRIPTION
        "Cisco Firepower mgmt:AccessPolicy managed object table"
    ::= { cfprApMgmtObjects 1 }

cfprApMgmtAccessPolicyEntry OBJECT-TYPE
    SYNTAX           CfprApMgmtAccessPolicyEntry
    MAX-ACCESS       not-accessible
    STATUS           current
    DESCRIPTION
        "Entry for the cfprApMgmtAccessPolicyTable table."
    INDEX { cfprApMgmtAccessPolicyInstanceId }
    ::= { cfprApMgmtAccessPolicyTable 1 }

CfprApMgmtAccessPolicyEntry ::= SEQUENCE {
    cfprApMgmtAccessPolicyInstanceId                                 CfprApManagedObjectId,
    cfprApMgmtAccessPolicyDn                                         CfprApManagedObjectDn,
    cfprApMgmtAccessPolicyRn                                         SnmpAdminString
}

cfprApMgmtAccessPolicyInstanceId OBJECT-TYPE
    SYNTAX       CfprApManagedObjectId
    MAX-ACCESS   not-accessible
    STATUS       current
    DESCRIPTION
        "Instance identifier of the managed object."
    ::= { cfprApMgmtAccessPolicyEntry 1 }

cfprApMgmtAccessPolicyDn OBJECT-TYPE
    SYNTAX       CfprApManagedObjectDn
    MAX-ACCESS   read-only
    STATUS       current
    DESCRIPTION
        "Cisco Firepower mgmt:AccessPolicy:dn managed object property"
    ::= { cfprApMgmtAccessPolicyEntry 2 }

cfprApMgmtAccessPolicyRn OBJECT-TYPE
    SYNTAX       SnmpAdminString
    MAX-ACCESS   read-only
    STATUS       current
    DESCRIPTION
        "Cisco Firepower mgmt:AccessPolicy:rn managed object property"
    ::= { cfprApMgmtAccessPolicyEntry 3 }

cfprApMgmtAccessPolicyItemTable OBJECT-TYPE
    SYNTAX           SEQUENCE OF CfprApMgmtAccessPolicyItemEntry
    MAX-ACCESS       not-accessible
    STATUS           current
    DESCRIPTION
        "Cisco Firepower mgmt:AccessPolicyItem managed object table"
    ::= { cfprApMgmtObjects 2 }

cfprApMgmtAccessPolicyItemEntry OBJECT-TYPE
    SYNTAX           CfprApMgmtAccessPolicyItemEntry
    MAX-ACCESS       not-accessible
    STATUS           current
    DESCRIPTION
        "Entry for the cfprApMgmtAccessPolicyItemTable table."
    INDEX { cfprApMgmtAccessPolicyItemInstanceId }
    ::= { cfprApMgmtAccessPolicyItemTable 1 }

CfprApMgmtAccessPolicyItemEntry ::= SEQUENCE {
    cfprApMgmtAccessPolicyItemInstanceId                             CfprApManagedObjectId,
    cfprApMgmtAccessPolicyItemDn                                     CfprApManagedObjectDn,
    cfprApMgmtAccessPolicyItemRn                                     SnmpAdminString,
    cfprApMgmtAccessPolicyItemDescr                                  SnmpAdminString,
    cfprApMgmtAccessPolicyItemIntId                                  SnmpAdminString,
    cfprApMgmtAccessPolicyItemIpPoolName                             SnmpAdminString,
    cfprApMgmtAccessPolicyItemName                                   SnmpAdminString,
    cfprApMgmtAccessPolicyItemPolicyLevel                            Gauge32,
    cfprApMgmtAccessPolicyItemPolicyOwner                            CfprApPolicyPolicyOwner,
    cfprApMgmtAccessPolicyItemSubject                                CfprApMgmtSubject
}

cfprApMgmtAccessPolicyItemInstanceId OBJECT-TYPE
    SYNTAX       CfprApManagedObjectId
    MAX-ACCESS   not-accessible
    STATUS       current
    DESCRIPTION
        "Instance identifier of the managed object."
    ::= { cfprApMgmtAccessPolicyItemEntry 1 }

cfprApMgmtAccessPolicyItemDn OBJECT-TYPE
    SYNTAX       CfprApManagedObjectDn
    MAX-ACCESS   read-only
    STATUS       current
    DESCRIPTION
        "Cisco Firepower mgmt:AccessPolicyItem:dn managed object property"
    ::= { cfprApMgmtAccessPolicyItemEntry 2 }

cfprApMgmtAccessPolicyItemRn OBJECT-TYPE
    SYNTAX       SnmpAdminString
    MAX-ACCESS   read-only
    STATUS       current
    DESCRIPTION
        "Cisco Firepower mgmt:AccessPolicyItem:rn managed object property"
    ::= { cfprApMgmtAccessPolicyItemEntry 3 }

cfprApMgmtAccessPolicyItemDescr OBJECT-TYPE
    SYNTAX       SnmpAdminString
    MAX-ACCESS   read-only
    STATUS       current
    DESCRIPTION
        "Cisco Firepower mgmt:AccessPolicyItem:descr managed
        object property"
    ::= { cfprApMgmtAccessPolicyItemEntry 4 }

cfprApMgmtAccessPolicyItemIntId OBJECT-TYPE
    SYNTAX       SnmpAdminString
    MAX-ACCESS   read-only
    STATUS       current
    DESCRIPTION
        "Cisco Firepower mgmt:AccessPolicyItem:intId managed
        object property"
    ::= { cfprApMgmtAccessPolicyItemEntry 5 }

cfprApMgmtAccessPolicyItemIpPoolName OBJECT-TYPE
    SYNTAX       SnmpAdminString
    MAX-ACCESS   read-only
    STATUS       current
    DESCRIPTION
        "Cisco Firepower mgmt:AccessPolicyItem:ipPoolName
        managed object property"
    ::= { cfprApMgmtAccessPolicyItemEntry 6 }

cfprApMgmtAccessPolicyItemName OBJECT-TYPE
    SYNTAX       SnmpAdminString
    MAX-ACCESS   read-only
    STATUS       current
    DESCRIPTION
        "Cisco Firepower mgmt:AccessPolicyItem:name managed
        object property"
    ::= { cfprApMgmtAccessPolicyItemEntry 7 }

cfprApMgmtAccessPolicyItemPolicyLevel OBJECT-TYPE
    SYNTAX       Gauge32
    MAX-ACCESS   read-only
    STATUS       current
    DESCRIPTION
        "Cisco Firepower mgmt:AccessPolicyItem:policyLevel
        managed object property"
    ::= { cfprApMgmtAccessPolicyItemEntry 8 }

cfprApMgmtAccessPolicyItemPolicyOwner OBJECT-TYPE
    SYNTAX       CfprApPolicyPolicyOwner
    MAX-ACCESS   read-only
    STATUS       current
    DESCRIPTION
        "Cisco Firepower mgmt:AccessPolicyItem:policyOwner
        managed object property"
    ::= { cfprApMgmtAccessPolicyItemEntry 9 }

cfprApMgmtAccessPolicyItemSubject OBJECT-TYPE
    SYNTAX       CfprApMgmtSubject
    MAX-ACCESS   read-only
    STATUS       current
    DESCRIPTION
        "Cisco Firepower mgmt:AccessPolicyItem:subject
        managed object property"
    ::= { cfprApMgmtAccessPolicyItemEntry 10 }

cfprApMgmtAccessPortTable OBJECT-TYPE
    SYNTAX           SEQUENCE OF CfprApMgmtAccessPortEntry
    MAX-ACCESS       not-accessible
    STATUS           current
    DESCRIPTION
        "Cisco Firepower mgmt:AccessPort managed object table"
    ::= { cfprApMgmtObjects 3 }

cfprApMgmtAccessPortEntry OBJECT-TYPE
    SYNTAX           CfprApMgmtAccessPortEntry
    MAX-ACCESS       not-accessible
    STATUS           current
    DESCRIPTION
        "Entry for the cfprApMgmtAccessPortTable table."
    INDEX { cfprApMgmtAccessPortInstanceId }
    ::= { cfprApMgmtAccessPortTable 1 }

CfprApMgmtAccessPortEntry ::= SEQUENCE {
    cfprApMgmtAccessPortInstanceId                                   CfprApManagedObjectId,
    cfprApMgmtAccessPortDn                                           CfprApManagedObjectDn,
    cfprApMgmtAccessPortRn                                           SnmpAdminString,
    cfprApMgmtAccessPortPort                                         Gauge32,
    cfprApMgmtAccessPortProtocol                                     CfprApIpProtocol
}

cfprApMgmtAccessPortInstanceId OBJECT-TYPE
    SYNTAX       CfprApManagedObjectId
    MAX-ACCESS   not-accessible
    STATUS       current
    DESCRIPTION
        "Instance identifier of the managed object."
    ::= { cfprApMgmtAccessPortEntry 1 }

cfprApMgmtAccessPortDn OBJECT-TYPE
    SYNTAX       CfprApManagedObjectDn
    MAX-ACCESS   read-only
    STATUS       current
    DESCRIPTION
        "Cisco Firepower mgmt:AccessPort:dn managed object property"
    ::= { cfprApMgmtAccessPortEntry 2 }

cfprApMgmtAccessPortRn OBJECT-TYPE
    SYNTAX       SnmpAdminString
    MAX-ACCESS   read-only
    STATUS       current
    DESCRIPTION
        "Cisco Firepower mgmt:AccessPort:rn managed object property"
    ::= { cfprApMgmtAccessPortEntry 3 }

cfprApMgmtAccessPortPort OBJECT-TYPE
    SYNTAX       Gauge32
    MAX-ACCESS   read-only
    STATUS       current
    DESCRIPTION
        "Cisco Firepower mgmt:AccessPort:port managed object property"
    ::= { cfprApMgmtAccessPortEntry 4 }

cfprApMgmtAccessPortProtocol OBJECT-TYPE
    SYNTAX       CfprApIpProtocol
    MAX-ACCESS   read-only
    STATUS       current
    DESCRIPTION
        "Cisco Firepower mgmt:AccessPort:protocol managed object property"
    ::= { cfprApMgmtAccessPortEntry 5 }

cfprApMgmtBackupTable OBJECT-TYPE
    SYNTAX           SEQUENCE OF CfprApMgmtBackupEntry
    MAX-ACCESS       not-accessible
    STATUS           current
    DESCRIPTION
        "Cisco Firepower mgmt:Backup managed object table"
    ::= { cfprApMgmtObjects 4 }

cfprApMgmtBackupEntry OBJECT-TYPE
    SYNTAX           CfprApMgmtBackupEntry
    MAX-ACCESS       not-accessible
    STATUS           current
    DESCRIPTION
        "Entry for the cfprApMgmtBackupTable table."
    INDEX { cfprApMgmtBackupInstanceId }
    ::= { cfprApMgmtBackupTable 1 }

CfprApMgmtBackupEntry ::= SEQUENCE {
    cfprApMgmtBackupInstanceId                                       CfprApManagedObjectId,
    cfprApMgmtBackupDn                                               CfprApManagedObjectDn,
    cfprApMgmtBackupRn                                               SnmpAdminString,
    cfprApMgmtBackupAdminState                                       CfprApCommClientAdminState,
    cfprApMgmtBackupDescr                                            SnmpAdminString,
    cfprApMgmtBackupFsmDescr                                         SnmpAdminString,
    cfprApMgmtBackupFsmPrev                                          SnmpAdminString,
    cfprApMgmtBackupFsmProgr                                         Gauge32,
    cfprApMgmtBackupFsmRmtInvErrCode                                 Gauge32,
    cfprApMgmtBackupFsmRmtInvErrDescr                                SnmpAdminString,
    cfprApMgmtBackupFsmRmtInvRslt                                    CfprApConditionRemoteInvRslt,
    cfprApMgmtBackupFsmStageDescr                                    SnmpAdminString,
    cfprApMgmtBackupFsmStamp                                         DateAndTime,
    cfprApMgmtBackupFsmStatus                                        SnmpAdminString,
    cfprApMgmtBackupFsmTry                                           Gauge32,
    cfprApMgmtBackupHostname                                         SnmpAdminString,
    cfprApMgmtBackupIntId                                            SnmpAdminString,
    cfprApMgmtBackupJob                                              CfprApMgmtBackupJob,
    cfprApMgmtBackupMaxFiles                                         Gauge32,
    cfprApMgmtBackupName                                             SnmpAdminString,
    cfprApMgmtBackupOperStatus                                       CfprApMgmtBackupStatus,
    cfprApMgmtBackupOwnerPolicy                                      SnmpAdminString,
    cfprApMgmtBackupPolicyLevel                                      Gauge32,
    cfprApMgmtBackupPolicyOwner                                      CfprApPolicyPolicyOwner,
    cfprApMgmtBackupPort                                             Gauge32,
    cfprApMgmtBackupPostAction                                       CfprApMgmtBackupPostAction,
    cfprApMgmtBackupPreservePooledValues                             TruthValue,
    cfprApMgmtBackupProto                                            CfprApMgmtBackupProto,
    cfprApMgmtBackupPwd                                              SnmpAdminString,
    cfprApMgmtBackupRemoteFile                                       SnmpAdminString,
    cfprApMgmtBackupType                                             CfprApMgmtBackupType,
    cfprApMgmtBackupUser                                             SnmpAdminString
}

cfprApMgmtBackupInstanceId OBJECT-TYPE
    SYNTAX       CfprApManagedObjectId
    MAX-ACCESS   not-accessible
    STATUS       current
    DESCRIPTION
        "Instance identifier of the managed object."
    ::= { cfprApMgmtBackupEntry 1 }

cfprApMgmtBackupDn OBJECT-TYPE
    SYNTAX       CfprApManagedObjectDn
    MAX-ACCESS   read-only
    STATUS       current
    DESCRIPTION
        "Cisco Firepower mgmt:Backup:dn managed object property"
    ::= { cfprApMgmtBackupEntry 2 }

cfprApMgmtBackupRn OBJECT-TYPE
    SYNTAX       SnmpAdminString
    MAX-ACCESS   read-only
    STATUS       current
    DESCRIPTION
        "Cisco Firepower mgmt:Backup:rn managed object property"
    ::= { cfprApMgmtBackupEntry 3 }

cfprApMgmtBackupAdminState OBJECT-TYPE
    SYNTAX       CfprApCommClientAdminState
    MAX-ACCESS   read-only
    STATUS       current
    DESCRIPTION
        "Cisco Firepower mgmt:Backup:adminState managed object property"
    ::= { cfprApMgmtBackupEntry 4 }

cfprApMgmtBackupDescr OBJECT-TYPE
    SYNTAX       SnmpAdminString
    MAX-ACCESS   read-only
    STATUS       current
    DESCRIPTION
        "Cisco Firepower mgmt:Backup:descr managed object property"
    ::= { cfprApMgmtBackupEntry 5 }

cfprApMgmtBackupFsmDescr OBJECT-TYPE
    SYNTAX       SnmpAdminString
    MAX-ACCESS   read-only
    STATUS       current
    DESCRIPTION
        "Cisco Firepower mgmt:Backup:fsmDescr managed object property"
    ::= { cfprApMgmtBackupEntry 6 }

cfprApMgmtBackupFsmPrev OBJECT-TYPE
    SYNTAX       SnmpAdminString
    MAX-ACCESS   read-only
    STATUS       current
    DESCRIPTION
        "Cisco Firepower mgmt:Backup:fsmPrev managed object property"
    ::= { cfprApMgmtBackupEntry 7 }

cfprApMgmtBackupFsmProgr OBJECT-TYPE
    SYNTAX       Gauge32
    MAX-ACCESS   read-only
    STATUS       current
    DESCRIPTION
        "Cisco Firepower mgmt:Backup:fsmProgr managed object property"
    ::= { cfprApMgmtBackupEntry 8 }

cfprApMgmtBackupFsmRmtInvErrCode OBJECT-TYPE
    SYNTAX       Gauge32
    MAX-ACCESS   read-only
    STATUS       current
    DESCRIPTION
        "Cisco Firepower mgmt:Backup:fsmRmtInvErrCode managed
        object property"
    ::= { cfprApMgmtBackupEntry 9 }

cfprApMgmtBackupFsmRmtInvErrDescr OBJECT-TYPE
    SYNTAX       SnmpAdminString
    MAX-ACCESS   read-only
    STATUS       current
    DESCRIPTION
        "Cisco Firepower mgmt:Backup:fsmRmtInvErrDescr
        managed object property"
    ::= { cfprApMgmtBackupEntry 10 }

cfprApMgmtBackupFsmRmtInvRslt OBJECT-TYPE
    SYNTAX       CfprApConditionRemoteInvRslt
    MAX-ACCESS   read-only
    STATUS       current
    DESCRIPTION
        "Cisco Firepower mgmt:Backup:fsmRmtInvRslt managed
        object property"
    ::= { cfprApMgmtBackupEntry 11 }

cfprApMgmtBackupFsmStageDescr OBJECT-TYPE
    SYNTAX       SnmpAdminString
    MAX-ACCESS   read-only
    STATUS       current
    DESCRIPTION
        "Cisco Firepower mgmt:Backup:fsmStageDescr managed
        object property"
    ::= { cfprApMgmtBackupEntry 12 }

cfprApMgmtBackupFsmStamp OBJECT-TYPE
    SYNTAX       DateAndTime
    MAX-ACCESS   read-only
    STATUS       current
    DESCRIPTION
        "Cisco Firepower mgmt:Backup:fsmStamp managed object property"
    ::= { cfprApMgmtBackupEntry 13 }

cfprApMgmtBackupFsmStatus OBJECT-TYPE
    SYNTAX       SnmpAdminString
    MAX-ACCESS   read-only
    STATUS       current
    DESCRIPTION
        "Cisco Firepower mgmt:Backup:fsmStatus managed object property"
    ::= { cfprApMgmtBackupEntry 14 }

cfprApMgmtBackupFsmTry OBJECT-TYPE
    SYNTAX       Gauge32
    MAX-ACCESS   read-only
    STATUS       current
    DESCRIPTION
        "Cisco Firepower mgmt:Backup:fsmTry managed object property"
    ::= { cfprApMgmtBackupEntry 15 }

cfprApMgmtBackupHostname OBJECT-TYPE
    SYNTAX       SnmpAdminString
    MAX-ACCESS   read-only
    STATUS       current
    DESCRIPTION
        "Cisco Firepower mgmt:Backup:hostname managed object property"
    ::= { cfprApMgmtBackupEntry 16 }

cfprApMgmtBackupIntId OBJECT-TYPE
    SYNTAX       SnmpAdminString
    MAX-ACCESS   read-only
    STATUS       current
    DESCRIPTION
        "Cisco Firepower mgmt:Backup:intId managed object property"
    ::= { cfprApMgmtBackupEntry 17 }

cfprApMgmtBackupJob OBJECT-TYPE
    SYNTAX       CfprApMgmtBackupJob
    MAX-ACCESS   read-only
    STATUS       current
    DESCRIPTION
        "Cisco Firepower mgmt:Backup:job managed object property"
    ::= { cfprApMgmtBackupEntry 18 }

cfprApMgmtBackupMaxFiles OBJECT-TYPE
    SYNTAX       Gauge32
    MAX-ACCESS   read-only
    STATUS       current
    DESCRIPTION
        "Cisco Firepower mgmt:Backup:maxFiles managed object property"
    ::= { cfprApMgmtBackupEntry 19 }

cfprApMgmtBackupName OBJECT-TYPE
    SYNTAX       SnmpAdminString
    MAX-ACCESS   read-only
    STATUS       current
    DESCRIPTION
        "Cisco Firepower mgmt:Backup:name managed object property"
    ::= { cfprApMgmtBackupEntry 20 }

cfprApMgmtBackupOperStatus OBJECT-TYPE
    SYNTAX       CfprApMgmtBackupStatus
    MAX-ACCESS   read-only
    STATUS       current
    DESCRIPTION
        "Cisco Firepower mgmt:Backup:operStatus managed object property"
    ::= { cfprApMgmtBackupEntry 21 }

cfprApMgmtBackupOwnerPolicy OBJECT-TYPE
    SYNTAX       SnmpAdminString
    MAX-ACCESS   read-only
    STATUS       current
    DESCRIPTION
        "Cisco Firepower mgmt:Backup:ownerPolicy managed object property"
    ::= { cfprApMgmtBackupEntry 22 }

cfprApMgmtBackupPolicyLevel OBJECT-TYPE
    SYNTAX       Gauge32
    MAX-ACCESS   read-only
    STATUS       current
    DESCRIPTION
        "Cisco Firepower mgmt:Backup:policyLevel managed object property"
    ::= { cfprApMgmtBackupEntry 23 }

cfprApMgmtBackupPolicyOwner OBJECT-TYPE
    SYNTAX       CfprApPolicyPolicyOwner
    MAX-ACCESS   read-only
    STATUS       current
    DESCRIPTION
        "Cisco Firepower mgmt:Backup:policyOwner managed object property"
    ::= { cfprApMgmtBackupEntry 24 }

cfprApMgmtBackupPort OBJECT-TYPE
    SYNTAX       Gauge32
    MAX-ACCESS   read-only
    STATUS       current
    DESCRIPTION
        "Cisco Firepower mgmt:Backup:port managed object property"
    ::= { cfprApMgmtBackupEntry 25 }

cfprApMgmtBackupPostAction OBJECT-TYPE
    SYNTAX       CfprApMgmtBackupPostAction
    MAX-ACCESS   read-only
    STATUS       current
    DESCRIPTION
        "Cisco Firepower mgmt:Backup:postAction managed object property"
    ::= { cfprApMgmtBackupEntry 26 }

cfprApMgmtBackupPreservePooledValues OBJECT-TYPE
    SYNTAX       TruthValue
    MAX-ACCESS   read-only
    STATUS       current
    DESCRIPTION
        "Cisco Firepower mgmt:Backup:preservePooledValues
        managed object property"
    ::= { cfprApMgmtBackupEntry 27 }

cfprApMgmtBackupProto OBJECT-TYPE
    SYNTAX       CfprApMgmtBackupProto
    MAX-ACCESS   read-only
    STATUS       current
    DESCRIPTION
        "Cisco Firepower mgmt:Backup:proto managed object property"
    ::= { cfprApMgmtBackupEntry 28 }

cfprApMgmtBackupPwd OBJECT-TYPE
    SYNTAX       SnmpAdminString
    MAX-ACCESS   read-only
    STATUS       current
    DESCRIPTION
        "Cisco Firepower mgmt:Backup:pwd managed object property"
    ::= { cfprApMgmtBackupEntry 29 }

cfprApMgmtBackupRemoteFile OBJECT-TYPE
    SYNTAX       SnmpAdminString
    MAX-ACCESS   read-only
    STATUS       current
    DESCRIPTION
        "Cisco Firepower mgmt:Backup:remoteFile managed object property"
    ::= { cfprApMgmtBackupEntry 30 }

cfprApMgmtBackupType OBJECT-TYPE
    SYNTAX       CfprApMgmtBackupType
    MAX-ACCESS   read-only
    STATUS       current
    DESCRIPTION
        "Cisco Firepower mgmt:Backup:type managed object property"
    ::= { cfprApMgmtBackupEntry 31 }

cfprApMgmtBackupUser OBJECT-TYPE
    SYNTAX       SnmpAdminString
    MAX-ACCESS   read-only
    STATUS       current
    DESCRIPTION
        "Cisco Firepower mgmt:Backup:user managed object property"
    ::= { cfprApMgmtBackupEntry 32 }

cfprApMgmtBackupExportExtPolicyTable OBJECT-TYPE
    SYNTAX           SEQUENCE OF CfprApMgmtBackupExportExtPolicyEntry
    MAX-ACCESS       not-accessible
    STATUS           current
    DESCRIPTION
        "Cisco Firepower mgmt:BackupExportExtPolicy managed object table"
    ::= { cfprApMgmtObjects 5 }

cfprApMgmtBackupExportExtPolicyEntry OBJECT-TYPE
    SYNTAX           CfprApMgmtBackupExportExtPolicyEntry
    MAX-ACCESS       not-accessible
    STATUS           current
    DESCRIPTION
        "Entry for the cfprApMgmtBackupExportExtPolicyTable table."
    INDEX { cfprApMgmtBackupExportExtPolicyInstanceId }
    ::= { cfprApMgmtBackupExportExtPolicyTable 1 }

CfprApMgmtBackupExportExtPolicyEntry ::= SEQUENCE {
    cfprApMgmtBackupExportExtPolicyInstanceId                        CfprApManagedObjectId,
    cfprApMgmtBackupExportExtPolicyDn                                CfprApManagedObjectDn,
    cfprApMgmtBackupExportExtPolicyRn                                SnmpAdminString,
    cfprApMgmtBackupExportExtPolicyAdminState                        CfprApMgmtAdminState,
    cfprApMgmtBackupExportExtPolicyDescr                             SnmpAdminString,
    cfprApMgmtBackupExportExtPolicyFrequency                         Gauge32,
    cfprApMgmtBackupExportExtPolicyIntId                             SnmpAdminString,
    cfprApMgmtBackupExportExtPolicyName                              SnmpAdminString,
    cfprApMgmtBackupExportExtPolicyPolicyLevel                       Gauge32,
    cfprApMgmtBackupExportExtPolicyPolicyOwner                       CfprApPolicyPolicyOwner
}

cfprApMgmtBackupExportExtPolicyInstanceId OBJECT-TYPE
    SYNTAX       CfprApManagedObjectId
    MAX-ACCESS   not-accessible
    STATUS       current
    DESCRIPTION
        "Instance identifier of the managed object."
    ::= { cfprApMgmtBackupExportExtPolicyEntry 1 }

cfprApMgmtBackupExportExtPolicyDn OBJECT-TYPE
    SYNTAX       CfprApManagedObjectDn
    MAX-ACCESS   read-only
    STATUS       current
    DESCRIPTION
        "Cisco Firepower mgmt:BackupExportExtPolicy:dn
        managed object property"
    ::= { cfprApMgmtBackupExportExtPolicyEntry 2 }

cfprApMgmtBackupExportExtPolicyRn OBJECT-TYPE
    SYNTAX       SnmpAdminString
    MAX-ACCESS   read-only
    STATUS       current
    DESCRIPTION
        "Cisco Firepower mgmt:BackupExportExtPolicy:rn
        managed object property"
    ::= { cfprApMgmtBackupExportExtPolicyEntry 3 }

cfprApMgmtBackupExportExtPolicyAdminState OBJECT-TYPE
    SYNTAX       CfprApMgmtAdminState
    MAX-ACCESS   read-only
    STATUS       current
    DESCRIPTION
        "Cisco Firepower mgmt:BackupExportExtPolicy:adminState
        managed object property"
    ::= { cfprApMgmtBackupExportExtPolicyEntry 4 }

cfprApMgmtBackupExportExtPolicyDescr OBJECT-TYPE
    SYNTAX       SnmpAdminString
    MAX-ACCESS   read-only
    STATUS       current
    DESCRIPTION
        "Cisco Firepower mgmt:BackupExportExtPolicy:descr
        managed object property"
    ::= { cfprApMgmtBackupExportExtPolicyEntry 5 }

cfprApMgmtBackupExportExtPolicyFrequency OBJECT-TYPE
    SYNTAX       Gauge32
    MAX-ACCESS   read-only
    STATUS       current
    DESCRIPTION
        "Cisco Firepower mgmt:BackupExportExtPolicy:frequency
        managed object property"
    ::= { cfprApMgmtBackupExportExtPolicyEntry 6 }

cfprApMgmtBackupExportExtPolicyIntId OBJECT-TYPE
    SYNTAX       SnmpAdminString
    MAX-ACCESS   read-only
    STATUS       current
    DESCRIPTION
        "Cisco Firepower mgmt:BackupExportExtPolicy:intId
        managed object property"
    ::= { cfprApMgmtBackupExportExtPolicyEntry 7 }

cfprApMgmtBackupExportExtPolicyName OBJECT-TYPE
    SYNTAX       SnmpAdminString
    MAX-ACCESS   read-only
    STATUS       current
    DESCRIPTION
        "Cisco Firepower mgmt:BackupExportExtPolicy:name
        managed object property"
    ::= { cfprApMgmtBackupExportExtPolicyEntry 8 }

cfprApMgmtBackupExportExtPolicyPolicyLevel OBJECT-TYPE
    SYNTAX       Gauge32
    MAX-ACCESS   read-only
    STATUS       current
    DESCRIPTION
        "Cisco Firepower mgmt:BackupExportExtPolicy:policyLevel
        managed object property"
    ::= { cfprApMgmtBackupExportExtPolicyEntry 9 }

cfprApMgmtBackupExportExtPolicyPolicyOwner OBJECT-TYPE
    SYNTAX       CfprApPolicyPolicyOwner
    MAX-ACCESS   read-only
    STATUS       current
    DESCRIPTION
        "Cisco Firepower mgmt:BackupExportExtPolicy:policyOwner
        managed object property"
    ::= { cfprApMgmtBackupExportExtPolicyEntry 10 }

cfprApMgmtBackupFsmTable OBJECT-TYPE
    SYNTAX           SEQUENCE OF CfprApMgmtBackupFsmEntry
    MAX-ACCESS       not-accessible
    STATUS           current
    DESCRIPTION
        "Cisco Firepower mgmt:BackupFsm managed object table"
    ::= { cfprApMgmtObjects 6 }

cfprApMgmtBackupFsmEntry OBJECT-TYPE
    SYNTAX           CfprApMgmtBackupFsmEntry
    MAX-ACCESS       not-accessible
    STATUS           current
    DESCRIPTION
        "Entry for the cfprApMgmtBackupFsmTable table."
    INDEX { cfprApMgmtBackupFsmInstanceId }
    ::= { cfprApMgmtBackupFsmTable 1 }

CfprApMgmtBackupFsmEntry ::= SEQUENCE {
    cfprApMgmtBackupFsmInstanceId                                    CfprApManagedObjectId,
    cfprApMgmtBackupFsmDn                                            CfprApManagedObjectDn,
    cfprApMgmtBackupFsmRn                                            SnmpAdminString,
    cfprApMgmtBackupFsmCompletionTime                                DateAndTime,
    cfprApMgmtBackupFsmCurrentFsm                                    CfprApMgmtBackupFsmCurrentFsm,
    cfprApMgmtBackupFsmDescrData                                     SnmpAdminString,
    cfprApMgmtBackupFsmFsmStatus                                     CfprApFsmFsmStageStatus,
    cfprApMgmtBackupFsmProgress                                      Gauge32,
    cfprApMgmtBackupFsmRmtErrCode                                    Gauge32,
    cfprApMgmtBackupFsmRmtErrDescr                                   SnmpAdminString,
    cfprApMgmtBackupFsmRmtRslt                                       CfprApConditionRemoteInvRslt
}

cfprApMgmtBackupFsmInstanceId OBJECT-TYPE
    SYNTAX       CfprApManagedObjectId
    MAX-ACCESS   not-accessible
    STATUS       current
    DESCRIPTION
        "Instance identifier of the managed object."
    ::= { cfprApMgmtBackupFsmEntry 1 }

cfprApMgmtBackupFsmDn OBJECT-TYPE
    SYNTAX       CfprApManagedObjectDn
    MAX-ACCESS   read-only
    STATUS       current
    DESCRIPTION
        "Cisco Firepower mgmt:BackupFsm:dn managed object property"
    ::= { cfprApMgmtBackupFsmEntry 2 }

cfprApMgmtBackupFsmRn OBJECT-TYPE
    SYNTAX       SnmpAdminString
    MAX-ACCESS   read-only
    STATUS       current
    DESCRIPTION
        "Cisco Firepower mgmt:BackupFsm:rn managed object property"
    ::= { cfprApMgmtBackupFsmEntry 3 }

cfprApMgmtBackupFsmCompletionTime OBJECT-TYPE
    SYNTAX       DateAndTime
    MAX-ACCESS   read-only
    STATUS       current
    DESCRIPTION
        "Cisco Firepower mgmt:BackupFsm:completionTime
        managed object property"
    ::= { cfprApMgmtBackupFsmEntry 4 }

cfprApMgmtBackupFsmCurrentFsm OBJECT-TYPE
    SYNTAX       CfprApMgmtBackupFsmCurrentFsm
    MAX-ACCESS   read-only
    STATUS       current
    DESCRIPTION
        "Cisco Firepower mgmt:BackupFsm:currentFsm managed
        object property"
    ::= { cfprApMgmtBackupFsmEntry 5 }

cfprApMgmtBackupFsmDescrData OBJECT-TYPE
    SYNTAX       SnmpAdminString
    MAX-ACCESS   read-only
    STATUS       current
    DESCRIPTION
        "Cisco Firepower mgmt:BackupFsm:descr managed object property"
    ::= { cfprApMgmtBackupFsmEntry 6 }

cfprApMgmtBackupFsmFsmStatus OBJECT-TYPE
    SYNTAX       CfprApFsmFsmStageStatus
    MAX-ACCESS   read-only
    STATUS       current
    DESCRIPTION
        "Cisco Firepower mgmt:BackupFsm:fsmStatus managed object property"
    ::= { cfprApMgmtBackupFsmEntry 7 }

cfprApMgmtBackupFsmProgress OBJECT-TYPE
    SYNTAX       Gauge32
    MAX-ACCESS   read-only
    STATUS       current
    DESCRIPTION
        "Cisco Firepower mgmt:BackupFsm:progress managed object property"
    ::= { cfprApMgmtBackupFsmEntry 8 }

cfprApMgmtBackupFsmRmtErrCode OBJECT-TYPE
    SYNTAX       Gauge32
    MAX-ACCESS   read-only
    STATUS       current
    DESCRIPTION
        "Cisco Firepower mgmt:BackupFsm:rmtErrCode managed
        object property"
    ::= { cfprApMgmtBackupFsmEntry 9 }

cfprApMgmtBackupFsmRmtErrDescr OBJECT-TYPE
    SYNTAX       SnmpAdminString
    MAX-ACCESS   read-only
    STATUS       current
    DESCRIPTION
        "Cisco Firepower mgmt:BackupFsm:rmtErrDescr managed
        object property"
    ::= { cfprApMgmtBackupFsmEntry 10 }

cfprApMgmtBackupFsmRmtRslt OBJECT-TYPE
    SYNTAX       CfprApConditionRemoteInvRslt
    MAX-ACCESS   read-only
    STATUS       current
    DESCRIPTION
        "Cisco Firepower mgmt:BackupFsm:rmtRslt managed object property"
    ::= { cfprApMgmtBackupFsmEntry 11 }

cfprApMgmtBackupFsmStageTable OBJECT-TYPE
    SYNTAX           SEQUENCE OF CfprApMgmtBackupFsmStageEntry
    MAX-ACCESS       not-accessible
    STATUS           current
    DESCRIPTION
        "Cisco Firepower mgmt:BackupFsmStage managed object table"
    ::= { cfprApMgmtObjects 7 }

cfprApMgmtBackupFsmStageEntry OBJECT-TYPE
    SYNTAX           CfprApMgmtBackupFsmStageEntry
    MAX-ACCESS       not-accessible
    STATUS           current
    DESCRIPTION
        "Entry for the cfprApMgmtBackupFsmStageTable table."
    INDEX { cfprApMgmtBackupFsmStageInstanceId }
    ::= { cfprApMgmtBackupFsmStageTable 1 }

CfprApMgmtBackupFsmStageEntry ::= SEQUENCE {
    cfprApMgmtBackupFsmStageInstanceId                               CfprApManagedObjectId,
    cfprApMgmtBackupFsmStageDn                                       CfprApManagedObjectDn,
    cfprApMgmtBackupFsmStageRn                                       SnmpAdminString,
    cfprApMgmtBackupFsmStageDescrData                                SnmpAdminString,
    cfprApMgmtBackupFsmStageLastUpdateTime                           DateAndTime,
    cfprApMgmtBackupFsmStageName                                     CfprApMgmtBackupFsmStageName,
    cfprApMgmtBackupFsmStageOrder                                    Gauge32,
    cfprApMgmtBackupFsmStageRetry                                    Gauge32,
    cfprApMgmtBackupFsmStageStageStatus                              CfprApFsmFsmStageStatus
}

cfprApMgmtBackupFsmStageInstanceId OBJECT-TYPE
    SYNTAX       CfprApManagedObjectId
    MAX-ACCESS   not-accessible
    STATUS       current
    DESCRIPTION
        "Instance identifier of the managed object."
    ::= { cfprApMgmtBackupFsmStageEntry 1 }

cfprApMgmtBackupFsmStageDn OBJECT-TYPE
    SYNTAX       CfprApManagedObjectDn
    MAX-ACCESS   read-only
    STATUS       current
    DESCRIPTION
        "Cisco Firepower mgmt:BackupFsmStage:dn managed object property"
    ::= { cfprApMgmtBackupFsmStageEntry 2 }

cfprApMgmtBackupFsmStageRn OBJECT-TYPE
    SYNTAX       SnmpAdminString
    MAX-ACCESS   read-only
    STATUS       current
    DESCRIPTION
        "Cisco Firepower mgmt:BackupFsmStage:rn managed object property"
    ::= { cfprApMgmtBackupFsmStageEntry 3 }

cfprApMgmtBackupFsmStageDescrData OBJECT-TYPE
    SYNTAX       SnmpAdminString
    MAX-ACCESS   read-only
    STATUS       current
    DESCRIPTION
        "Cisco Firepower mgmt:BackupFsmStage:descr managed
        object property"
    ::= { cfprApMgmtBackupFsmStageEntry 4 }

cfprApMgmtBackupFsmStageLastUpdateTime OBJECT-TYPE
    SYNTAX       DateAndTime
    MAX-ACCESS   read-only
    STATUS       current
    DESCRIPTION
        "Cisco Firepower mgmt:BackupFsmStage:lastUpdateTime
        managed object property"
    ::= { cfprApMgmtBackupFsmStageEntry 5 }

cfprApMgmtBackupFsmStageName OBJECT-TYPE
    SYNTAX       CfprApMgmtBackupFsmStageName
    MAX-ACCESS   read-only
    STATUS       current
    DESCRIPTION
        "Cisco Firepower mgmt:BackupFsmStage:name managed object property"
    ::= { cfprApMgmtBackupFsmStageEntry 6 }

cfprApMgmtBackupFsmStageOrder OBJECT-TYPE
    SYNTAX       Gauge32
    MAX-ACCESS   read-only
    STATUS       current
    DESCRIPTION
        "Cisco Firepower mgmt:BackupFsmStage:order managed
        object property"
    ::= { cfprApMgmtBackupFsmStageEntry 7 }

cfprApMgmtBackupFsmStageRetry OBJECT-TYPE
    SYNTAX       Gauge32
    MAX-ACCESS   read-only
    STATUS       current
    DESCRIPTION
        "Cisco Firepower mgmt:BackupFsmStage:retry managed
        object property"
    ::= { cfprApMgmtBackupFsmStageEntry 8 }

cfprApMgmtBackupFsmStageStageStatus OBJECT-TYPE
    SYNTAX       CfprApFsmFsmStageStatus
    MAX-ACCESS   read-only
    STATUS       current
    DESCRIPTION
        "Cisco Firepower mgmt:BackupFsmStage:stageStatus
        managed object property"
    ::= { cfprApMgmtBackupFsmStageEntry 9 }

cfprApMgmtBackupFsmTaskTable OBJECT-TYPE
    SYNTAX           SEQUENCE OF CfprApMgmtBackupFsmTaskEntry
    MAX-ACCESS       not-accessible
    STATUS           current
    DESCRIPTION
        "Cisco Firepower mgmt:BackupFsmTask managed object table"
    ::= { cfprApMgmtObjects 8 }

cfprApMgmtBackupFsmTaskEntry OBJECT-TYPE
    SYNTAX           CfprApMgmtBackupFsmTaskEntry
    MAX-ACCESS       not-accessible
    STATUS           current
    DESCRIPTION
        "Entry for the cfprApMgmtBackupFsmTaskTable table."
    INDEX { cfprApMgmtBackupFsmTaskInstanceId }
    ::= { cfprApMgmtBackupFsmTaskTable 1 }

CfprApMgmtBackupFsmTaskEntry ::= SEQUENCE {
    cfprApMgmtBackupFsmTaskInstanceId                                CfprApManagedObjectId,
    cfprApMgmtBackupFsmTaskDn                                        CfprApManagedObjectDn,
    cfprApMgmtBackupFsmTaskRn                                        SnmpAdminString,
    cfprApMgmtBackupFsmTaskCompletion                                CfprApFsmCompletion,
    cfprApMgmtBackupFsmTaskFlags                                     CfprApFsmFlags,
    cfprApMgmtBackupFsmTaskItem                                      CfprApMgmtBackupFsmTaskItem,
    cfprApMgmtBackupFsmTaskSeqId                                     Gauge32
}

cfprApMgmtBackupFsmTaskInstanceId OBJECT-TYPE
    SYNTAX       CfprApManagedObjectId
    MAX-ACCESS   not-accessible
    STATUS       current
    DESCRIPTION
        "Instance identifier of the managed object."
    ::= { cfprApMgmtBackupFsmTaskEntry 1 }

cfprApMgmtBackupFsmTaskDn OBJECT-TYPE
    SYNTAX       CfprApManagedObjectDn
    MAX-ACCESS   read-only
    STATUS       current
    DESCRIPTION
        "Cisco Firepower mgmt:BackupFsmTask:dn managed object property"
    ::= { cfprApMgmtBackupFsmTaskEntry 2 }

cfprApMgmtBackupFsmTaskRn OBJECT-TYPE
    SYNTAX       SnmpAdminString
    MAX-ACCESS   read-only
    STATUS       current
    DESCRIPTION
        "Cisco Firepower mgmt:BackupFsmTask:rn managed object property"
    ::= { cfprApMgmtBackupFsmTaskEntry 3 }

cfprApMgmtBackupFsmTaskCompletion OBJECT-TYPE
    SYNTAX       CfprApFsmCompletion
    MAX-ACCESS   read-only
    STATUS       current
    DESCRIPTION
        "Cisco Firepower mgmt:BackupFsmTask:completion
        managed object property"
    ::= { cfprApMgmtBackupFsmTaskEntry 4 }

cfprApMgmtBackupFsmTaskFlags OBJECT-TYPE
    SYNTAX       CfprApFsmFlags
    MAX-ACCESS   read-only
    STATUS       current
    DESCRIPTION
        "Cisco Firepower mgmt:BackupFsmTask:flags managed object property"
    ::= { cfprApMgmtBackupFsmTaskEntry 5 }

cfprApMgmtBackupFsmTaskItem OBJECT-TYPE
    SYNTAX       CfprApMgmtBackupFsmTaskItem
    MAX-ACCESS   read-only
    STATUS       current
    DESCRIPTION
        "Cisco Firepower mgmt:BackupFsmTask:item managed object property"
    ::= { cfprApMgmtBackupFsmTaskEntry 6 }

cfprApMgmtBackupFsmTaskSeqId OBJECT-TYPE
    SYNTAX       Gauge32
    MAX-ACCESS   read-only
    STATUS       current
    DESCRIPTION
        "Cisco Firepower mgmt:BackupFsmTask:seqId managed object property"
    ::= { cfprApMgmtBackupFsmTaskEntry 7 }

cfprApMgmtBackupPolicyTable OBJECT-TYPE
    SYNTAX           SEQUENCE OF CfprApMgmtBackupPolicyEntry
    MAX-ACCESS       not-accessible
    STATUS           current
    DESCRIPTION
        "Cisco Firepower mgmt:BackupPolicy managed object table"
    ::= { cfprApMgmtObjects 9 }

cfprApMgmtBackupPolicyEntry OBJECT-TYPE
    SYNTAX           CfprApMgmtBackupPolicyEntry
    MAX-ACCESS       not-accessible
    STATUS           current
    DESCRIPTION
        "Entry for the cfprApMgmtBackupPolicyTable table."
    INDEX { cfprApMgmtBackupPolicyInstanceId }
    ::= { cfprApMgmtBackupPolicyTable 1 }

CfprApMgmtBackupPolicyEntry ::= SEQUENCE {
    cfprApMgmtBackupPolicyInstanceId                                 CfprApManagedObjectId,
    cfprApMgmtBackupPolicyDn                                         CfprApManagedObjectDn,
    cfprApMgmtBackupPolicyRn                                         SnmpAdminString,
    cfprApMgmtBackupPolicyAdminState                                 CfprApMgmtExportPolicyAdminState,
    cfprApMgmtBackupPolicyDescr                                      SnmpAdminString,
    cfprApMgmtBackupPolicyFsmDescr                                   SnmpAdminString,
    cfprApMgmtBackupPolicyFsmPrev                                    SnmpAdminString,
    cfprApMgmtBackupPolicyFsmProgr                                   Gauge32,
    cfprApMgmtBackupPolicyFsmRmtInvErrCode                           Gauge32,
    cfprApMgmtBackupPolicyFsmRmtInvErrDescr                          SnmpAdminString,
    cfprApMgmtBackupPolicyFsmRmtInvRslt                              CfprApConditionRemoteInvRslt,
    cfprApMgmtBackupPolicyFsmStageDescr                              SnmpAdminString,
    cfprApMgmtBackupPolicyFsmStamp                                   DateAndTime,
    cfprApMgmtBackupPolicyFsmStatus                                  SnmpAdminString,
    cfprApMgmtBackupPolicyFsmTry                                     Gauge32,
    cfprApMgmtBackupPolicyHost                                       SnmpAdminString,
    cfprApMgmtBackupPolicyIntId                                      SnmpAdminString,
    cfprApMgmtBackupPolicyLastBackup                                 DateAndTime,
    cfprApMgmtBackupPolicyMaxFiles                                   Gauge32,
    cfprApMgmtBackupPolicyName                                       SnmpAdminString,
    cfprApMgmtBackupPolicyPolicyLevel                                Gauge32,
    cfprApMgmtBackupPolicyPolicyOwner                                CfprApPolicyPolicyOwner,
    cfprApMgmtBackupPolicyPort                                       Gauge32,
    cfprApMgmtBackupPolicyProto                                      CfprApMgmtExportPolicyProto,
    cfprApMgmtBackupPolicyPwd                                        SnmpAdminString,
    cfprApMgmtBackupPolicyRemoteFile                                 SnmpAdminString,
    cfprApMgmtBackupPolicySchedule                                   CfprApMgmtBackupInterval,
    cfprApMgmtBackupPolicyUser                                       SnmpAdminString
}

cfprApMgmtBackupPolicyInstanceId OBJECT-TYPE
    SYNTAX       CfprApManagedObjectId
    MAX-ACCESS   not-accessible
    STATUS       current
    DESCRIPTION
        "Instance identifier of the managed object."
    ::= { cfprApMgmtBackupPolicyEntry 1 }

cfprApMgmtBackupPolicyDn OBJECT-TYPE
    SYNTAX       CfprApManagedObjectDn
    MAX-ACCESS   read-only
    STATUS       current
    DESCRIPTION
        "Cisco Firepower mgmt:BackupPolicy:dn managed object property"
    ::= { cfprApMgmtBackupPolicyEntry 2 }

cfprApMgmtBackupPolicyRn OBJECT-TYPE
    SYNTAX       SnmpAdminString
    MAX-ACCESS   read-only
    STATUS       current
    DESCRIPTION
        "Cisco Firepower mgmt:BackupPolicy:rn managed object property"
    ::= { cfprApMgmtBackupPolicyEntry 3 }

cfprApMgmtBackupPolicyAdminState OBJECT-TYPE
    SYNTAX       CfprApMgmtExportPolicyAdminState
    MAX-ACCESS   read-only
    STATUS       current
    DESCRIPTION
        "Cisco Firepower mgmt:BackupPolicy:adminState managed
        object property"
    ::= { cfprApMgmtBackupPolicyEntry 4 }

cfprApMgmtBackupPolicyDescr OBJECT-TYPE
    SYNTAX       SnmpAdminString
    MAX-ACCESS   read-only
    STATUS       current
    DESCRIPTION
        "Cisco Firepower mgmt:BackupPolicy:descr managed object property"
    ::= { cfprApMgmtBackupPolicyEntry 5 }

cfprApMgmtBackupPolicyFsmDescr OBJECT-TYPE
    SYNTAX       SnmpAdminString
    MAX-ACCESS   read-only
    STATUS       current
    DESCRIPTION
        "Cisco Firepower mgmt:BackupPolicy:fsmDescr managed
        object property"
    ::= { cfprApMgmtBackupPolicyEntry 6 }

cfprApMgmtBackupPolicyFsmPrev OBJECT-TYPE
    SYNTAX       SnmpAdminString
    MAX-ACCESS   read-only
    STATUS       current
    DESCRIPTION
        "Cisco Firepower mgmt:BackupPolicy:fsmPrev managed
        object property"
    ::= { cfprApMgmtBackupPolicyEntry 7 }

cfprApMgmtBackupPolicyFsmProgr OBJECT-TYPE
    SYNTAX       Gauge32
    MAX-ACCESS   read-only
    STATUS       current
    DESCRIPTION
        "Cisco Firepower mgmt:BackupPolicy:fsmProgr managed
        object property"
    ::= { cfprApMgmtBackupPolicyEntry 8 }

cfprApMgmtBackupPolicyFsmRmtInvErrCode OBJECT-TYPE
    SYNTAX       Gauge32
    MAX-ACCESS   read-only
    STATUS       current
    DESCRIPTION
        "Cisco Firepower mgmt:BackupPolicy:fsmRmtInvErrCode
        managed object property"
    ::= { cfprApMgmtBackupPolicyEntry 9 }

cfprApMgmtBackupPolicyFsmRmtInvErrDescr OBJECT-TYPE
    SYNTAX       SnmpAdminString
    MAX-ACCESS   read-only
    STATUS       current
    DESCRIPTION
        "Cisco Firepower mgmt:BackupPolicy:fsmRmtInvErrDescr
        managed object property"
    ::= { cfprApMgmtBackupPolicyEntry 10 }

cfprApMgmtBackupPolicyFsmRmtInvRslt OBJECT-TYPE
    SYNTAX       CfprApConditionRemoteInvRslt
    MAX-ACCESS   read-only
    STATUS       current
    DESCRIPTION
        "Cisco Firepower mgmt:BackupPolicy:fsmRmtInvRslt
        managed object property"
    ::= { cfprApMgmtBackupPolicyEntry 11 }

cfprApMgmtBackupPolicyFsmStageDescr OBJECT-TYPE
    SYNTAX       SnmpAdminString
    MAX-ACCESS   read-only
    STATUS       current
    DESCRIPTION
        "Cisco Firepower mgmt:BackupPolicy:fsmStageDescr
        managed object property"
    ::= { cfprApMgmtBackupPolicyEntry 12 }

cfprApMgmtBackupPolicyFsmStamp OBJECT-TYPE
    SYNTAX       DateAndTime
    MAX-ACCESS   read-only
    STATUS       current
    DESCRIPTION
        "Cisco Firepower mgmt:BackupPolicy:fsmStamp managed
        object property"
    ::= { cfprApMgmtBackupPolicyEntry 13 }

cfprApMgmtBackupPolicyFsmStatus OBJECT-TYPE
    SYNTAX       SnmpAdminString
    MAX-ACCESS   read-only
    STATUS       current
    DESCRIPTION
        "Cisco Firepower mgmt:BackupPolicy:fsmStatus managed
        object property"
    ::= { cfprApMgmtBackupPolicyEntry 14 }

cfprApMgmtBackupPolicyFsmTry OBJECT-TYPE
    SYNTAX       Gauge32
    MAX-ACCESS   read-only
    STATUS       current
    DESCRIPTION
        "Cisco Firepower mgmt:BackupPolicy:fsmTry managed object property"
    ::= { cfprApMgmtBackupPolicyEntry 15 }

cfprApMgmtBackupPolicyHost OBJECT-TYPE
    SYNTAX       SnmpAdminString
    MAX-ACCESS   read-only
    STATUS       current
    DESCRIPTION
        "Cisco Firepower mgmt:BackupPolicy:host managed object property"
    ::= { cfprApMgmtBackupPolicyEntry 16 }

cfprApMgmtBackupPolicyIntId OBJECT-TYPE
    SYNTAX       SnmpAdminString
    MAX-ACCESS   read-only
    STATUS       current
    DESCRIPTION
        "Cisco Firepower mgmt:BackupPolicy:intId managed object property"
    ::= { cfprApMgmtBackupPolicyEntry 17 }

cfprApMgmtBackupPolicyLastBackup OBJECT-TYPE
    SYNTAX       DateAndTime
    MAX-ACCESS   read-only
    STATUS       current
    DESCRIPTION
        "Cisco Firepower mgmt:BackupPolicy:lastBackup managed
        object property"
    ::= { cfprApMgmtBackupPolicyEntry 18 }

cfprApMgmtBackupPolicyMaxFiles OBJECT-TYPE
    SYNTAX       Gauge32
    MAX-ACCESS   read-only
    STATUS       current
    DESCRIPTION
        "Cisco Firepower mgmt:BackupPolicy:maxFiles managed
        object property"
    ::= { cfprApMgmtBackupPolicyEntry 19 }

cfprApMgmtBackupPolicyName OBJECT-TYPE
    SYNTAX       SnmpAdminString
    MAX-ACCESS   read-only
    STATUS       current
    DESCRIPTION
        "Cisco Firepower mgmt:BackupPolicy:name managed object property"
    ::= { cfprApMgmtBackupPolicyEntry 20 }

cfprApMgmtBackupPolicyPolicyLevel OBJECT-TYPE
    SYNTAX       Gauge32
    MAX-ACCESS   read-only
    STATUS       current
    DESCRIPTION
        "Cisco Firepower mgmt:BackupPolicy:policyLevel
        managed object property"
    ::= { cfprApMgmtBackupPolicyEntry 21 }

cfprApMgmtBackupPolicyPolicyOwner OBJECT-TYPE
    SYNTAX       CfprApPolicyPolicyOwner
    MAX-ACCESS   read-only
    STATUS       current
    DESCRIPTION
        "Cisco Firepower mgmt:BackupPolicy:policyOwner
        managed object property"
    ::= { cfprApMgmtBackupPolicyEntry 22 }

cfprApMgmtBackupPolicyPort OBJECT-TYPE
    SYNTAX       Gauge32
    MAX-ACCESS   read-only
    STATUS       current
    DESCRIPTION
        "Cisco Firepower mgmt:BackupPolicy:port managed object property"
    ::= { cfprApMgmtBackupPolicyEntry 23 }

cfprApMgmtBackupPolicyProto OBJECT-TYPE
    SYNTAX       CfprApMgmtExportPolicyProto
    MAX-ACCESS   read-only
    STATUS       current
    DESCRIPTION
        "Cisco Firepower mgmt:BackupPolicy:proto managed object property"
    ::= { cfprApMgmtBackupPolicyEntry 24 }

cfprApMgmtBackupPolicyPwd OBJECT-TYPE
    SYNTAX       SnmpAdminString
    MAX-ACCESS   read-only
    STATUS       current
    DESCRIPTION
        "Cisco Firepower mgmt:BackupPolicy:pwd managed object property"
    ::= { cfprApMgmtBackupPolicyEntry 25 }

cfprApMgmtBackupPolicyRemoteFile OBJECT-TYPE
    SYNTAX       SnmpAdminString
    MAX-ACCESS   read-only
    STATUS       current
    DESCRIPTION
        "Cisco Firepower mgmt:BackupPolicy:remoteFile managed
        object property"
    ::= { cfprApMgmtBackupPolicyEntry 26 }

cfprApMgmtBackupPolicySchedule OBJECT-TYPE
    SYNTAX       CfprApMgmtBackupInterval
    MAX-ACCESS   read-only
    STATUS       current
    DESCRIPTION
        "Cisco Firepower mgmt:BackupPolicy:schedule managed
        object property"
    ::= { cfprApMgmtBackupPolicyEntry 27 }

cfprApMgmtBackupPolicyUser OBJECT-TYPE
    SYNTAX       SnmpAdminString
    MAX-ACCESS   read-only
    STATUS       current
    DESCRIPTION
        "Cisco Firepower mgmt:BackupPolicy:user managed object property"
    ::= { cfprApMgmtBackupPolicyEntry 28 }

cfprApMgmtBackupPolicyConfigTable OBJECT-TYPE
    SYNTAX           SEQUENCE OF CfprApMgmtBackupPolicyConfigEntry
    MAX-ACCESS       not-accessible
    STATUS           current
    DESCRIPTION
        "Cisco Firepower mgmt:BackupPolicyConfig managed object table"
    ::= { cfprApMgmtObjects 10 }

cfprApMgmtBackupPolicyConfigEntry OBJECT-TYPE
    SYNTAX           CfprApMgmtBackupPolicyConfigEntry
    MAX-ACCESS       not-accessible
    STATUS           current
    DESCRIPTION
        "Entry for the cfprApMgmtBackupPolicyConfigTable table."
    INDEX { cfprApMgmtBackupPolicyConfigInstanceId }
    ::= { cfprApMgmtBackupPolicyConfigTable 1 }

CfprApMgmtBackupPolicyConfigEntry ::= SEQUENCE {
    cfprApMgmtBackupPolicyConfigInstanceId                           CfprApManagedObjectId,
    cfprApMgmtBackupPolicyConfigDn                                   CfprApManagedObjectDn,
    cfprApMgmtBackupPolicyConfigRn                                   SnmpAdminString,
    cfprApMgmtBackupPolicyConfigAdminState                           CfprApTrigAdminState,
    cfprApMgmtBackupPolicyConfigAutoDelete                           TruthValue,
    cfprApMgmtBackupPolicyConfigBackupDate                           DateAndTime,
    cfprApMgmtBackupPolicyConfigBackupIssue                          CfprApMgmtBackupIssue,
    cfprApMgmtBackupPolicyConfigDescr                                SnmpAdminString,
    cfprApMgmtBackupPolicyConfigIgnoreCap                            TruthValue,
    cfprApMgmtBackupPolicyConfigIntId                                SnmpAdminString,
    cfprApMgmtBackupPolicyConfigName                                 SnmpAdminString,
    cfprApMgmtBackupPolicyConfigOperScheduler                        SnmpAdminString,
    cfprApMgmtBackupPolicyConfigOperState                            CfprApTrigTrigOperState,
    cfprApMgmtBackupPolicyConfigPolicyLevel                          Gauge32,
    cfprApMgmtBackupPolicyConfigPolicyOwner                          CfprApPolicyPolicyOwner,
    cfprApMgmtBackupPolicyConfigScheduler                            SnmpAdminString
}

cfprApMgmtBackupPolicyConfigInstanceId OBJECT-TYPE
    SYNTAX       CfprApManagedObjectId
    MAX-ACCESS   not-accessible
    STATUS       current
    DESCRIPTION
        "Instance identifier of the managed object."
    ::= { cfprApMgmtBackupPolicyConfigEntry 1 }

cfprApMgmtBackupPolicyConfigDn OBJECT-TYPE
    SYNTAX       CfprApManagedObjectDn
    MAX-ACCESS   read-only
    STATUS       current
    DESCRIPTION
        "Cisco Firepower mgmt:BackupPolicyConfig:dn managed
        object property"
    ::= { cfprApMgmtBackupPolicyConfigEntry 2 }

cfprApMgmtBackupPolicyConfigRn OBJECT-TYPE
    SYNTAX       SnmpAdminString
    MAX-ACCESS   read-only
    STATUS       current
    DESCRIPTION
        "Cisco Firepower mgmt:BackupPolicyConfig:rn managed
        object property"
    ::= { cfprApMgmtBackupPolicyConfigEntry 3 }

cfprApMgmtBackupPolicyConfigAdminState OBJECT-TYPE
    SYNTAX       CfprApTrigAdminState
    MAX-ACCESS   read-only
    STATUS       current
    DESCRIPTION
        "Cisco Firepower mgmt:BackupPolicyConfig:adminState
        managed object property"
    ::= { cfprApMgmtBackupPolicyConfigEntry 4 }

cfprApMgmtBackupPolicyConfigAutoDelete OBJECT-TYPE
    SYNTAX       TruthValue
    MAX-ACCESS   read-only
    STATUS       current
    DESCRIPTION
        "Cisco Firepower mgmt:BackupPolicyConfig:autoDelete
        managed object property"
    ::= { cfprApMgmtBackupPolicyConfigEntry 5 }

cfprApMgmtBackupPolicyConfigBackupDate OBJECT-TYPE
    SYNTAX       DateAndTime
    MAX-ACCESS   read-only
    STATUS       current
    DESCRIPTION
        "Cisco Firepower mgmt:BackupPolicyConfig:backupDate
        managed object property"
    ::= { cfprApMgmtBackupPolicyConfigEntry 6 }

cfprApMgmtBackupPolicyConfigBackupIssue OBJECT-TYPE
    SYNTAX       CfprApMgmtBackupIssue
    MAX-ACCESS   read-only
    STATUS       current
    DESCRIPTION
        "Cisco Firepower mgmt:BackupPolicyConfig:backupIssue
        managed object property"
    ::= { cfprApMgmtBackupPolicyConfigEntry 7 }

cfprApMgmtBackupPolicyConfigDescr OBJECT-TYPE
    SYNTAX       SnmpAdminString
    MAX-ACCESS   read-only
    STATUS       current
    DESCRIPTION
        "Cisco Firepower mgmt:BackupPolicyConfig:descr
        managed object property"
    ::= { cfprApMgmtBackupPolicyConfigEntry 8 }

cfprApMgmtBackupPolicyConfigIgnoreCap OBJECT-TYPE
    SYNTAX       TruthValue
    MAX-ACCESS   read-only
    STATUS       current
    DESCRIPTION
        "Cisco Firepower mgmt:BackupPolicyConfig:ignoreCap
        managed object property"
    ::= { cfprApMgmtBackupPolicyConfigEntry 9 }

cfprApMgmtBackupPolicyConfigIntId OBJECT-TYPE
    SYNTAX       SnmpAdminString
    MAX-ACCESS   read-only
    STATUS       current
    DESCRIPTION
        "Cisco Firepower mgmt:BackupPolicyConfig:intId
        managed object property"
    ::= { cfprApMgmtBackupPolicyConfigEntry 10 }

cfprApMgmtBackupPolicyConfigName OBJECT-TYPE
    SYNTAX       SnmpAdminString
    MAX-ACCESS   read-only
    STATUS       current
    DESCRIPTION
        "Cisco Firepower mgmt:BackupPolicyConfig:name managed
        object property"
    ::= { cfprApMgmtBackupPolicyConfigEntry 11 }

cfprApMgmtBackupPolicyConfigOperScheduler OBJECT-TYPE
    SYNTAX       SnmpAdminString
    MAX-ACCESS   read-only
    STATUS       current
    DESCRIPTION
        "Cisco Firepower mgmt:BackupPolicyConfig:operScheduler
        managed object property"
    ::= { cfprApMgmtBackupPolicyConfigEntry 12 }

cfprApMgmtBackupPolicyConfigOperState OBJECT-TYPE
    SYNTAX       CfprApTrigTrigOperState
    MAX-ACCESS   read-only
    STATUS       current
    DESCRIPTION
        "Cisco Firepower mgmt:BackupPolicyConfig:operState
        managed object property"
    ::= { cfprApMgmtBackupPolicyConfigEntry 13 }

cfprApMgmtBackupPolicyConfigPolicyLevel OBJECT-TYPE
    SYNTAX       Gauge32
    MAX-ACCESS   read-only
    STATUS       current
    DESCRIPTION
        "Cisco Firepower mgmt:BackupPolicyConfig:policyLevel
        managed object property"
    ::= { cfprApMgmtBackupPolicyConfigEntry 14 }

cfprApMgmtBackupPolicyConfigPolicyOwner OBJECT-TYPE
    SYNTAX       CfprApPolicyPolicyOwner
    MAX-ACCESS   read-only
    STATUS       current
    DESCRIPTION
        "Cisco Firepower mgmt:BackupPolicyConfig:policyOwner
        managed object property"
    ::= { cfprApMgmtBackupPolicyConfigEntry 15 }

cfprApMgmtBackupPolicyConfigScheduler OBJECT-TYPE
    SYNTAX       SnmpAdminString
    MAX-ACCESS   read-only
    STATUS       current
    DESCRIPTION
        "Cisco Firepower mgmt:BackupPolicyConfig:scheduler
        managed object property"
    ::= { cfprApMgmtBackupPolicyConfigEntry 16 }

cfprApMgmtBackupPolicyFsmTable OBJECT-TYPE
    SYNTAX           SEQUENCE OF CfprApMgmtBackupPolicyFsmEntry
    MAX-ACCESS       not-accessible
    STATUS           current
    DESCRIPTION
        "Cisco Firepower mgmt:BackupPolicyFsm managed object table"
    ::= { cfprApMgmtObjects 11 }

cfprApMgmtBackupPolicyFsmEntry OBJECT-TYPE
    SYNTAX           CfprApMgmtBackupPolicyFsmEntry
    MAX-ACCESS       not-accessible
    STATUS           current
    DESCRIPTION
        "Entry for the cfprApMgmtBackupPolicyFsmTable table."
    INDEX { cfprApMgmtBackupPolicyFsmInstanceId }
    ::= { cfprApMgmtBackupPolicyFsmTable 1 }

CfprApMgmtBackupPolicyFsmEntry ::= SEQUENCE {
    cfprApMgmtBackupPolicyFsmInstanceId                              CfprApManagedObjectId,
    cfprApMgmtBackupPolicyFsmDn                                      CfprApManagedObjectDn,
    cfprApMgmtBackupPolicyFsmRn                                      SnmpAdminString,
    cfprApMgmtBackupPolicyFsmCompletionTime                          DateAndTime,
    cfprApMgmtBackupPolicyFsmCurrentFsm                              CfprApMgmtBackupPolicyFsmCurrentFsm,
    cfprApMgmtBackupPolicyFsmDescrData                               SnmpAdminString,
    cfprApMgmtBackupPolicyFsmFsmStatus                               CfprApFsmFsmStageStatus,
    cfprApMgmtBackupPolicyFsmProgress                                Gauge32,
    cfprApMgmtBackupPolicyFsmRmtErrCode                              Gauge32,
    cfprApMgmtBackupPolicyFsmRmtErrDescr                             SnmpAdminString,
    cfprApMgmtBackupPolicyFsmRmtRslt                                 CfprApConditionRemoteInvRslt
}

cfprApMgmtBackupPolicyFsmInstanceId OBJECT-TYPE
    SYNTAX       CfprApManagedObjectId
    MAX-ACCESS   not-accessible
    STATUS       current
    DESCRIPTION
        "Instance identifier of the managed object."
    ::= { cfprApMgmtBackupPolicyFsmEntry 1 }

cfprApMgmtBackupPolicyFsmDn OBJECT-TYPE
    SYNTAX       CfprApManagedObjectDn
    MAX-ACCESS   read-only
    STATUS       current
    DESCRIPTION
        "Cisco Firepower mgmt:BackupPolicyFsm:dn managed object property"
    ::= { cfprApMgmtBackupPolicyFsmEntry 2 }

cfprApMgmtBackupPolicyFsmRn OBJECT-TYPE
    SYNTAX       SnmpAdminString
    MAX-ACCESS   read-only
    STATUS       current
    DESCRIPTION
        "Cisco Firepower mgmt:BackupPolicyFsm:rn managed object property"
    ::= { cfprApMgmtBackupPolicyFsmEntry 3 }

cfprApMgmtBackupPolicyFsmCompletionTime OBJECT-TYPE
    SYNTAX       DateAndTime
    MAX-ACCESS   read-only
    STATUS       current
    DESCRIPTION
        "Cisco Firepower mgmt:BackupPolicyFsm:completionTime
        managed object property"
    ::= { cfprApMgmtBackupPolicyFsmEntry 4 }

cfprApMgmtBackupPolicyFsmCurrentFsm OBJECT-TYPE
    SYNTAX       CfprApMgmtBackupPolicyFsmCurrentFsm
    MAX-ACCESS   read-only
    STATUS       current
    DESCRIPTION
        "Cisco Firepower mgmt:BackupPolicyFsm:currentFsm
        managed object property"
    ::= { cfprApMgmtBackupPolicyFsmEntry 5 }

cfprApMgmtBackupPolicyFsmDescrData OBJECT-TYPE
    SYNTAX       SnmpAdminString
    MAX-ACCESS   read-only
    STATUS       current
    DESCRIPTION
        "Cisco Firepower mgmt:BackupPolicyFsm:descr managed
        object property"
    ::= { cfprApMgmtBackupPolicyFsmEntry 6 }

cfprApMgmtBackupPolicyFsmFsmStatus OBJECT-TYPE
    SYNTAX       CfprApFsmFsmStageStatus
    MAX-ACCESS   read-only
    STATUS       current
    DESCRIPTION
        "Cisco Firepower mgmt:BackupPolicyFsm:fsmStatus
        managed object property"
    ::= { cfprApMgmtBackupPolicyFsmEntry 7 }

cfprApMgmtBackupPolicyFsmProgress OBJECT-TYPE
    SYNTAX       Gauge32
    MAX-ACCESS   read-only
    STATUS       current
    DESCRIPTION
        "Cisco Firepower mgmt:BackupPolicyFsm:progress
        managed object property"
    ::= { cfprApMgmtBackupPolicyFsmEntry 8 }

cfprApMgmtBackupPolicyFsmRmtErrCode OBJECT-TYPE
    SYNTAX       Gauge32
    MAX-ACCESS   read-only
    STATUS       current
    DESCRIPTION
        "Cisco Firepower mgmt:BackupPolicyFsm:rmtErrCode
        managed object property"
    ::= { cfprApMgmtBackupPolicyFsmEntry 9 }

cfprApMgmtBackupPolicyFsmRmtErrDescr OBJECT-TYPE
    SYNTAX       SnmpAdminString
    MAX-ACCESS   read-only
    STATUS       current
    DESCRIPTION
        "Cisco Firepower mgmt:BackupPolicyFsm:rmtErrDescr
        managed object property"
    ::= { cfprApMgmtBackupPolicyFsmEntry 10 }

cfprApMgmtBackupPolicyFsmRmtRslt OBJECT-TYPE
    SYNTAX       CfprApConditionRemoteInvRslt
    MAX-ACCESS   read-only
    STATUS       current
    DESCRIPTION
        "Cisco Firepower mgmt:BackupPolicyFsm:rmtRslt managed
        object property"
    ::= { cfprApMgmtBackupPolicyFsmEntry 11 }

cfprApMgmtBackupPolicyFsmStageTable OBJECT-TYPE
    SYNTAX           SEQUENCE OF CfprApMgmtBackupPolicyFsmStageEntry
    MAX-ACCESS       not-accessible
    STATUS           current
    DESCRIPTION
        "Cisco Firepower mgmt:BackupPolicyFsmStage managed object table"
    ::= { cfprApMgmtObjects 12 }

cfprApMgmtBackupPolicyFsmStageEntry OBJECT-TYPE
    SYNTAX           CfprApMgmtBackupPolicyFsmStageEntry
    MAX-ACCESS       not-accessible
    STATUS           current
    DESCRIPTION
        "Entry for the cfprApMgmtBackupPolicyFsmStageTable table."
    INDEX { cfprApMgmtBackupPolicyFsmStageInstanceId }
    ::= { cfprApMgmtBackupPolicyFsmStageTable 1 }

CfprApMgmtBackupPolicyFsmStageEntry ::= SEQUENCE {
    cfprApMgmtBackupPolicyFsmStageInstanceId                         CfprApManagedObjectId,
    cfprApMgmtBackupPolicyFsmStageDn                                 CfprApManagedObjectDn,
    cfprApMgmtBackupPolicyFsmStageRn                                 SnmpAdminString,
    cfprApMgmtBackupPolicyFsmStageDescrData                          SnmpAdminString,
    cfprApMgmtBackupPolicyFsmStageLastUpdateTime                     DateAndTime,
    cfprApMgmtBackupPolicyFsmStageName                               CfprApMgmtBackupPolicyFsmStageName,
    cfprApMgmtBackupPolicyFsmStageOrder                              Gauge32,
    cfprApMgmtBackupPolicyFsmStageRetry                              Gauge32,
    cfprApMgmtBackupPolicyFsmStageStageStatus                        CfprApFsmFsmStageStatus
}

cfprApMgmtBackupPolicyFsmStageInstanceId OBJECT-TYPE
    SYNTAX       CfprApManagedObjectId
    MAX-ACCESS   not-accessible
    STATUS       current
    DESCRIPTION
        "Instance identifier of the managed object."
    ::= { cfprApMgmtBackupPolicyFsmStageEntry 1 }

cfprApMgmtBackupPolicyFsmStageDn OBJECT-TYPE
    SYNTAX       CfprApManagedObjectDn
    MAX-ACCESS   read-only
    STATUS       current
    DESCRIPTION
        "Cisco Firepower mgmt:BackupPolicyFsmStage:dn managed
        object property"
    ::= { cfprApMgmtBackupPolicyFsmStageEntry 2 }

cfprApMgmtBackupPolicyFsmStageRn OBJECT-TYPE
    SYNTAX       SnmpAdminString
    MAX-ACCESS   read-only
    STATUS       current
    DESCRIPTION
        "Cisco Firepower mgmt:BackupPolicyFsmStage:rn managed
        object property"
    ::= { cfprApMgmtBackupPolicyFsmStageEntry 3 }

cfprApMgmtBackupPolicyFsmStageDescrData OBJECT-TYPE
    SYNTAX       SnmpAdminString
    MAX-ACCESS   read-only
    STATUS       current
    DESCRIPTION
        "Cisco Firepower mgmt:BackupPolicyFsmStage:descr
        managed object property"
    ::= { cfprApMgmtBackupPolicyFsmStageEntry 4 }

cfprApMgmtBackupPolicyFsmStageLastUpdateTime OBJECT-TYPE
    SYNTAX       DateAndTime
    MAX-ACCESS   read-only
    STATUS       current
    DESCRIPTION
        "Cisco Firepower mgmt:BackupPolicyFsmStage:lastUpdateTime
        managed object property"
    ::= { cfprApMgmtBackupPolicyFsmStageEntry 5 }

cfprApMgmtBackupPolicyFsmStageName OBJECT-TYPE
    SYNTAX       CfprApMgmtBackupPolicyFsmStageName
    MAX-ACCESS   read-only
    STATUS       current
    DESCRIPTION
        "Cisco Firepower mgmt:BackupPolicyFsmStage:name
        managed object property"
    ::= { cfprApMgmtBackupPolicyFsmStageEntry 6 }

cfprApMgmtBackupPolicyFsmStageOrder OBJECT-TYPE
    SYNTAX       Gauge32
    MAX-ACCESS   read-only
    STATUS       current
    DESCRIPTION
        "Cisco Firepower mgmt:BackupPolicyFsmStage:order
        managed object property"
    ::= { cfprApMgmtBackupPolicyFsmStageEntry 7 }

cfprApMgmtBackupPolicyFsmStageRetry OBJECT-TYPE
    SYNTAX       Gauge32
    MAX-ACCESS   read-only
    STATUS       current
    DESCRIPTION
        "Cisco Firepower mgmt:BackupPolicyFsmStage:retry
        managed object property"
    ::= { cfprApMgmtBackupPolicyFsmStageEntry 8 }

cfprApMgmtBackupPolicyFsmStageStageStatus OBJECT-TYPE
    SYNTAX       CfprApFsmFsmStageStatus
    MAX-ACCESS   read-only
    STATUS       current
    DESCRIPTION
        "Cisco Firepower mgmt:BackupPolicyFsmStage:stageStatus
        managed object property"
    ::= { cfprApMgmtBackupPolicyFsmStageEntry 9 }

cfprApMgmtCfgExportPolicyTable OBJECT-TYPE
    SYNTAX           SEQUENCE OF CfprApMgmtCfgExportPolicyEntry
    MAX-ACCESS       not-accessible
    STATUS           current
    DESCRIPTION
        "Cisco Firepower mgmt:CfgExportPolicy managed object table"
    ::= { cfprApMgmtObjects 13 }

cfprApMgmtCfgExportPolicyEntry OBJECT-TYPE
    SYNTAX           CfprApMgmtCfgExportPolicyEntry
    MAX-ACCESS       not-accessible
    STATUS           current
    DESCRIPTION
        "Entry for the cfprApMgmtCfgExportPolicyTable table."
    INDEX { cfprApMgmtCfgExportPolicyInstanceId }
    ::= { cfprApMgmtCfgExportPolicyTable 1 }

CfprApMgmtCfgExportPolicyEntry ::= SEQUENCE {
    cfprApMgmtCfgExportPolicyInstanceId                              CfprApManagedObjectId,
    cfprApMgmtCfgExportPolicyDn                                      CfprApManagedObjectDn,
    cfprApMgmtCfgExportPolicyRn                                      SnmpAdminString,
    cfprApMgmtCfgExportPolicyAdminState                              CfprApMgmtExportPolicyAdminState,
    cfprApMgmtCfgExportPolicyDescr                                   SnmpAdminString,
    cfprApMgmtCfgExportPolicyFsmDescr                                SnmpAdminString,
    cfprApMgmtCfgExportPolicyFsmPrev                                 SnmpAdminString,
    cfprApMgmtCfgExportPolicyFsmProgr                                Gauge32,
    cfprApMgmtCfgExportPolicyFsmRmtInvErrCode                        Gauge32,
    cfprApMgmtCfgExportPolicyFsmRmtInvErrDescr                       SnmpAdminString,
    cfprApMgmtCfgExportPolicyFsmRmtInvRslt                           CfprApConditionRemoteInvRslt,
    cfprApMgmtCfgExportPolicyFsmStageDescr                           SnmpAdminString,
    cfprApMgmtCfgExportPolicyFsmStamp                                DateAndTime,
    cfprApMgmtCfgExportPolicyFsmStatus                               SnmpAdminString,
    cfprApMgmtCfgExportPolicyFsmTry                                  Gauge32,
    cfprApMgmtCfgExportPolicyHost                                    SnmpAdminString,
    cfprApMgmtCfgExportPolicyIntId                                   SnmpAdminString,
    cfprApMgmtCfgExportPolicyLastBackup                              DateAndTime,
    cfprApMgmtCfgExportPolicyMaxFiles                                Gauge32,
    cfprApMgmtCfgExportPolicyName                                    SnmpAdminString,
    cfprApMgmtCfgExportPolicyPolicyLevel                             Gauge32,
    cfprApMgmtCfgExportPolicyPolicyOwner                             CfprApPolicyPolicyOwner,
    cfprApMgmtCfgExportPolicyPort                                    Gauge32,
    cfprApMgmtCfgExportPolicyProto                                   CfprApMgmtExportPolicyProto,
    cfprApMgmtCfgExportPolicyPwd                                     SnmpAdminString,
    cfprApMgmtCfgExportPolicyRemoteFile                              SnmpAdminString,
    cfprApMgmtCfgExportPolicySchedule                                CfprApMgmtBackupInterval,
    cfprApMgmtCfgExportPolicyUser                                    SnmpAdminString
}

cfprApMgmtCfgExportPolicyInstanceId OBJECT-TYPE
    SYNTAX       CfprApManagedObjectId
    MAX-ACCESS   not-accessible
    STATUS       current
    DESCRIPTION
        "Instance identifier of the managed object."
    ::= { cfprApMgmtCfgExportPolicyEntry 1 }

cfprApMgmtCfgExportPolicyDn OBJECT-TYPE
    SYNTAX       CfprApManagedObjectDn
    MAX-ACCESS   read-only
    STATUS       current
    DESCRIPTION
        "Cisco Firepower mgmt:CfgExportPolicy:dn managed object property"
    ::= { cfprApMgmtCfgExportPolicyEntry 2 }

cfprApMgmtCfgExportPolicyRn OBJECT-TYPE
    SYNTAX       SnmpAdminString
    MAX-ACCESS   read-only
    STATUS       current
    DESCRIPTION
        "Cisco Firepower mgmt:CfgExportPolicy:rn managed object property"
    ::= { cfprApMgmtCfgExportPolicyEntry 3 }

cfprApMgmtCfgExportPolicyAdminState OBJECT-TYPE
    SYNTAX       CfprApMgmtExportPolicyAdminState
    MAX-ACCESS   read-only
    STATUS       current
    DESCRIPTION
        "Cisco Firepower mgmt:CfgExportPolicy:adminState
        managed object property"
    ::= { cfprApMgmtCfgExportPolicyEntry 4 }

cfprApMgmtCfgExportPolicyDescr OBJECT-TYPE
    SYNTAX       SnmpAdminString
    MAX-ACCESS   read-only
    STATUS       current
    DESCRIPTION
        "Cisco Firepower mgmt:CfgExportPolicy:descr managed
        object property"
    ::= { cfprApMgmtCfgExportPolicyEntry 5 }

cfprApMgmtCfgExportPolicyFsmDescr OBJECT-TYPE
    SYNTAX       SnmpAdminString
    MAX-ACCESS   read-only
    STATUS       current
    DESCRIPTION
        "Cisco Firepower mgmt:CfgExportPolicy:fsmDescr
        managed object property"
    ::= { cfprApMgmtCfgExportPolicyEntry 6 }

cfprApMgmtCfgExportPolicyFsmPrev OBJECT-TYPE
    SYNTAX       SnmpAdminString
    MAX-ACCESS   read-only
    STATUS       current
    DESCRIPTION
        "Cisco Firepower mgmt:CfgExportPolicy:fsmPrev managed
        object property"
    ::= { cfprApMgmtCfgExportPolicyEntry 7 }

cfprApMgmtCfgExportPolicyFsmProgr OBJECT-TYPE
    SYNTAX       Gauge32
    MAX-ACCESS   read-only
    STATUS       current
    DESCRIPTION
        "Cisco Firepower mgmt:CfgExportPolicy:fsmProgr
        managed object property"
    ::= { cfprApMgmtCfgExportPolicyEntry 8 }

cfprApMgmtCfgExportPolicyFsmRmtInvErrCode OBJECT-TYPE
    SYNTAX       Gauge32
    MAX-ACCESS   read-only
    STATUS       current
    DESCRIPTION
        "Cisco Firepower mgmt:CfgExportPolicy:fsmRmtInvErrCode
        managed object property"
    ::= { cfprApMgmtCfgExportPolicyEntry 9 }

cfprApMgmtCfgExportPolicyFsmRmtInvErrDescr OBJECT-TYPE
    SYNTAX       SnmpAdminString
    MAX-ACCESS   read-only
    STATUS       current
    DESCRIPTION
        "Cisco Firepower mgmt:CfgExportPolicy:fsmRmtInvErrDescr
        managed object property"
    ::= { cfprApMgmtCfgExportPolicyEntry 10 }

cfprApMgmtCfgExportPolicyFsmRmtInvRslt OBJECT-TYPE
    SYNTAX       CfprApConditionRemoteInvRslt
    MAX-ACCESS   read-only
    STATUS       current
    DESCRIPTION
        "Cisco Firepower mgmt:CfgExportPolicy:fsmRmtInvRslt
        managed object property"
    ::= { cfprApMgmtCfgExportPolicyEntry 11 }

cfprApMgmtCfgExportPolicyFsmStageDescr OBJECT-TYPE
    SYNTAX       SnmpAdminString
    MAX-ACCESS   read-only
    STATUS       current
    DESCRIPTION
        "Cisco Firepower mgmt:CfgExportPolicy:fsmStageDescr
        managed object property"
    ::= { cfprApMgmtCfgExportPolicyEntry 12 }

cfprApMgmtCfgExportPolicyFsmStamp OBJECT-TYPE
    SYNTAX       DateAndTime
    MAX-ACCESS   read-only
    STATUS       current
    DESCRIPTION
        "Cisco Firepower mgmt:CfgExportPolicy:fsmStamp
        managed object property"
    ::= { cfprApMgmtCfgExportPolicyEntry 13 }

cfprApMgmtCfgExportPolicyFsmStatus OBJECT-TYPE
    SYNTAX       SnmpAdminString
    MAX-ACCESS   read-only
    STATUS       current
    DESCRIPTION
        "Cisco Firepower mgmt:CfgExportPolicy:fsmStatus
        managed object property"
    ::= { cfprApMgmtCfgExportPolicyEntry 14 }

cfprApMgmtCfgExportPolicyFsmTry OBJECT-TYPE
    SYNTAX       Gauge32
    MAX-ACCESS   read-only
    STATUS       current
    DESCRIPTION
        "Cisco Firepower mgmt:CfgExportPolicy:fsmTry managed
        object property"
    ::= { cfprApMgmtCfgExportPolicyEntry 15 }

cfprApMgmtCfgExportPolicyHost OBJECT-TYPE
    SYNTAX       SnmpAdminString
    MAX-ACCESS   read-only
    STATUS       current
    DESCRIPTION
        "Cisco Firepower mgmt:CfgExportPolicy:host managed
        object property"
    ::= { cfprApMgmtCfgExportPolicyEntry 16 }

cfprApMgmtCfgExportPolicyIntId OBJECT-TYPE
    SYNTAX       SnmpAdminString
    MAX-ACCESS   read-only
    STATUS       current
    DESCRIPTION
        "Cisco Firepower mgmt:CfgExportPolicy:intId managed
        object property"
    ::= { cfprApMgmtCfgExportPolicyEntry 17 }

cfprApMgmtCfgExportPolicyLastBackup OBJECT-TYPE
    SYNTAX       DateAndTime
    MAX-ACCESS   read-only
    STATUS       current
    DESCRIPTION
        "Cisco Firepower mgmt:CfgExportPolicy:lastBackup
        managed object property"
    ::= { cfprApMgmtCfgExportPolicyEntry 18 }

cfprApMgmtCfgExportPolicyMaxFiles OBJECT-TYPE
    SYNTAX       Gauge32
    MAX-ACCESS   read-only
    STATUS       current
    DESCRIPTION
        "Cisco Firepower mgmt:CfgExportPolicy:maxFiles
        managed object property"
    ::= { cfprApMgmtCfgExportPolicyEntry 19 }

cfprApMgmtCfgExportPolicyName OBJECT-TYPE
    SYNTAX       SnmpAdminString
    MAX-ACCESS   read-only
    STATUS       current
    DESCRIPTION
        "Cisco Firepower mgmt:CfgExportPolicy:name managed
        object property"
    ::= { cfprApMgmtCfgExportPolicyEntry 20 }

cfprApMgmtCfgExportPolicyPolicyLevel OBJECT-TYPE
    SYNTAX       Gauge32
    MAX-ACCESS   read-only
    STATUS       current
    DESCRIPTION
        "Cisco Firepower mgmt:CfgExportPolicy:policyLevel
        managed object property"
    ::= { cfprApMgmtCfgExportPolicyEntry 21 }

cfprApMgmtCfgExportPolicyPolicyOwner OBJECT-TYPE
    SYNTAX       CfprApPolicyPolicyOwner
    MAX-ACCESS   read-only
    STATUS       current
    DESCRIPTION
        "Cisco Firepower mgmt:CfgExportPolicy:policyOwner
        managed object property"
    ::= { cfprApMgmtCfgExportPolicyEntry 22 }

cfprApMgmtCfgExportPolicyPort OBJECT-TYPE
    SYNTAX       Gauge32
    MAX-ACCESS   read-only
    STATUS       current
    DESCRIPTION
        "Cisco Firepower mgmt:CfgExportPolicy:port managed
        object property"
    ::= { cfprApMgmtCfgExportPolicyEntry 23 }

cfprApMgmtCfgExportPolicyProto OBJECT-TYPE
    SYNTAX       CfprApMgmtExportPolicyProto
    MAX-ACCESS   read-only
    STATUS       current
    DESCRIPTION
        "Cisco Firepower mgmt:CfgExportPolicy:proto managed
        object property"
    ::= { cfprApMgmtCfgExportPolicyEntry 24 }

cfprApMgmtCfgExportPolicyPwd OBJECT-TYPE
    SYNTAX       SnmpAdminString
    MAX-ACCESS   read-only
    STATUS       current
    DESCRIPTION
        "Cisco Firepower mgmt:CfgExportPolicy:pwd managed object property"
    ::= { cfprApMgmtCfgExportPolicyEntry 25 }

cfprApMgmtCfgExportPolicyRemoteFile OBJECT-TYPE
    SYNTAX       SnmpAdminString
    MAX-ACCESS   read-only
    STATUS       current
    DESCRIPTION
        "Cisco Firepower mgmt:CfgExportPolicy:remoteFile
        managed object property"
    ::= { cfprApMgmtCfgExportPolicyEntry 26 }

cfprApMgmtCfgExportPolicySchedule OBJECT-TYPE
    SYNTAX       CfprApMgmtBackupInterval
    MAX-ACCESS   read-only
    STATUS       current
    DESCRIPTION
        "Cisco Firepower mgmt:CfgExportPolicy:schedule
        managed object property"
    ::= { cfprApMgmtCfgExportPolicyEntry 27 }

cfprApMgmtCfgExportPolicyUser OBJECT-TYPE
    SYNTAX       SnmpAdminString
    MAX-ACCESS   read-only
    STATUS       current
    DESCRIPTION
        "Cisco Firepower mgmt:CfgExportPolicy:user managed
        object property"
    ::= { cfprApMgmtCfgExportPolicyEntry 28 }

cfprApMgmtCfgExportPolicyFsmTable OBJECT-TYPE
    SYNTAX           SEQUENCE OF CfprApMgmtCfgExportPolicyFsmEntry
    MAX-ACCESS       not-accessible
    STATUS           current
    DESCRIPTION
        "Cisco Firepower mgmt:CfgExportPolicyFsm managed object table"
    ::= { cfprApMgmtObjects 14 }

cfprApMgmtCfgExportPolicyFsmEntry OBJECT-TYPE
    SYNTAX           CfprApMgmtCfgExportPolicyFsmEntry
    MAX-ACCESS       not-accessible
    STATUS           current
    DESCRIPTION
        "Entry for the cfprApMgmtCfgExportPolicyFsmTable table."
    INDEX { cfprApMgmtCfgExportPolicyFsmInstanceId }
    ::= { cfprApMgmtCfgExportPolicyFsmTable 1 }

CfprApMgmtCfgExportPolicyFsmEntry ::= SEQUENCE {
    cfprApMgmtCfgExportPolicyFsmInstanceId                           CfprApManagedObjectId,
    cfprApMgmtCfgExportPolicyFsmDn                                   CfprApManagedObjectDn,
    cfprApMgmtCfgExportPolicyFsmRn                                   SnmpAdminString,
    cfprApMgmtCfgExportPolicyFsmCompletionTime                       DateAndTime,
    cfprApMgmtCfgExportPolicyFsmCurrentFsm                           CfprApMgmtCfgExportPolicyFsmCurrentFsm,
    cfprApMgmtCfgExportPolicyFsmDescrData                            SnmpAdminString,
    cfprApMgmtCfgExportPolicyFsmFsmStatus                            CfprApFsmFsmStageStatus,
    cfprApMgmtCfgExportPolicyFsmProgress                             Gauge32,
    cfprApMgmtCfgExportPolicyFsmRmtErrCode                           Gauge32,
    cfprApMgmtCfgExportPolicyFsmRmtErrDescr                          SnmpAdminString,
    cfprApMgmtCfgExportPolicyFsmRmtRslt                              CfprApConditionRemoteInvRslt
}

cfprApMgmtCfgExportPolicyFsmInstanceId OBJECT-TYPE
    SYNTAX       CfprApManagedObjectId
    MAX-ACCESS   not-accessible
    STATUS       current
    DESCRIPTION
        "Instance identifier of the managed object."
    ::= { cfprApMgmtCfgExportPolicyFsmEntry 1 }

cfprApMgmtCfgExportPolicyFsmDn OBJECT-TYPE
    SYNTAX       CfprApManagedObjectDn
    MAX-ACCESS   read-only
    STATUS       current
    DESCRIPTION
        "Cisco Firepower mgmt:CfgExportPolicyFsm:dn managed
        object property"
    ::= { cfprApMgmtCfgExportPolicyFsmEntry 2 }

cfprApMgmtCfgExportPolicyFsmRn OBJECT-TYPE
    SYNTAX       SnmpAdminString
    MAX-ACCESS   read-only
    STATUS       current
    DESCRIPTION
        "Cisco Firepower mgmt:CfgExportPolicyFsm:rn managed
        object property"
    ::= { cfprApMgmtCfgExportPolicyFsmEntry 3 }

cfprApMgmtCfgExportPolicyFsmCompletionTime OBJECT-TYPE
    SYNTAX       DateAndTime
    MAX-ACCESS   read-only
    STATUS       current
    DESCRIPTION
        "Cisco Firepower mgmt:CfgExportPolicyFsm:completionTime
        managed object property"
    ::= { cfprApMgmtCfgExportPolicyFsmEntry 4 }

cfprApMgmtCfgExportPolicyFsmCurrentFsm OBJECT-TYPE
    SYNTAX       CfprApMgmtCfgExportPolicyFsmCurrentFsm
    MAX-ACCESS   read-only
    STATUS       current
    DESCRIPTION
        "Cisco Firepower mgmt:CfgExportPolicyFsm:currentFsm
        managed object property"
    ::= { cfprApMgmtCfgExportPolicyFsmEntry 5 }

cfprApMgmtCfgExportPolicyFsmDescrData OBJECT-TYPE
    SYNTAX       SnmpAdminString
    MAX-ACCESS   read-only
    STATUS       current
    DESCRIPTION
        "Cisco Firepower mgmt:CfgExportPolicyFsm:descr
        managed object property"
    ::= { cfprApMgmtCfgExportPolicyFsmEntry 6 }

cfprApMgmtCfgExportPolicyFsmFsmStatus OBJECT-TYPE
    SYNTAX       CfprApFsmFsmStageStatus
    MAX-ACCESS   read-only
    STATUS       current
    DESCRIPTION
        "Cisco Firepower mgmt:CfgExportPolicyFsm:fsmStatus
        managed object property"
    ::= { cfprApMgmtCfgExportPolicyFsmEntry 7 }

cfprApMgmtCfgExportPolicyFsmProgress OBJECT-TYPE
    SYNTAX       Gauge32
    MAX-ACCESS   read-only
    STATUS       current
    DESCRIPTION
        "Cisco Firepower mgmt:CfgExportPolicyFsm:progress
        managed object property"
    ::= { cfprApMgmtCfgExportPolicyFsmEntry 8 }

cfprApMgmtCfgExportPolicyFsmRmtErrCode OBJECT-TYPE
    SYNTAX       Gauge32
    MAX-ACCESS   read-only
    STATUS       current
    DESCRIPTION
        "Cisco Firepower mgmt:CfgExportPolicyFsm:rmtErrCode
        managed object property"
    ::= { cfprApMgmtCfgExportPolicyFsmEntry 9 }

cfprApMgmtCfgExportPolicyFsmRmtErrDescr OBJECT-TYPE
    SYNTAX       SnmpAdminString
    MAX-ACCESS   read-only
    STATUS       current
    DESCRIPTION
        "Cisco Firepower mgmt:CfgExportPolicyFsm:rmtErrDescr
        managed object property"
    ::= { cfprApMgmtCfgExportPolicyFsmEntry 10 }

cfprApMgmtCfgExportPolicyFsmRmtRslt OBJECT-TYPE
    SYNTAX       CfprApConditionRemoteInvRslt
    MAX-ACCESS   read-only
    STATUS       current
    DESCRIPTION
        "Cisco Firepower mgmt:CfgExportPolicyFsm:rmtRslt
        managed object property"
    ::= { cfprApMgmtCfgExportPolicyFsmEntry 11 }

cfprApMgmtCfgExportPolicyFsmStageTable OBJECT-TYPE
    SYNTAX           SEQUENCE OF CfprApMgmtCfgExportPolicyFsmStageEntry
    MAX-ACCESS       not-accessible
    STATUS           current
    DESCRIPTION
        "Cisco Firepower mgmt:CfgExportPolicyFsmStage managed
        object table"
    ::= { cfprApMgmtObjects 15 }

cfprApMgmtCfgExportPolicyFsmStageEntry OBJECT-TYPE
    SYNTAX           CfprApMgmtCfgExportPolicyFsmStageEntry
    MAX-ACCESS       not-accessible
    STATUS           current
    DESCRIPTION
        "Entry for the cfprApMgmtCfgExportPolicyFsmStageTable table."
    INDEX { cfprApMgmtCfgExportPolicyFsmStageInstanceId }
    ::= { cfprApMgmtCfgExportPolicyFsmStageTable 1 }

CfprApMgmtCfgExportPolicyFsmStageEntry ::= SEQUENCE {
    cfprApMgmtCfgExportPolicyFsmStageInstanceId                      CfprApManagedObjectId,
    cfprApMgmtCfgExportPolicyFsmStageDn                              CfprApManagedObjectDn,
    cfprApMgmtCfgExportPolicyFsmStageRn                              SnmpAdminString,
    cfprApMgmtCfgExportPolicyFsmStageDescrData                       SnmpAdminString,
    cfprApMgmtCfgExportPolicyFsmStageLastUpdateTime                  DateAndTime,
    cfprApMgmtCfgExportPolicyFsmStageName                            CfprApMgmtCfgExportPolicyFsmStageName,
    cfprApMgmtCfgExportPolicyFsmStageOrder                           Gauge32,
    cfprApMgmtCfgExportPolicyFsmStageRetry                           Gauge32,
    cfprApMgmtCfgExportPolicyFsmStageStageStatus                     CfprApFsmFsmStageStatus
}

cfprApMgmtCfgExportPolicyFsmStageInstanceId OBJECT-TYPE
    SYNTAX       CfprApManagedObjectId
    MAX-ACCESS   not-accessible
    STATUS       current
    DESCRIPTION
        "Instance identifier of the managed object."
    ::= { cfprApMgmtCfgExportPolicyFsmStageEntry 1 }

cfprApMgmtCfgExportPolicyFsmStageDn OBJECT-TYPE
    SYNTAX       CfprApManagedObjectDn
    MAX-ACCESS   read-only
    STATUS       current
    DESCRIPTION
        "Cisco Firepower mgmt:CfgExportPolicyFsmStage:dn
        managed object property"
    ::= { cfprApMgmtCfgExportPolicyFsmStageEntry 2 }

cfprApMgmtCfgExportPolicyFsmStageRn OBJECT-TYPE
    SYNTAX       SnmpAdminString
    MAX-ACCESS   read-only
    STATUS       current
    DESCRIPTION
        "Cisco Firepower mgmt:CfgExportPolicyFsmStage:rn
        managed object property"
    ::= { cfprApMgmtCfgExportPolicyFsmStageEntry 3 }

cfprApMgmtCfgExportPolicyFsmStageDescrData OBJECT-TYPE
    SYNTAX       SnmpAdminString
    MAX-ACCESS   read-only
    STATUS       current
    DESCRIPTION
        "Cisco Firepower mgmt:CfgExportPolicyFsmStage:descr
        managed object property"
    ::= { cfprApMgmtCfgExportPolicyFsmStageEntry 4 }

cfprApMgmtCfgExportPolicyFsmStageLastUpdateTime OBJECT-TYPE
    SYNTAX       DateAndTime
    MAX-ACCESS   read-only
    STATUS       current
    DESCRIPTION
        "Cisco Firepower mgmt:CfgExportPolicyFsmStage:lastUpdateTime
        managed object property"
    ::= { cfprApMgmtCfgExportPolicyFsmStageEntry 5 }

cfprApMgmtCfgExportPolicyFsmStageName OBJECT-TYPE
    SYNTAX       CfprApMgmtCfgExportPolicyFsmStageName
    MAX-ACCESS   read-only
    STATUS       current
    DESCRIPTION
        "Cisco Firepower mgmt:CfgExportPolicyFsmStage:name
        managed object property"
    ::= { cfprApMgmtCfgExportPolicyFsmStageEntry 6 }

cfprApMgmtCfgExportPolicyFsmStageOrder OBJECT-TYPE
    SYNTAX       Gauge32
    MAX-ACCESS   read-only
    STATUS       current
    DESCRIPTION
        "Cisco Firepower mgmt:CfgExportPolicyFsmStage:order
        managed object property"
    ::= { cfprApMgmtCfgExportPolicyFsmStageEntry 7 }

cfprApMgmtCfgExportPolicyFsmStageRetry OBJECT-TYPE
    SYNTAX       Gauge32
    MAX-ACCESS   read-only
    STATUS       current
    DESCRIPTION
        "Cisco Firepower mgmt:CfgExportPolicyFsmStage:retry
        managed object property"
    ::= { cfprApMgmtCfgExportPolicyFsmStageEntry 8 }

cfprApMgmtCfgExportPolicyFsmStageStageStatus OBJECT-TYPE
    SYNTAX       CfprApFsmFsmStageStatus
    MAX-ACCESS   read-only
    STATUS       current
    DESCRIPTION
        "Cisco Firepower mgmt:CfgExportPolicyFsmStage:stageStatus
        managed object property"
    ::= { cfprApMgmtCfgExportPolicyFsmStageEntry 9 }

cfprApMgmtCimcSecureBootTable OBJECT-TYPE
    SYNTAX           SEQUENCE OF CfprApMgmtCimcSecureBootEntry
    MAX-ACCESS       not-accessible
    STATUS           current
    DESCRIPTION
        "Cisco Firepower mgmt:CimcSecureBoot managed object table"
    ::= { cfprApMgmtObjects 16 }

cfprApMgmtCimcSecureBootEntry OBJECT-TYPE
    SYNTAX           CfprApMgmtCimcSecureBootEntry
    MAX-ACCESS       not-accessible
    STATUS           current
    DESCRIPTION
        "Entry for the cfprApMgmtCimcSecureBootTable table."
    INDEX { cfprApMgmtCimcSecureBootInstanceId }
    ::= { cfprApMgmtCimcSecureBootTable 1 }

CfprApMgmtCimcSecureBootEntry ::= SEQUENCE {
    cfprApMgmtCimcSecureBootInstanceId                               CfprApManagedObjectId,
    cfprApMgmtCimcSecureBootDn                                       CfprApManagedObjectDn,
    cfprApMgmtCimcSecureBootRn                                       SnmpAdminString,
    cfprApMgmtCimcSecureBootAdminState                               CfprApMgmtCimcSecureBootAdminState,
    cfprApMgmtCimcSecureBootOperState                                CfprApMgmtSecureBootOperState
}

cfprApMgmtCimcSecureBootInstanceId OBJECT-TYPE
    SYNTAX       CfprApManagedObjectId
    MAX-ACCESS   not-accessible
    STATUS       current
    DESCRIPTION
        "Instance identifier of the managed object."
    ::= { cfprApMgmtCimcSecureBootEntry 1 }

cfprApMgmtCimcSecureBootDn OBJECT-TYPE
    SYNTAX       CfprApManagedObjectDn
    MAX-ACCESS   read-only
    STATUS       current
    DESCRIPTION
        "Cisco Firepower mgmt:CimcSecureBoot:dn managed object property"
    ::= { cfprApMgmtCimcSecureBootEntry 2 }

cfprApMgmtCimcSecureBootRn OBJECT-TYPE
    SYNTAX       SnmpAdminString
    MAX-ACCESS   read-only
    STATUS       current
    DESCRIPTION
        "Cisco Firepower mgmt:CimcSecureBoot:rn managed object property"
    ::= { cfprApMgmtCimcSecureBootEntry 3 }

cfprApMgmtCimcSecureBootAdminState OBJECT-TYPE
    SYNTAX       CfprApMgmtCimcSecureBootAdminState
    MAX-ACCESS   read-only
    STATUS       current
    DESCRIPTION
        "Cisco Firepower mgmt:CimcSecureBoot:adminState
        managed object property"
    ::= { cfprApMgmtCimcSecureBootEntry 4 }

cfprApMgmtCimcSecureBootOperState OBJECT-TYPE
    SYNTAX       CfprApMgmtSecureBootOperState
    MAX-ACCESS   read-only
    STATUS       current
    DESCRIPTION
        "Cisco Firepower mgmt:CimcSecureBoot:operState
        managed object property"
    ::= { cfprApMgmtCimcSecureBootEntry 5 }

cfprApMgmtConnectionTable OBJECT-TYPE
    SYNTAX           SEQUENCE OF CfprApMgmtConnectionEntry
    MAX-ACCESS       not-accessible
    STATUS           current
    DESCRIPTION
        "Cisco Firepower mgmt:Connection managed object table"
    ::= { cfprApMgmtObjects 17 }

cfprApMgmtConnectionEntry OBJECT-TYPE
    SYNTAX           CfprApMgmtConnectionEntry
    MAX-ACCESS       not-accessible
    STATUS           current
    DESCRIPTION
        "Entry for the cfprApMgmtConnectionTable table."
    INDEX { cfprApMgmtConnectionInstanceId }
    ::= { cfprApMgmtConnectionTable 1 }

CfprApMgmtConnectionEntry ::= SEQUENCE {
    cfprApMgmtConnectionInstanceId                                   CfprApManagedObjectId,
    cfprApMgmtConnectionDn                                           CfprApManagedObjectDn,
    cfprApMgmtConnectionRn                                           SnmpAdminString,
    cfprApMgmtConnectionAck                                          CfprApMgmtConnectionState,
    cfprApMgmtConnectionOperState                                    CfprApMgmtConnectionState,
    cfprApMgmtConnectionType                                         CfprApMgmtSource
}

cfprApMgmtConnectionInstanceId OBJECT-TYPE
    SYNTAX       CfprApManagedObjectId
    MAX-ACCESS   not-accessible
    STATUS       current
    DESCRIPTION
        "Instance identifier of the managed object."
    ::= { cfprApMgmtConnectionEntry 1 }

cfprApMgmtConnectionDn OBJECT-TYPE
    SYNTAX       CfprApManagedObjectDn
    MAX-ACCESS   read-only
    STATUS       current
    DESCRIPTION
        "Cisco Firepower mgmt:Connection:dn managed object property"
    ::= { cfprApMgmtConnectionEntry 2 }

cfprApMgmtConnectionRn OBJECT-TYPE
    SYNTAX       SnmpAdminString
    MAX-ACCESS   read-only
    STATUS       current
    DESCRIPTION
        "Cisco Firepower mgmt:Connection:rn managed object property"
    ::= { cfprApMgmtConnectionEntry 3 }

cfprApMgmtConnectionAck OBJECT-TYPE
    SYNTAX       CfprApMgmtConnectionState
    MAX-ACCESS   read-only
    STATUS       current
    DESCRIPTION
        "Cisco Firepower mgmt:Connection:ack managed object property"
    ::= { cfprApMgmtConnectionEntry 4 }

cfprApMgmtConnectionOperState OBJECT-TYPE
    SYNTAX       CfprApMgmtConnectionState
    MAX-ACCESS   read-only
    STATUS       current
    DESCRIPTION
        "Cisco Firepower mgmt:Connection:operState managed
        object property"
    ::= { cfprApMgmtConnectionEntry 5 }

cfprApMgmtConnectionType OBJECT-TYPE
    SYNTAX       CfprApMgmtSource
    MAX-ACCESS   read-only
    STATUS       current
    DESCRIPTION
        "Cisco Firepower mgmt:Connection:type managed object property"
    ::= { cfprApMgmtConnectionEntry 6 }

cfprApMgmtControllerTable OBJECT-TYPE
    SYNTAX           SEQUENCE OF CfprApMgmtControllerEntry
    MAX-ACCESS       not-accessible
    STATUS           current
    DESCRIPTION
        "Cisco Firepower mgmt:Controller managed object table"
    ::= { cfprApMgmtObjects 18 }

cfprApMgmtControllerEntry OBJECT-TYPE
    SYNTAX           CfprApMgmtControllerEntry
    MAX-ACCESS       not-accessible
    STATUS           current
    DESCRIPTION
        "Entry for the cfprApMgmtControllerTable table."
    INDEX { cfprApMgmtControllerInstanceId }
    ::= { cfprApMgmtControllerTable 1 }

CfprApMgmtControllerEntry ::= SEQUENCE {
    cfprApMgmtControllerInstanceId                                   CfprApManagedObjectId,
    cfprApMgmtControllerDn                                           CfprApManagedObjectDn,
    cfprApMgmtControllerRn                                           SnmpAdminString,
    cfprApMgmtControllerDbVersion                                    SnmpAdminString,
    cfprApMgmtControllerDimmBlacklistingOperState                    CfprApMgmtDimmBlacklistingOperState,
    cfprApMgmtControllerFsmDescr                                     SnmpAdminString,
    cfprApMgmtControllerFsmFlags                                     SnmpAdminString,
    cfprApMgmtControllerFsmPrev                                      SnmpAdminString,
    cfprApMgmtControllerFsmProgr                                     Gauge32,
    cfprApMgmtControllerFsmRmtInvErrCode                             Gauge32,
    cfprApMgmtControllerFsmRmtInvErrDescr                            SnmpAdminString,
    cfprApMgmtControllerFsmRmtInvRslt                                CfprApConditionRemoteInvRslt,
    cfprApMgmtControllerFsmStageDescr                                SnmpAdminString,
    cfprApMgmtControllerFsmStamp                                     DateAndTime,
    cfprApMgmtControllerFsmStatus                                    SnmpAdminString,
    cfprApMgmtControllerFsmTry                                       Gauge32,
    cfprApMgmtControllerGuid                                         SnmpAdminString,
    cfprApMgmtControllerModel                                        SnmpAdminString,
    cfprApMgmtControllerOperConn                                     SnmpAdminString,
    cfprApMgmtControllerRevision                                     SnmpAdminString,
    cfprApMgmtControllerSerial                                       SnmpAdminString,
    cfprApMgmtControllerStorageOobInterfaceSupported                 TruthValue,
    cfprApMgmtControllerStorageSubsystemState                        CfprApMgmtStorageSubsystemState,
    cfprApMgmtControllerSubject                                      CfprApMgmtSubject,
    cfprApMgmtControllerVendor                                       SnmpAdminString
}

cfprApMgmtControllerInstanceId OBJECT-TYPE
    SYNTAX       CfprApManagedObjectId
    MAX-ACCESS   not-accessible
    STATUS       current
    DESCRIPTION
        "Instance identifier of the managed object."
    ::= { cfprApMgmtControllerEntry 1 }

cfprApMgmtControllerDn OBJECT-TYPE
    SYNTAX       CfprApManagedObjectDn
    MAX-ACCESS   read-only
    STATUS       current
    DESCRIPTION
        "Cisco Firepower mgmt:Controller:dn managed object property"
    ::= { cfprApMgmtControllerEntry 2 }

cfprApMgmtControllerRn OBJECT-TYPE
    SYNTAX       SnmpAdminString
    MAX-ACCESS   read-only
    STATUS       current
    DESCRIPTION
        "Cisco Firepower mgmt:Controller:rn managed object property"
    ::= { cfprApMgmtControllerEntry 3 }

cfprApMgmtControllerDbVersion OBJECT-TYPE
    SYNTAX       SnmpAdminString
    MAX-ACCESS   read-only
    STATUS       current
    DESCRIPTION
        "Cisco Firepower mgmt:Controller:dbVersion managed
        object property"
    ::= { cfprApMgmtControllerEntry 4 }

cfprApMgmtControllerDimmBlacklistingOperState OBJECT-TYPE
    SYNTAX       CfprApMgmtDimmBlacklistingOperState
    MAX-ACCESS   read-only
    STATUS       current
    DESCRIPTION
        "Cisco Firepower mgmt:Controller:dimmBlacklistingOperState
        managed object property"
    ::= { cfprApMgmtControllerEntry 5 }

cfprApMgmtControllerFsmDescr OBJECT-TYPE
    SYNTAX       SnmpAdminString
    MAX-ACCESS   read-only
    STATUS       current
    DESCRIPTION
        "Cisco Firepower mgmt:Controller:fsmDescr managed object property"
    ::= { cfprApMgmtControllerEntry 6 }

cfprApMgmtControllerFsmFlags OBJECT-TYPE
    SYNTAX       SnmpAdminString
    MAX-ACCESS   read-only
    STATUS       current
    DESCRIPTION
        "Cisco Firepower mgmt:Controller:fsmFlags managed object property"
    ::= { cfprApMgmtControllerEntry 7 }

cfprApMgmtControllerFsmPrev OBJECT-TYPE
    SYNTAX       SnmpAdminString
    MAX-ACCESS   read-only
    STATUS       current
    DESCRIPTION
        "Cisco Firepower mgmt:Controller:fsmPrev managed object property"
    ::= { cfprApMgmtControllerEntry 8 }

cfprApMgmtControllerFsmProgr OBJECT-TYPE
    SYNTAX       Gauge32
    MAX-ACCESS   read-only
    STATUS       current
    DESCRIPTION
        "Cisco Firepower mgmt:Controller:fsmProgr managed object property"
    ::= { cfprApMgmtControllerEntry 9 }

cfprApMgmtControllerFsmRmtInvErrCode OBJECT-TYPE
    SYNTAX       Gauge32
    MAX-ACCESS   read-only
    STATUS       current
    DESCRIPTION
        "Cisco Firepower mgmt:Controller:fsmRmtInvErrCode
        managed object property"
    ::= { cfprApMgmtControllerEntry 10 }

cfprApMgmtControllerFsmRmtInvErrDescr OBJECT-TYPE
    SYNTAX       SnmpAdminString
    MAX-ACCESS   read-only
    STATUS       current
    DESCRIPTION
        "Cisco Firepower mgmt:Controller:fsmRmtInvErrDescr
        managed object property"
    ::= { cfprApMgmtControllerEntry 11 }

cfprApMgmtControllerFsmRmtInvRslt OBJECT-TYPE
    SYNTAX       CfprApConditionRemoteInvRslt
    MAX-ACCESS   read-only
    STATUS       current
    DESCRIPTION
        "Cisco Firepower mgmt:Controller:fsmRmtInvRslt
        managed object property"
    ::= { cfprApMgmtControllerEntry 12 }

cfprApMgmtControllerFsmStageDescr OBJECT-TYPE
    SYNTAX       SnmpAdminString
    MAX-ACCESS   read-only
    STATUS       current
    DESCRIPTION
        "Cisco Firepower mgmt:Controller:fsmStageDescr
        managed object property"
    ::= { cfprApMgmtControllerEntry 13 }

cfprApMgmtControllerFsmStamp OBJECT-TYPE
    SYNTAX       DateAndTime
    MAX-ACCESS   read-only
    STATUS       current
    DESCRIPTION
        "Cisco Firepower mgmt:Controller:fsmStamp managed object property"
    ::= { cfprApMgmtControllerEntry 14 }

cfprApMgmtControllerFsmStatus OBJECT-TYPE
    SYNTAX       SnmpAdminString
    MAX-ACCESS   read-only
    STATUS       current
    DESCRIPTION
        "Cisco Firepower mgmt:Controller:fsmStatus managed
        object property"
    ::= { cfprApMgmtControllerEntry 15 }

cfprApMgmtControllerFsmTry OBJECT-TYPE
    SYNTAX       Gauge32
    MAX-ACCESS   read-only
    STATUS       current
    DESCRIPTION
        "Cisco Firepower mgmt:Controller:fsmTry managed object property"
    ::= { cfprApMgmtControllerEntry 16 }

cfprApMgmtControllerGuid OBJECT-TYPE
    SYNTAX       SnmpAdminString
    MAX-ACCESS   read-only
    STATUS       current
    DESCRIPTION
        "Cisco Firepower mgmt:Controller:guid managed object property"
    ::= { cfprApMgmtControllerEntry 17 }

cfprApMgmtControllerModel OBJECT-TYPE
    SYNTAX       SnmpAdminString
    MAX-ACCESS   read-only
    STATUS       current
    DESCRIPTION
        "Cisco Firepower mgmt:Controller:model managed object property"
    ::= { cfprApMgmtControllerEntry 18 }

cfprApMgmtControllerOperConn OBJECT-TYPE
    SYNTAX       SnmpAdminString
    MAX-ACCESS   read-only
    STATUS       current
    DESCRIPTION
        "Cisco Firepower mgmt:Controller:operConn managed object property"
    ::= { cfprApMgmtControllerEntry 19 }

cfprApMgmtControllerRevision OBJECT-TYPE
    SYNTAX       SnmpAdminString
    MAX-ACCESS   read-only
    STATUS       current
    DESCRIPTION
        "Cisco Firepower mgmt:Controller:revision managed object property"
    ::= { cfprApMgmtControllerEntry 20 }

cfprApMgmtControllerSerial OBJECT-TYPE
    SYNTAX       SnmpAdminString
    MAX-ACCESS   read-only
    STATUS       current
    DESCRIPTION
        "Cisco Firepower mgmt:Controller:serial managed object property"
    ::= { cfprApMgmtControllerEntry 21 }

cfprApMgmtControllerStorageOobInterfaceSupported OBJECT-TYPE
    SYNTAX       TruthValue
    MAX-ACCESS   read-only
    STATUS       current
    DESCRIPTION
        "Cisco Firepower mgmt:Controller:storageOobInterfaceSupported
        managed object property"
    ::= { cfprApMgmtControllerEntry 22 }

cfprApMgmtControllerStorageSubsystemState OBJECT-TYPE
    SYNTAX       CfprApMgmtStorageSubsystemState
    MAX-ACCESS   read-only
    STATUS       current
    DESCRIPTION
        "Cisco Firepower mgmt:Controller:storageSubsystemState
        managed object property"
    ::= { cfprApMgmtControllerEntry 23 }

cfprApMgmtControllerSubject OBJECT-TYPE
    SYNTAX       CfprApMgmtSubject
    MAX-ACCESS   read-only
    STATUS       current
    DESCRIPTION
        "Cisco Firepower mgmt:Controller:subject managed object property"
    ::= { cfprApMgmtControllerEntry 24 }

cfprApMgmtControllerVendor OBJECT-TYPE
    SYNTAX       SnmpAdminString
    MAX-ACCESS   read-only
    STATUS       current
    DESCRIPTION
        "Cisco Firepower mgmt:Controller:vendor managed object property"
    ::= { cfprApMgmtControllerEntry 25 }

cfprApMgmtControllerFsmTable OBJECT-TYPE
    SYNTAX           SEQUENCE OF CfprApMgmtControllerFsmEntry
    MAX-ACCESS       not-accessible
    STATUS           current
    DESCRIPTION
        "Cisco Firepower mgmt:ControllerFsm managed object table"
    ::= { cfprApMgmtObjects 19 }

cfprApMgmtControllerFsmEntry OBJECT-TYPE
    SYNTAX           CfprApMgmtControllerFsmEntry
    MAX-ACCESS       not-accessible
    STATUS           current
    DESCRIPTION
        "Entry for the cfprApMgmtControllerFsmTable table."
    INDEX { cfprApMgmtControllerFsmInstanceId }
    ::= { cfprApMgmtControllerFsmTable 1 }

CfprApMgmtControllerFsmEntry ::= SEQUENCE {
    cfprApMgmtControllerFsmInstanceId                                CfprApManagedObjectId,
    cfprApMgmtControllerFsmDn                                        CfprApManagedObjectDn,
    cfprApMgmtControllerFsmRn                                        SnmpAdminString,
    cfprApMgmtControllerFsmCompletionTime                            DateAndTime,
    cfprApMgmtControllerFsmCurrentFsm                                CfprApMgmtControllerFsmCurrentFsm,
    cfprApMgmtControllerFsmDescrData                                 SnmpAdminString,
    cfprApMgmtControllerFsmFsmStatus                                 CfprApFsmFsmStageStatus,
    cfprApMgmtControllerFsmProgress                                  Gauge32,
    cfprApMgmtControllerFsmRmtErrCode                                Gauge32,
    cfprApMgmtControllerFsmRmtErrDescr                               SnmpAdminString,
    cfprApMgmtControllerFsmRmtRslt                                   CfprApConditionRemoteInvRslt
}

cfprApMgmtControllerFsmInstanceId OBJECT-TYPE
    SYNTAX       CfprApManagedObjectId
    MAX-ACCESS   not-accessible
    STATUS       current
    DESCRIPTION
        "Instance identifier of the managed object."
    ::= { cfprApMgmtControllerFsmEntry 1 }

cfprApMgmtControllerFsmDn OBJECT-TYPE
    SYNTAX       CfprApManagedObjectDn
    MAX-ACCESS   read-only
    STATUS       current
    DESCRIPTION
        "Cisco Firepower mgmt:ControllerFsm:dn managed object property"
    ::= { cfprApMgmtControllerFsmEntry 2 }

cfprApMgmtControllerFsmRn OBJECT-TYPE
    SYNTAX       SnmpAdminString
    MAX-ACCESS   read-only
    STATUS       current
    DESCRIPTION
        "Cisco Firepower mgmt:ControllerFsm:rn managed object property"
    ::= { cfprApMgmtControllerFsmEntry 3 }

cfprApMgmtControllerFsmCompletionTime OBJECT-TYPE
    SYNTAX       DateAndTime
    MAX-ACCESS   read-only
    STATUS       current
    DESCRIPTION
        "Cisco Firepower mgmt:ControllerFsm:completionTime
        managed object property"
    ::= { cfprApMgmtControllerFsmEntry 4 }

cfprApMgmtControllerFsmCurrentFsm OBJECT-TYPE
    SYNTAX       CfprApMgmtControllerFsmCurrentFsm
    MAX-ACCESS   read-only
    STATUS       current
    DESCRIPTION
        "Cisco Firepower mgmt:ControllerFsm:currentFsm
        managed object property"
    ::= { cfprApMgmtControllerFsmEntry 5 }

cfprApMgmtControllerFsmDescrData OBJECT-TYPE
    SYNTAX       SnmpAdminString
    MAX-ACCESS   read-only
    STATUS       current
    DESCRIPTION
        "Cisco Firepower mgmt:ControllerFsm:descr managed object property"
    ::= { cfprApMgmtControllerFsmEntry 6 }

cfprApMgmtControllerFsmFsmStatus OBJECT-TYPE
    SYNTAX       CfprApFsmFsmStageStatus
    MAX-ACCESS   read-only
    STATUS       current
    DESCRIPTION
        "Cisco Firepower mgmt:ControllerFsm:fsmStatus managed
        object property"
    ::= { cfprApMgmtControllerFsmEntry 7 }

cfprApMgmtControllerFsmProgress OBJECT-TYPE
    SYNTAX       Gauge32
    MAX-ACCESS   read-only
    STATUS       current
    DESCRIPTION
        "Cisco Firepower mgmt:ControllerFsm:progress managed
        object property"
    ::= { cfprApMgmtControllerFsmEntry 8 }

cfprApMgmtControllerFsmRmtErrCode OBJECT-TYPE
    SYNTAX       Gauge32
    MAX-ACCESS   read-only
    STATUS       current
    DESCRIPTION
        "Cisco Firepower mgmt:ControllerFsm:rmtErrCode
        managed object property"
    ::= { cfprApMgmtControllerFsmEntry 9 }

cfprApMgmtControllerFsmRmtErrDescr OBJECT-TYPE
    SYNTAX       SnmpAdminString
    MAX-ACCESS   read-only
    STATUS       current
    DESCRIPTION
        "Cisco Firepower mgmt:ControllerFsm:rmtErrDescr
        managed object property"
    ::= { cfprApMgmtControllerFsmEntry 10 }

cfprApMgmtControllerFsmRmtRslt OBJECT-TYPE
    SYNTAX       CfprApConditionRemoteInvRslt
    MAX-ACCESS   read-only
    STATUS       current
    DESCRIPTION
        "Cisco Firepower mgmt:ControllerFsm:rmtRslt managed
        object property"
    ::= { cfprApMgmtControllerFsmEntry 11 }

cfprApMgmtControllerFsmStageTable OBJECT-TYPE
    SYNTAX           SEQUENCE OF CfprApMgmtControllerFsmStageEntry
    MAX-ACCESS       not-accessible
    STATUS           current
    DESCRIPTION
        "Cisco Firepower mgmt:ControllerFsmStage managed object table"
    ::= { cfprApMgmtObjects 20 }

cfprApMgmtControllerFsmStageEntry OBJECT-TYPE
    SYNTAX           CfprApMgmtControllerFsmStageEntry
    MAX-ACCESS       not-accessible
    STATUS           current
    DESCRIPTION
        "Entry for the cfprApMgmtControllerFsmStageTable table."
    INDEX { cfprApMgmtControllerFsmStageInstanceId }
    ::= { cfprApMgmtControllerFsmStageTable 1 }

CfprApMgmtControllerFsmStageEntry ::= SEQUENCE {
    cfprApMgmtControllerFsmStageInstanceId                           CfprApManagedObjectId,
    cfprApMgmtControllerFsmStageDn                                   CfprApManagedObjectDn,
    cfprApMgmtControllerFsmStageRn                                   SnmpAdminString,
    cfprApMgmtControllerFsmStageDescrData                            SnmpAdminString,
    cfprApMgmtControllerFsmStageLastUpdateTime                       DateAndTime,
    cfprApMgmtControllerFsmStageName                                 CfprApMgmtControllerFsmStageName,
    cfprApMgmtControllerFsmStageOrder                                Gauge32,
    cfprApMgmtControllerFsmStageRetry                                Gauge32,
    cfprApMgmtControllerFsmStageStageStatus                          CfprApFsmFsmStageStatus
}

cfprApMgmtControllerFsmStageInstanceId OBJECT-TYPE
    SYNTAX       CfprApManagedObjectId
    MAX-ACCESS   not-accessible
    STATUS       current
    DESCRIPTION
        "Instance identifier of the managed object."
    ::= { cfprApMgmtControllerFsmStageEntry 1 }

cfprApMgmtControllerFsmStageDn OBJECT-TYPE
    SYNTAX       CfprApManagedObjectDn
    MAX-ACCESS   read-only
    STATUS       current
    DESCRIPTION
        "Cisco Firepower mgmt:ControllerFsmStage:dn managed
        object property"
    ::= { cfprApMgmtControllerFsmStageEntry 2 }

cfprApMgmtControllerFsmStageRn OBJECT-TYPE
    SYNTAX       SnmpAdminString
    MAX-ACCESS   read-only
    STATUS       current
    DESCRIPTION
        "Cisco Firepower mgmt:ControllerFsmStage:rn managed
        object property"
    ::= { cfprApMgmtControllerFsmStageEntry 3 }

cfprApMgmtControllerFsmStageDescrData OBJECT-TYPE
    SYNTAX       SnmpAdminString
    MAX-ACCESS   read-only
    STATUS       current
    DESCRIPTION
        "Cisco Firepower mgmt:ControllerFsmStage:descr
        managed object property"
    ::= { cfprApMgmtControllerFsmStageEntry 4 }

cfprApMgmtControllerFsmStageLastUpdateTime OBJECT-TYPE
    SYNTAX       DateAndTime
    MAX-ACCESS   read-only
    STATUS       current
    DESCRIPTION
        "Cisco Firepower mgmt:ControllerFsmStage:lastUpdateTime
        managed object property"
    ::= { cfprApMgmtControllerFsmStageEntry 5 }

cfprApMgmtControllerFsmStageName OBJECT-TYPE
    SYNTAX       CfprApMgmtControllerFsmStageName
    MAX-ACCESS   read-only
    STATUS       current
    DESCRIPTION
        "Cisco Firepower mgmt:ControllerFsmStage:name managed
        object property"
    ::= { cfprApMgmtControllerFsmStageEntry 6 }

cfprApMgmtControllerFsmStageOrder OBJECT-TYPE
    SYNTAX       Gauge32
    MAX-ACCESS   read-only
    STATUS       current
    DESCRIPTION
        "Cisco Firepower mgmt:ControllerFsmStage:order
        managed object property"
    ::= { cfprApMgmtControllerFsmStageEntry 7 }

cfprApMgmtControllerFsmStageRetry OBJECT-TYPE
    SYNTAX       Gauge32
    MAX-ACCESS   read-only
    STATUS       current
    DESCRIPTION
        "Cisco Firepower mgmt:ControllerFsmStage:retry
        managed object property"
    ::= { cfprApMgmtControllerFsmStageEntry 8 }

cfprApMgmtControllerFsmStageStageStatus OBJECT-TYPE
    SYNTAX       CfprApFsmFsmStageStatus
    MAX-ACCESS   read-only
    STATUS       current
    DESCRIPTION
        "Cisco Firepower mgmt:ControllerFsmStage:stageStatus
        managed object property"
    ::= { cfprApMgmtControllerFsmStageEntry 9 }

cfprApMgmtControllerFsmTaskTable OBJECT-TYPE
    SYNTAX           SEQUENCE OF CfprApMgmtControllerFsmTaskEntry
    MAX-ACCESS       not-accessible
    STATUS           current
    DESCRIPTION
        "Cisco Firepower mgmt:ControllerFsmTask managed object table"
    ::= { cfprApMgmtObjects 21 }

cfprApMgmtControllerFsmTaskEntry OBJECT-TYPE
    SYNTAX           CfprApMgmtControllerFsmTaskEntry
    MAX-ACCESS       not-accessible
    STATUS           current
    DESCRIPTION
        "Entry for the cfprApMgmtControllerFsmTaskTable table."
    INDEX { cfprApMgmtControllerFsmTaskInstanceId }
    ::= { cfprApMgmtControllerFsmTaskTable 1 }

CfprApMgmtControllerFsmTaskEntry ::= SEQUENCE {
    cfprApMgmtControllerFsmTaskInstanceId                            CfprApManagedObjectId,
    cfprApMgmtControllerFsmTaskDn                                    CfprApManagedObjectDn,
    cfprApMgmtControllerFsmTaskRn                                    SnmpAdminString,
    cfprApMgmtControllerFsmTaskCompletion                            CfprApFsmCompletion,
    cfprApMgmtControllerFsmTaskFlags                                 CfprApMgmtControllerFsmTaskFlags,
    cfprApMgmtControllerFsmTaskItem                                  CfprApMgmtControllerFsmTaskItem,
    cfprApMgmtControllerFsmTaskSeqId                                 Gauge32
}

cfprApMgmtControllerFsmTaskInstanceId OBJECT-TYPE
    SYNTAX       CfprApManagedObjectId
    MAX-ACCESS   not-accessible
    STATUS       current
    DESCRIPTION
        "Instance identifier of the managed object."
    ::= { cfprApMgmtControllerFsmTaskEntry 1 }

cfprApMgmtControllerFsmTaskDn OBJECT-TYPE
    SYNTAX       CfprApManagedObjectDn
    MAX-ACCESS   read-only
    STATUS       current
    DESCRIPTION
        "Cisco Firepower mgmt:ControllerFsmTask:dn managed
        object property"
    ::= { cfprApMgmtControllerFsmTaskEntry 2 }

cfprApMgmtControllerFsmTaskRn OBJECT-TYPE
    SYNTAX       SnmpAdminString
    MAX-ACCESS   read-only
    STATUS       current
    DESCRIPTION
        "Cisco Firepower mgmt:ControllerFsmTask:rn managed
        object property"
    ::= { cfprApMgmtControllerFsmTaskEntry 3 }

cfprApMgmtControllerFsmTaskCompletion OBJECT-TYPE
    SYNTAX       CfprApFsmCompletion
    MAX-ACCESS   read-only
    STATUS       current
    DESCRIPTION
        "Cisco Firepower mgmt:ControllerFsmTask:completion
        managed object property"
    ::= { cfprApMgmtControllerFsmTaskEntry 4 }

cfprApMgmtControllerFsmTaskFlags OBJECT-TYPE
    SYNTAX       CfprApMgmtControllerFsmTaskFlags
    MAX-ACCESS   read-only
    STATUS       current
    DESCRIPTION
        "Cisco Firepower mgmt:ControllerFsmTask:flags managed
        object property"
    ::= { cfprApMgmtControllerFsmTaskEntry 5 }

cfprApMgmtControllerFsmTaskItem OBJECT-TYPE
    SYNTAX       CfprApMgmtControllerFsmTaskItem
    MAX-ACCESS   read-only
    STATUS       current
    DESCRIPTION
        "Cisco Firepower mgmt:ControllerFsmTask:item managed
        object property"
    ::= { cfprApMgmtControllerFsmTaskEntry 6 }

cfprApMgmtControllerFsmTaskSeqId OBJECT-TYPE
    SYNTAX       Gauge32
    MAX-ACCESS   read-only
    STATUS       current
    DESCRIPTION
        "Cisco Firepower mgmt:ControllerFsmTask:seqId managed
        object property"
    ::= { cfprApMgmtControllerFsmTaskEntry 7 }

cfprApMgmtEntityTable OBJECT-TYPE
    SYNTAX           SEQUENCE OF CfprApMgmtEntityEntry
    MAX-ACCESS       not-accessible
    STATUS           current
    DESCRIPTION
        "Cisco Firepower mgmt:Entity managed object table"
    ::= { cfprApMgmtObjects 22 }

cfprApMgmtEntityEntry OBJECT-TYPE
    SYNTAX           CfprApMgmtEntityEntry
    MAX-ACCESS       not-accessible
    STATUS           current
    DESCRIPTION
        "Entry for the cfprApMgmtEntityTable table."
    INDEX { cfprApMgmtEntityInstanceId }
    ::= { cfprApMgmtEntityTable 1 }

CfprApMgmtEntityEntry ::= SEQUENCE {
    cfprApMgmtEntityInstanceId                                       CfprApManagedObjectId,
    cfprApMgmtEntityDn                                               CfprApManagedObjectDn,
    cfprApMgmtEntityRn                                               SnmpAdminString,
    cfprApMgmtEntityChassis1                                         SnmpAdminString,
    cfprApMgmtEntityChassis2                                         SnmpAdminString,
    cfprApMgmtEntityChassis3                                         SnmpAdminString,
    cfprApMgmtEntityChassisDeviceIoState1                            CfprApMgmtEntityChassisDeviceIoState1,
    cfprApMgmtEntityChassisDeviceIoState2                            CfprApMgmtEntityChassisDeviceIoState2,
    cfprApMgmtEntityChassisDeviceIoState3                            CfprApMgmtEntityChassisDeviceIoState3,
    cfprApMgmtEntityHaFailureReason                                  CfprApMgmtEntityHaFailureReason,
    cfprApMgmtEntityHaReadiness                                      CfprApMgmtEntityHaReadiness,
    cfprApMgmtEntityHaReady                                          TruthValue,
    cfprApMgmtEntityId                                               CfprApNetworkSwitchId,
    cfprApMgmtEntityLeadership                                       CfprApMgmtEntityLeadership,
    cfprApMgmtEntityMgmtServicesState                                CfprApMgmtEntityMgmtServicesState,
    cfprApMgmtEntityProblems                                         CfprApMgmtEntityProblems,
    cfprApMgmtEntitySshAuthKeysCsum                                  SnmpAdminString,
    cfprApMgmtEntitySshAuthKeysSize                                  Unsigned64,
    cfprApMgmtEntitySshKeyStatus                                     Unsigned64,
    cfprApMgmtEntitySshRootPubKeyCsum                                SnmpAdminString,
    cfprApMgmtEntitySshRootPubKeySize                                Unsigned64,
    cfprApMgmtEntityState                                            CfprApMgmtEntityState,
    cfprApMgmtEntityUmbilicalState                                   CfprApMgmtEntityUmbilicalState,
    cfprApMgmtEntityVersionMismatch                                  TruthValue
}

cfprApMgmtEntityInstanceId OBJECT-TYPE
    SYNTAX       CfprApManagedObjectId
    MAX-ACCESS   not-accessible
    STATUS       current
    DESCRIPTION
        "Instance identifier of the managed object."
    ::= { cfprApMgmtEntityEntry 1 }

cfprApMgmtEntityDn OBJECT-TYPE
    SYNTAX       CfprApManagedObjectDn
    MAX-ACCESS   read-only
    STATUS       current
    DESCRIPTION
        "Cisco Firepower mgmt:Entity:dn managed object property"
    ::= { cfprApMgmtEntityEntry 2 }

cfprApMgmtEntityRn OBJECT-TYPE
    SYNTAX       SnmpAdminString
    MAX-ACCESS   read-only
    STATUS       current
    DESCRIPTION
        "Cisco Firepower mgmt:Entity:rn managed object property"
    ::= { cfprApMgmtEntityEntry 3 }

cfprApMgmtEntityChassis1 OBJECT-TYPE
    SYNTAX       SnmpAdminString
    MAX-ACCESS   read-only
    STATUS       current
    DESCRIPTION
        "Cisco Firepower mgmt:Entity:chassis1 managed object property"
    ::= { cfprApMgmtEntityEntry 4 }

cfprApMgmtEntityChassis2 OBJECT-TYPE
    SYNTAX       SnmpAdminString
    MAX-ACCESS   read-only
    STATUS       current
    DESCRIPTION
        "Cisco Firepower mgmt:Entity:chassis2 managed object property"
    ::= { cfprApMgmtEntityEntry 5 }

cfprApMgmtEntityChassis3 OBJECT-TYPE
    SYNTAX       SnmpAdminString
    MAX-ACCESS   read-only
    STATUS       current
    DESCRIPTION
        "Cisco Firepower mgmt:Entity:chassis3 managed object property"
    ::= { cfprApMgmtEntityEntry 6 }

cfprApMgmtEntityChassisDeviceIoState1 OBJECT-TYPE
    SYNTAX       CfprApMgmtEntityChassisDeviceIoState1
    MAX-ACCESS   read-only
    STATUS       current
    DESCRIPTION
        "Cisco Firepower mgmt:Entity:chassisDeviceIoState1
        managed object property"
    ::= { cfprApMgmtEntityEntry 7 }

cfprApMgmtEntityChassisDeviceIoState2 OBJECT-TYPE
    SYNTAX       CfprApMgmtEntityChassisDeviceIoState2
    MAX-ACCESS   read-only
    STATUS       current
    DESCRIPTION
        "Cisco Firepower mgmt:Entity:chassisDeviceIoState2
        managed object property"
    ::= { cfprApMgmtEntityEntry 8 }

cfprApMgmtEntityChassisDeviceIoState3 OBJECT-TYPE
    SYNTAX       CfprApMgmtEntityChassisDeviceIoState3
    MAX-ACCESS   read-only
    STATUS       current
    DESCRIPTION
        "Cisco Firepower mgmt:Entity:chassisDeviceIoState3
        managed object property"
    ::= { cfprApMgmtEntityEntry 9 }

cfprApMgmtEntityHaFailureReason OBJECT-TYPE
    SYNTAX       CfprApMgmtEntityHaFailureReason
    MAX-ACCESS   read-only
    STATUS       current
    DESCRIPTION
        "Cisco Firepower mgmt:Entity:haFailureReason managed
        object property"
    ::= { cfprApMgmtEntityEntry 10 }

cfprApMgmtEntityHaReadiness OBJECT-TYPE
    SYNTAX       CfprApMgmtEntityHaReadiness
    MAX-ACCESS   read-only
    STATUS       current
    DESCRIPTION
        "Cisco Firepower mgmt:Entity:haReadiness managed object property"
    ::= { cfprApMgmtEntityEntry 11 }

cfprApMgmtEntityHaReady OBJECT-TYPE
    SYNTAX       TruthValue
    MAX-ACCESS   read-only
    STATUS       current
    DESCRIPTION
        "Cisco Firepower mgmt:Entity:haReady managed object property"
    ::= { cfprApMgmtEntityEntry 12 }

cfprApMgmtEntityId OBJECT-TYPE
    SYNTAX       CfprApNetworkSwitchId
    MAX-ACCESS   read-only
    STATUS       current
    DESCRIPTION
        "Cisco Firepower mgmt:Entity:id managed object property"
    ::= { cfprApMgmtEntityEntry 13 }

cfprApMgmtEntityLeadership OBJECT-TYPE
    SYNTAX       CfprApMgmtEntityLeadership
    MAX-ACCESS   read-only
    STATUS       current
    DESCRIPTION
        "Cisco Firepower mgmt:Entity:leadership managed object property"
    ::= { cfprApMgmtEntityEntry 14 }

cfprApMgmtEntityMgmtServicesState OBJECT-TYPE
    SYNTAX       CfprApMgmtEntityMgmtServicesState
    MAX-ACCESS   read-only
    STATUS       current
    DESCRIPTION
        "Cisco Firepower mgmt:Entity:mgmtServicesState
        managed object property"
    ::= { cfprApMgmtEntityEntry 15 }

cfprApMgmtEntityProblems OBJECT-TYPE
    SYNTAX       CfprApMgmtEntityProblems
    MAX-ACCESS   read-only
    STATUS       current
    DESCRIPTION
        "Cisco Firepower mgmt:Entity:problems managed object property"
    ::= { cfprApMgmtEntityEntry 16 }

cfprApMgmtEntitySshAuthKeysCsum OBJECT-TYPE
    SYNTAX       SnmpAdminString
    MAX-ACCESS   read-only
    STATUS       current
    DESCRIPTION
        "Cisco Firepower mgmt:Entity:sshAuthKeysCsum managed
        object property"
    ::= { cfprApMgmtEntityEntry 17 }

cfprApMgmtEntitySshAuthKeysSize OBJECT-TYPE
    SYNTAX       Unsigned64
    MAX-ACCESS   read-only
    STATUS       current
    DESCRIPTION
        "Cisco Firepower mgmt:Entity:sshAuthKeysSize managed
        object property"
    ::= { cfprApMgmtEntityEntry 18 }

cfprApMgmtEntitySshKeyStatus OBJECT-TYPE
    SYNTAX       Unsigned64
    MAX-ACCESS   read-only
    STATUS       current
    DESCRIPTION
        "Cisco Firepower mgmt:Entity:sshKeyStatus managed object property"
    ::= { cfprApMgmtEntityEntry 19 }

cfprApMgmtEntitySshRootPubKeyCsum OBJECT-TYPE
    SYNTAX       SnmpAdminString
    MAX-ACCESS   read-only
    STATUS       current
    DESCRIPTION
        "Cisco Firepower mgmt:Entity:sshRootPubKeyCsum
        managed object property"
    ::= { cfprApMgmtEntityEntry 20 }

cfprApMgmtEntitySshRootPubKeySize OBJECT-TYPE
    SYNTAX       Unsigned64
    MAX-ACCESS   read-only
    STATUS       current
    DESCRIPTION
        "Cisco Firepower mgmt:Entity:sshRootPubKeySize
        managed object property"
    ::= { cfprApMgmtEntityEntry 21 }

cfprApMgmtEntityState OBJECT-TYPE
    SYNTAX       CfprApMgmtEntityState
    MAX-ACCESS   read-only
    STATUS       current
    DESCRIPTION
        "Cisco Firepower mgmt:Entity:state managed object property"
    ::= { cfprApMgmtEntityEntry 22 }

cfprApMgmtEntityUmbilicalState OBJECT-TYPE
    SYNTAX       CfprApMgmtEntityUmbilicalState
    MAX-ACCESS   read-only
    STATUS       current
    DESCRIPTION
        "Cisco Firepower mgmt:Entity:umbilicalState managed
        object property"
    ::= { cfprApMgmtEntityEntry 23 }

cfprApMgmtEntityVersionMismatch OBJECT-TYPE
    SYNTAX       TruthValue
    MAX-ACCESS   read-only
    STATUS       current
    DESCRIPTION
        "Cisco Firepower mgmt:Entity:versionMismatch managed
        object property"
    ::= { cfprApMgmtEntityEntry 24 }

cfprApMgmtExportPolicyFsmTable OBJECT-TYPE
    SYNTAX           SEQUENCE OF CfprApMgmtExportPolicyFsmEntry
    MAX-ACCESS       not-accessible
    STATUS           current
    DESCRIPTION
        "Cisco Firepower mgmt:ExportPolicyFsm managed object table"
    ::= { cfprApMgmtObjects 23 }

cfprApMgmtExportPolicyFsmEntry OBJECT-TYPE
    SYNTAX           CfprApMgmtExportPolicyFsmEntry
    MAX-ACCESS       not-accessible
    STATUS           current
    DESCRIPTION
        "Entry for the cfprApMgmtExportPolicyFsmTable table."
    INDEX { cfprApMgmtExportPolicyFsmInstanceId }
    ::= { cfprApMgmtExportPolicyFsmTable 1 }

CfprApMgmtExportPolicyFsmEntry ::= SEQUENCE {
    cfprApMgmtExportPolicyFsmInstanceId                              CfprApManagedObjectId,
    cfprApMgmtExportPolicyFsmDn                                      CfprApManagedObjectDn,
    cfprApMgmtExportPolicyFsmRn                                      SnmpAdminString,
    cfprApMgmtExportPolicyFsmCompletionTime                          DateAndTime,
    cfprApMgmtExportPolicyFsmCurrentFsm                              CfprApMgmtExportPolicyFsmCurrentFsm,
    cfprApMgmtExportPolicyFsmDescr                                   SnmpAdminString,
    cfprApMgmtExportPolicyFsmFsmStatus                               CfprApFsmFsmStageStatus,
    cfprApMgmtExportPolicyFsmProgress                                Gauge32,
    cfprApMgmtExportPolicyFsmRmtErrCode                              Gauge32,
    cfprApMgmtExportPolicyFsmRmtErrDescr                             SnmpAdminString,
    cfprApMgmtExportPolicyFsmRmtRslt                                 CfprApConditionRemoteInvRslt
}

cfprApMgmtExportPolicyFsmInstanceId OBJECT-TYPE
    SYNTAX       CfprApManagedObjectId
    MAX-ACCESS   not-accessible
    STATUS       current
    DESCRIPTION
        "Instance identifier of the managed object."
    ::= { cfprApMgmtExportPolicyFsmEntry 1 }

cfprApMgmtExportPolicyFsmDn OBJECT-TYPE
    SYNTAX       CfprApManagedObjectDn
    MAX-ACCESS   read-only
    STATUS       current
    DESCRIPTION
        "Cisco Firepower mgmt:ExportPolicyFsm:dn managed object property"
    ::= { cfprApMgmtExportPolicyFsmEntry 2 }

cfprApMgmtExportPolicyFsmRn OBJECT-TYPE
    SYNTAX       SnmpAdminString
    MAX-ACCESS   read-only
    STATUS       current
    DESCRIPTION
        "Cisco Firepower mgmt:ExportPolicyFsm:rn managed object property"
    ::= { cfprApMgmtExportPolicyFsmEntry 3 }

cfprApMgmtExportPolicyFsmCompletionTime OBJECT-TYPE
    SYNTAX       DateAndTime
    MAX-ACCESS   read-only
    STATUS       current
    DESCRIPTION
        "Cisco Firepower mgmt:ExportPolicyFsm:completionTime
        managed object property"
    ::= { cfprApMgmtExportPolicyFsmEntry 4 }

cfprApMgmtExportPolicyFsmCurrentFsm OBJECT-TYPE
    SYNTAX       CfprApMgmtExportPolicyFsmCurrentFsm
    MAX-ACCESS   read-only
    STATUS       current
    DESCRIPTION
        "Cisco Firepower mgmt:ExportPolicyFsm:currentFsm
        managed object property"
    ::= { cfprApMgmtExportPolicyFsmEntry 5 }

cfprApMgmtExportPolicyFsmDescr OBJECT-TYPE
    SYNTAX       SnmpAdminString
    MAX-ACCESS   read-only
    STATUS       current
    DESCRIPTION
        "Cisco Firepower mgmt:ExportPolicyFsm:descr managed
        object property"
    ::= { cfprApMgmtExportPolicyFsmEntry 6 }

cfprApMgmtExportPolicyFsmFsmStatus OBJECT-TYPE
    SYNTAX       CfprApFsmFsmStageStatus
    MAX-ACCESS   read-only
    STATUS       current
    DESCRIPTION
        "Cisco Firepower mgmt:ExportPolicyFsm:fsmStatus
        managed object property"
    ::= { cfprApMgmtExportPolicyFsmEntry 7 }

cfprApMgmtExportPolicyFsmProgress OBJECT-TYPE
    SYNTAX       Gauge32
    MAX-ACCESS   read-only
    STATUS       current
    DESCRIPTION
        "Cisco Firepower mgmt:ExportPolicyFsm:progress
        managed object property"
    ::= { cfprApMgmtExportPolicyFsmEntry 8 }

cfprApMgmtExportPolicyFsmRmtErrCode OBJECT-TYPE
    SYNTAX       Gauge32
    MAX-ACCESS   read-only
    STATUS       current
    DESCRIPTION
        "Cisco Firepower mgmt:ExportPolicyFsm:rmtErrCode
        managed object property"
    ::= { cfprApMgmtExportPolicyFsmEntry 9 }

cfprApMgmtExportPolicyFsmRmtErrDescr OBJECT-TYPE
    SYNTAX       SnmpAdminString
    MAX-ACCESS   read-only
    STATUS       current
    DESCRIPTION
        "Cisco Firepower mgmt:ExportPolicyFsm:rmtErrDescr
        managed object property"
    ::= { cfprApMgmtExportPolicyFsmEntry 10 }

cfprApMgmtExportPolicyFsmRmtRslt OBJECT-TYPE
    SYNTAX       CfprApConditionRemoteInvRslt
    MAX-ACCESS   read-only
    STATUS       current
    DESCRIPTION
        "Cisco Firepower mgmt:ExportPolicyFsm:rmtRslt managed
        object property"
    ::= { cfprApMgmtExportPolicyFsmEntry 11 }

cfprApMgmtExportPolicyFsmStageTable OBJECT-TYPE
    SYNTAX           SEQUENCE OF CfprApMgmtExportPolicyFsmStageEntry
    MAX-ACCESS       not-accessible
    STATUS           current
    DESCRIPTION
        "Cisco Firepower mgmt:ExportPolicyFsmStage managed object table"
    ::= { cfprApMgmtObjects 24 }

cfprApMgmtExportPolicyFsmStageEntry OBJECT-TYPE
    SYNTAX           CfprApMgmtExportPolicyFsmStageEntry
    MAX-ACCESS       not-accessible
    STATUS           current
    DESCRIPTION
        "Entry for the cfprApMgmtExportPolicyFsmStageTable table."
    INDEX { cfprApMgmtExportPolicyFsmStageInstanceId }
    ::= { cfprApMgmtExportPolicyFsmStageTable 1 }

CfprApMgmtExportPolicyFsmStageEntry ::= SEQUENCE {
    cfprApMgmtExportPolicyFsmStageInstanceId                         CfprApManagedObjectId,
    cfprApMgmtExportPolicyFsmStageDn                                 CfprApManagedObjectDn,
    cfprApMgmtExportPolicyFsmStageRn                                 SnmpAdminString,
    cfprApMgmtExportPolicyFsmStageDescr                              SnmpAdminString,
    cfprApMgmtExportPolicyFsmStageLastUpdateTime                     DateAndTime,
    cfprApMgmtExportPolicyFsmStageName                               CfprApMgmtExportPolicyFsmStageName,
    cfprApMgmtExportPolicyFsmStageOrder                              Gauge32,
    cfprApMgmtExportPolicyFsmStageRetry                              Gauge32,
    cfprApMgmtExportPolicyFsmStageStageStatus                        CfprApFsmFsmStageStatus
}

cfprApMgmtExportPolicyFsmStageInstanceId OBJECT-TYPE
    SYNTAX       CfprApManagedObjectId
    MAX-ACCESS   not-accessible
    STATUS       current
    DESCRIPTION
        "Instance identifier of the managed object."
    ::= { cfprApMgmtExportPolicyFsmStageEntry 1 }

cfprApMgmtExportPolicyFsmStageDn OBJECT-TYPE
    SYNTAX       CfprApManagedObjectDn
    MAX-ACCESS   read-only
    STATUS       current
    DESCRIPTION
        "Cisco Firepower mgmt:ExportPolicyFsmStage:dn managed
        object property"
    ::= { cfprApMgmtExportPolicyFsmStageEntry 2 }

cfprApMgmtExportPolicyFsmStageRn OBJECT-TYPE
    SYNTAX       SnmpAdminString
    MAX-ACCESS   read-only
    STATUS       current
    DESCRIPTION
        "Cisco Firepower mgmt:ExportPolicyFsmStage:rn managed
        object property"
    ::= { cfprApMgmtExportPolicyFsmStageEntry 3 }

cfprApMgmtExportPolicyFsmStageDescr OBJECT-TYPE
    SYNTAX       SnmpAdminString
    MAX-ACCESS   read-only
    STATUS       current
    DESCRIPTION
        "Cisco Firepower mgmt:ExportPolicyFsmStage:descr
        managed object property"
    ::= { cfprApMgmtExportPolicyFsmStageEntry 4 }

cfprApMgmtExportPolicyFsmStageLastUpdateTime OBJECT-TYPE
    SYNTAX       DateAndTime
    MAX-ACCESS   read-only
    STATUS       current
    DESCRIPTION
        "Cisco Firepower mgmt:ExportPolicyFsmStage:lastUpdateTime
        managed object property"
    ::= { cfprApMgmtExportPolicyFsmStageEntry 5 }

cfprApMgmtExportPolicyFsmStageName OBJECT-TYPE
    SYNTAX       CfprApMgmtExportPolicyFsmStageName
    MAX-ACCESS   read-only
    STATUS       current
    DESCRIPTION
        "Cisco Firepower mgmt:ExportPolicyFsmStage:name
        managed object property"
    ::= { cfprApMgmtExportPolicyFsmStageEntry 6 }

cfprApMgmtExportPolicyFsmStageOrder OBJECT-TYPE
    SYNTAX       Gauge32
    MAX-ACCESS   read-only
    STATUS       current
    DESCRIPTION
        "Cisco Firepower mgmt:ExportPolicyFsmStage:order
        managed object property"
    ::= { cfprApMgmtExportPolicyFsmStageEntry 7 }

cfprApMgmtExportPolicyFsmStageRetry OBJECT-TYPE
    SYNTAX       Gauge32
    MAX-ACCESS   read-only
    STATUS       current
    DESCRIPTION
        "Cisco Firepower mgmt:ExportPolicyFsmStage:retry
        managed object property"
    ::= { cfprApMgmtExportPolicyFsmStageEntry 8 }

cfprApMgmtExportPolicyFsmStageStageStatus OBJECT-TYPE
    SYNTAX       CfprApFsmFsmStageStatus
    MAX-ACCESS   read-only
    STATUS       current
    DESCRIPTION
        "Cisco Firepower mgmt:ExportPolicyFsmStage:stageStatus
        managed object property"
    ::= { cfprApMgmtExportPolicyFsmStageEntry 9 }

cfprApMgmtExportPolicyFsmTaskTable OBJECT-TYPE
    SYNTAX           SEQUENCE OF CfprApMgmtExportPolicyFsmTaskEntry
    MAX-ACCESS       not-accessible
    STATUS           current
    DESCRIPTION
        "Cisco Firepower mgmt:ExportPolicyFsmTask managed object table"
    ::= { cfprApMgmtObjects 25 }

cfprApMgmtExportPolicyFsmTaskEntry OBJECT-TYPE
    SYNTAX           CfprApMgmtExportPolicyFsmTaskEntry
    MAX-ACCESS       not-accessible
    STATUS           current
    DESCRIPTION
        "Entry for the cfprApMgmtExportPolicyFsmTaskTable table."
    INDEX { cfprApMgmtExportPolicyFsmTaskInstanceId }
    ::= { cfprApMgmtExportPolicyFsmTaskTable 1 }

CfprApMgmtExportPolicyFsmTaskEntry ::= SEQUENCE {
    cfprApMgmtExportPolicyFsmTaskInstanceId                          CfprApManagedObjectId,
    cfprApMgmtExportPolicyFsmTaskDn                                  CfprApManagedObjectDn,
    cfprApMgmtExportPolicyFsmTaskRn                                  SnmpAdminString,
    cfprApMgmtExportPolicyFsmTaskCompletion                          CfprApFsmCompletion,
    cfprApMgmtExportPolicyFsmTaskFlags                               CfprApFsmFlags,
    cfprApMgmtExportPolicyFsmTaskItem                                CfprApMgmtExportPolicyFsmTaskItem,
    cfprApMgmtExportPolicyFsmTaskSeqId                               Gauge32
}

cfprApMgmtExportPolicyFsmTaskInstanceId OBJECT-TYPE
    SYNTAX       CfprApManagedObjectId
    MAX-ACCESS   not-accessible
    STATUS       current
    DESCRIPTION
        "Instance identifier of the managed object."
    ::= { cfprApMgmtExportPolicyFsmTaskEntry 1 }

cfprApMgmtExportPolicyFsmTaskDn OBJECT-TYPE
    SYNTAX       CfprApManagedObjectDn
    MAX-ACCESS   read-only
    STATUS       current
    DESCRIPTION
        "Cisco Firepower mgmt:ExportPolicyFsmTask:dn managed
        object property"
    ::= { cfprApMgmtExportPolicyFsmTaskEntry 2 }

cfprApMgmtExportPolicyFsmTaskRn OBJECT-TYPE
    SYNTAX       SnmpAdminString
    MAX-ACCESS   read-only
    STATUS       current
    DESCRIPTION
        "Cisco Firepower mgmt:ExportPolicyFsmTask:rn managed
        object property"
    ::= { cfprApMgmtExportPolicyFsmTaskEntry 3 }

cfprApMgmtExportPolicyFsmTaskCompletion OBJECT-TYPE
    SYNTAX       CfprApFsmCompletion
    MAX-ACCESS   read-only
    STATUS       current
    DESCRIPTION
        "Cisco Firepower mgmt:ExportPolicyFsmTask:completion
        managed object property"
    ::= { cfprApMgmtExportPolicyFsmTaskEntry 4 }

cfprApMgmtExportPolicyFsmTaskFlags OBJECT-TYPE
    SYNTAX       CfprApFsmFlags
    MAX-ACCESS   read-only
    STATUS       current
    DESCRIPTION
        "Cisco Firepower mgmt:ExportPolicyFsmTask:flags
        managed object property"
    ::= { cfprApMgmtExportPolicyFsmTaskEntry 5 }

cfprApMgmtExportPolicyFsmTaskItem OBJECT-TYPE
    SYNTAX       CfprApMgmtExportPolicyFsmTaskItem
    MAX-ACCESS   read-only
    STATUS       current
    DESCRIPTION
        "Cisco Firepower mgmt:ExportPolicyFsmTask:item
        managed object property"
    ::= { cfprApMgmtExportPolicyFsmTaskEntry 6 }

cfprApMgmtExportPolicyFsmTaskSeqId OBJECT-TYPE
    SYNTAX       Gauge32
    MAX-ACCESS   read-only
    STATUS       current
    DESCRIPTION
        "Cisco Firepower mgmt:ExportPolicyFsmTask:seqId
        managed object property"
    ::= { cfprApMgmtExportPolicyFsmTaskEntry 7 }

cfprApMgmtIPv6IfAddrTable OBJECT-TYPE
    SYNTAX           SEQUENCE OF CfprApMgmtIPv6IfAddrEntry
    MAX-ACCESS       not-accessible
    STATUS           current
    DESCRIPTION
        "Cisco Firepower mgmt:IPv6IfAddr managed object table"
    ::= { cfprApMgmtObjects 26 }

cfprApMgmtIPv6IfAddrEntry OBJECT-TYPE
    SYNTAX           CfprApMgmtIPv6IfAddrEntry
    MAX-ACCESS       not-accessible
    STATUS           current
    DESCRIPTION
        "Entry for the cfprApMgmtIPv6IfAddrTable table."
    INDEX { cfprApMgmtIPv6IfAddrInstanceId }
    ::= { cfprApMgmtIPv6IfAddrTable 1 }

CfprApMgmtIPv6IfAddrEntry ::= SEQUENCE {
    cfprApMgmtIPv6IfAddrInstanceId                                   CfprApManagedObjectId,
    cfprApMgmtIPv6IfAddrDn                                           CfprApManagedObjectDn,
    cfprApMgmtIPv6IfAddrRn                                           SnmpAdminString,
    cfprApMgmtIPv6IfAddrAddr                                         InetAddressIPv6,
    cfprApMgmtIPv6IfAddrDefGw                                        InetAddressIPv6,
    cfprApMgmtIPv6IfAddrFsmDescr                                     SnmpAdminString,
    cfprApMgmtIPv6IfAddrFsmPrev                                      SnmpAdminString,
    cfprApMgmtIPv6IfAddrFsmProgr                                     Gauge32,
    cfprApMgmtIPv6IfAddrFsmRmtInvErrCode                             Gauge32,
    cfprApMgmtIPv6IfAddrFsmRmtInvErrDescr                            SnmpAdminString,
    cfprApMgmtIPv6IfAddrFsmRmtInvRslt                                CfprApConditionRemoteInvRslt,
    cfprApMgmtIPv6IfAddrFsmStageDescr                                SnmpAdminString,
    cfprApMgmtIPv6IfAddrFsmStamp                                     DateAndTime,
    cfprApMgmtIPv6IfAddrFsmStatus                                    SnmpAdminString,
    cfprApMgmtIPv6IfAddrFsmTry                                       Gauge32,
    cfprApMgmtIPv6IfAddrPrefix                                       Gauge32
}

cfprApMgmtIPv6IfAddrInstanceId OBJECT-TYPE
    SYNTAX       CfprApManagedObjectId
    MAX-ACCESS   not-accessible
    STATUS       current
    DESCRIPTION
        "Instance identifier of the managed object."
    ::= { cfprApMgmtIPv6IfAddrEntry 1 }

cfprApMgmtIPv6IfAddrDn OBJECT-TYPE
    SYNTAX       CfprApManagedObjectDn
    MAX-ACCESS   read-only
    STATUS       current
    DESCRIPTION
        "Cisco Firepower mgmt:IPv6IfAddr:dn managed object property"
    ::= { cfprApMgmtIPv6IfAddrEntry 2 }

cfprApMgmtIPv6IfAddrRn OBJECT-TYPE
    SYNTAX       SnmpAdminString
    MAX-ACCESS   read-only
    STATUS       current
    DESCRIPTION
        "Cisco Firepower mgmt:IPv6IfAddr:rn managed object property"
    ::= { cfprApMgmtIPv6IfAddrEntry 3 }

cfprApMgmtIPv6IfAddrAddr OBJECT-TYPE
    SYNTAX       InetAddressIPv6
    MAX-ACCESS   read-only
    STATUS       current
    DESCRIPTION
        "Cisco Firepower mgmt:IPv6IfAddr:addr managed object property"
    ::= { cfprApMgmtIPv6IfAddrEntry 4 }

cfprApMgmtIPv6IfAddrDefGw OBJECT-TYPE
    SYNTAX       InetAddressIPv6
    MAX-ACCESS   read-only
    STATUS       current
    DESCRIPTION
        "Cisco Firepower mgmt:IPv6IfAddr:defGw managed object property"
    ::= { cfprApMgmtIPv6IfAddrEntry 5 }

cfprApMgmtIPv6IfAddrFsmDescr OBJECT-TYPE
    SYNTAX       SnmpAdminString
    MAX-ACCESS   read-only
    STATUS       current
    DESCRIPTION
        "Cisco Firepower mgmt:IPv6IfAddr:fsmDescr managed object property"
    ::= { cfprApMgmtIPv6IfAddrEntry 6 }

cfprApMgmtIPv6IfAddrFsmPrev OBJECT-TYPE
    SYNTAX       SnmpAdminString
    MAX-ACCESS   read-only
    STATUS       current
    DESCRIPTION
        "Cisco Firepower mgmt:IPv6IfAddr:fsmPrev managed object property"
    ::= { cfprApMgmtIPv6IfAddrEntry 7 }

cfprApMgmtIPv6IfAddrFsmProgr OBJECT-TYPE
    SYNTAX       Gauge32
    MAX-ACCESS   read-only
    STATUS       current
    DESCRIPTION
        "Cisco Firepower mgmt:IPv6IfAddr:fsmProgr managed object property"
    ::= { cfprApMgmtIPv6IfAddrEntry 8 }

cfprApMgmtIPv6IfAddrFsmRmtInvErrCode OBJECT-TYPE
    SYNTAX       Gauge32
    MAX-ACCESS   read-only
    STATUS       current
    DESCRIPTION
        "Cisco Firepower mgmt:IPv6IfAddr:fsmRmtInvErrCode
        managed object property"
    ::= { cfprApMgmtIPv6IfAddrEntry 9 }

cfprApMgmtIPv6IfAddrFsmRmtInvErrDescr OBJECT-TYPE
    SYNTAX       SnmpAdminString
    MAX-ACCESS   read-only
    STATUS       current
    DESCRIPTION
        "Cisco Firepower mgmt:IPv6IfAddr:fsmRmtInvErrDescr
        managed object property"
    ::= { cfprApMgmtIPv6IfAddrEntry 10 }

cfprApMgmtIPv6IfAddrFsmRmtInvRslt OBJECT-TYPE
    SYNTAX       CfprApConditionRemoteInvRslt
    MAX-ACCESS   read-only
    STATUS       current
    DESCRIPTION
        "Cisco Firepower mgmt:IPv6IfAddr:fsmRmtInvRslt
        managed object property"
    ::= { cfprApMgmtIPv6IfAddrEntry 11 }

cfprApMgmtIPv6IfAddrFsmStageDescr OBJECT-TYPE
    SYNTAX       SnmpAdminString
    MAX-ACCESS   read-only
    STATUS       current
    DESCRIPTION
        "Cisco Firepower mgmt:IPv6IfAddr:fsmStageDescr
        managed object property"
    ::= { cfprApMgmtIPv6IfAddrEntry 12 }

cfprApMgmtIPv6IfAddrFsmStamp OBJECT-TYPE
    SYNTAX       DateAndTime
    MAX-ACCESS   read-only
    STATUS       current
    DESCRIPTION
        "Cisco Firepower mgmt:IPv6IfAddr:fsmStamp managed object property"
    ::= { cfprApMgmtIPv6IfAddrEntry 13 }

cfprApMgmtIPv6IfAddrFsmStatus OBJECT-TYPE
    SYNTAX       SnmpAdminString
    MAX-ACCESS   read-only
    STATUS       current
    DESCRIPTION
        "Cisco Firepower mgmt:IPv6IfAddr:fsmStatus managed
        object property"
    ::= { cfprApMgmtIPv6IfAddrEntry 14 }

cfprApMgmtIPv6IfAddrFsmTry OBJECT-TYPE
    SYNTAX       Gauge32
    MAX-ACCESS   read-only
    STATUS       current
    DESCRIPTION
        "Cisco Firepower mgmt:IPv6IfAddr:fsmTry managed object property"
    ::= { cfprApMgmtIPv6IfAddrEntry 15 }

cfprApMgmtIPv6IfAddrPrefix OBJECT-TYPE
    SYNTAX       Gauge32
    MAX-ACCESS   read-only
    STATUS       current
    DESCRIPTION
        "Cisco Firepower mgmt:IPv6IfAddr:prefix managed object property"
    ::= { cfprApMgmtIPv6IfAddrEntry 16 }

cfprApMgmtIPv6IfAddrFsmTable OBJECT-TYPE
    SYNTAX           SEQUENCE OF CfprApMgmtIPv6IfAddrFsmEntry
    MAX-ACCESS       not-accessible
    STATUS           current
    DESCRIPTION
        "Cisco Firepower mgmt:IPv6IfAddrFsm managed object table"
    ::= { cfprApMgmtObjects 27 }

cfprApMgmtIPv6IfAddrFsmEntry OBJECT-TYPE
    SYNTAX           CfprApMgmtIPv6IfAddrFsmEntry
    MAX-ACCESS       not-accessible
    STATUS           current
    DESCRIPTION
        "Entry for the cfprApMgmtIPv6IfAddrFsmTable table."
    INDEX { cfprApMgmtIPv6IfAddrFsmInstanceId }
    ::= { cfprApMgmtIPv6IfAddrFsmTable 1 }

CfprApMgmtIPv6IfAddrFsmEntry ::= SEQUENCE {
    cfprApMgmtIPv6IfAddrFsmInstanceId                                CfprApManagedObjectId,
    cfprApMgmtIPv6IfAddrFsmDn                                        CfprApManagedObjectDn,
    cfprApMgmtIPv6IfAddrFsmRn                                        SnmpAdminString,
    cfprApMgmtIPv6IfAddrFsmCompletionTime                            DateAndTime,
    cfprApMgmtIPv6IfAddrFsmCurrentFsm                                CfprApMgmtIPv6IfAddrFsmCurrentFsm,
    cfprApMgmtIPv6IfAddrFsmDescrData                                 SnmpAdminString,
    cfprApMgmtIPv6IfAddrFsmFsmStatus                                 CfprApFsmFsmStageStatus,
    cfprApMgmtIPv6IfAddrFsmProgress                                  Gauge32,
    cfprApMgmtIPv6IfAddrFsmRmtErrCode                                Gauge32,
    cfprApMgmtIPv6IfAddrFsmRmtErrDescr                               SnmpAdminString,
    cfprApMgmtIPv6IfAddrFsmRmtRslt                                   CfprApConditionRemoteInvRslt
}

cfprApMgmtIPv6IfAddrFsmInstanceId OBJECT-TYPE
    SYNTAX       CfprApManagedObjectId
    MAX-ACCESS   not-accessible
    STATUS       current
    DESCRIPTION
        "Instance identifier of the managed object."
    ::= { cfprApMgmtIPv6IfAddrFsmEntry 1 }

cfprApMgmtIPv6IfAddrFsmDn OBJECT-TYPE
    SYNTAX       CfprApManagedObjectDn
    MAX-ACCESS   read-only
    STATUS       current
    DESCRIPTION
        "Cisco Firepower mgmt:IPv6IfAddrFsm:dn managed object property"
    ::= { cfprApMgmtIPv6IfAddrFsmEntry 2 }

cfprApMgmtIPv6IfAddrFsmRn OBJECT-TYPE
    SYNTAX       SnmpAdminString
    MAX-ACCESS   read-only
    STATUS       current
    DESCRIPTION
        "Cisco Firepower mgmt:IPv6IfAddrFsm:rn managed object property"
    ::= { cfprApMgmtIPv6IfAddrFsmEntry 3 }

cfprApMgmtIPv6IfAddrFsmCompletionTime OBJECT-TYPE
    SYNTAX       DateAndTime
    MAX-ACCESS   read-only
    STATUS       current
    DESCRIPTION
        "Cisco Firepower mgmt:IPv6IfAddrFsm:completionTime
        managed object property"
    ::= { cfprApMgmtIPv6IfAddrFsmEntry 4 }

cfprApMgmtIPv6IfAddrFsmCurrentFsm OBJECT-TYPE
    SYNTAX       CfprApMgmtIPv6IfAddrFsmCurrentFsm
    MAX-ACCESS   read-only
    STATUS       current
    DESCRIPTION
        "Cisco Firepower mgmt:IPv6IfAddrFsm:currentFsm
        managed object property"
    ::= { cfprApMgmtIPv6IfAddrFsmEntry 5 }

cfprApMgmtIPv6IfAddrFsmDescrData OBJECT-TYPE
    SYNTAX       SnmpAdminString
    MAX-ACCESS   read-only
    STATUS       current
    DESCRIPTION
        "Cisco Firepower mgmt:IPv6IfAddrFsm:descr managed object property"
    ::= { cfprApMgmtIPv6IfAddrFsmEntry 6 }

cfprApMgmtIPv6IfAddrFsmFsmStatus OBJECT-TYPE
    SYNTAX       CfprApFsmFsmStageStatus
    MAX-ACCESS   read-only
    STATUS       current
    DESCRIPTION
        "Cisco Firepower mgmt:IPv6IfAddrFsm:fsmStatus managed
        object property"
    ::= { cfprApMgmtIPv6IfAddrFsmEntry 7 }

cfprApMgmtIPv6IfAddrFsmProgress OBJECT-TYPE
    SYNTAX       Gauge32
    MAX-ACCESS   read-only
    STATUS       current
    DESCRIPTION
        "Cisco Firepower mgmt:IPv6IfAddrFsm:progress managed
        object property"
    ::= { cfprApMgmtIPv6IfAddrFsmEntry 8 }

cfprApMgmtIPv6IfAddrFsmRmtErrCode OBJECT-TYPE
    SYNTAX       Gauge32
    MAX-ACCESS   read-only
    STATUS       current
    DESCRIPTION
        "Cisco Firepower mgmt:IPv6IfAddrFsm:rmtErrCode
        managed object property"
    ::= { cfprApMgmtIPv6IfAddrFsmEntry 9 }

cfprApMgmtIPv6IfAddrFsmRmtErrDescr OBJECT-TYPE
    SYNTAX       SnmpAdminString
    MAX-ACCESS   read-only
    STATUS       current
    DESCRIPTION
        "Cisco Firepower mgmt:IPv6IfAddrFsm:rmtErrDescr
        managed object property"
    ::= { cfprApMgmtIPv6IfAddrFsmEntry 10 }

cfprApMgmtIPv6IfAddrFsmRmtRslt OBJECT-TYPE
    SYNTAX       CfprApConditionRemoteInvRslt
    MAX-ACCESS   read-only
    STATUS       current
    DESCRIPTION
        "Cisco Firepower mgmt:IPv6IfAddrFsm:rmtRslt managed
        object property"
    ::= { cfprApMgmtIPv6IfAddrFsmEntry 11 }

cfprApMgmtIPv6IfAddrFsmStageTable OBJECT-TYPE
    SYNTAX           SEQUENCE OF CfprApMgmtIPv6IfAddrFsmStageEntry
    MAX-ACCESS       not-accessible
    STATUS           current
    DESCRIPTION
        "Cisco Firepower mgmt:IPv6IfAddrFsmStage managed object table"
    ::= { cfprApMgmtObjects 28 }

cfprApMgmtIPv6IfAddrFsmStageEntry OBJECT-TYPE
    SYNTAX           CfprApMgmtIPv6IfAddrFsmStageEntry
    MAX-ACCESS       not-accessible
    STATUS           current
    DESCRIPTION
        "Entry for the cfprApMgmtIPv6IfAddrFsmStageTable table."
    INDEX { cfprApMgmtIPv6IfAddrFsmStageInstanceId }
    ::= { cfprApMgmtIPv6IfAddrFsmStageTable 1 }

CfprApMgmtIPv6IfAddrFsmStageEntry ::= SEQUENCE {
    cfprApMgmtIPv6IfAddrFsmStageInstanceId                           CfprApManagedObjectId,
    cfprApMgmtIPv6IfAddrFsmStageDn                                   CfprApManagedObjectDn,
    cfprApMgmtIPv6IfAddrFsmStageRn                                   SnmpAdminString,
    cfprApMgmtIPv6IfAddrFsmStageDescrData                            SnmpAdminString,
    cfprApMgmtIPv6IfAddrFsmStageLastUpdateTime                       DateAndTime,
    cfprApMgmtIPv6IfAddrFsmStageName                                 CfprApMgmtIPv6IfAddrFsmStageName,
    cfprApMgmtIPv6IfAddrFsmStageOrder                                Gauge32,
    cfprApMgmtIPv6IfAddrFsmStageRetry                                Gauge32,
    cfprApMgmtIPv6IfAddrFsmStageStageStatus                          CfprApFsmFsmStageStatus
}

cfprApMgmtIPv6IfAddrFsmStageInstanceId OBJECT-TYPE
    SYNTAX       CfprApManagedObjectId
    MAX-ACCESS   not-accessible
    STATUS       current
    DESCRIPTION
        "Instance identifier of the managed object."
    ::= { cfprApMgmtIPv6IfAddrFsmStageEntry 1 }

cfprApMgmtIPv6IfAddrFsmStageDn OBJECT-TYPE
    SYNTAX       CfprApManagedObjectDn
    MAX-ACCESS   read-only
    STATUS       current
    DESCRIPTION
        "Cisco Firepower mgmt:IPv6IfAddrFsmStage:dn managed
        object property"
    ::= { cfprApMgmtIPv6IfAddrFsmStageEntry 2 }

cfprApMgmtIPv6IfAddrFsmStageRn OBJECT-TYPE
    SYNTAX       SnmpAdminString
    MAX-ACCESS   read-only
    STATUS       current
    DESCRIPTION
        "Cisco Firepower mgmt:IPv6IfAddrFsmStage:rn managed
        object property"
    ::= { cfprApMgmtIPv6IfAddrFsmStageEntry 3 }

cfprApMgmtIPv6IfAddrFsmStageDescrData OBJECT-TYPE
    SYNTAX       SnmpAdminString
    MAX-ACCESS   read-only
    STATUS       current
    DESCRIPTION
        "Cisco Firepower mgmt:IPv6IfAddrFsmStage:descr
        managed object property"
    ::= { cfprApMgmtIPv6IfAddrFsmStageEntry 4 }

cfprApMgmtIPv6IfAddrFsmStageLastUpdateTime OBJECT-TYPE
    SYNTAX       DateAndTime
    MAX-ACCESS   read-only
    STATUS       current
    DESCRIPTION
        "Cisco Firepower mgmt:IPv6IfAddrFsmStage:lastUpdateTime
        managed object property"
    ::= { cfprApMgmtIPv6IfAddrFsmStageEntry 5 }

cfprApMgmtIPv6IfAddrFsmStageName OBJECT-TYPE
    SYNTAX       CfprApMgmtIPv6IfAddrFsmStageName
    MAX-ACCESS   read-only
    STATUS       current
    DESCRIPTION
        "Cisco Firepower mgmt:IPv6IfAddrFsmStage:name managed
        object property"
    ::= { cfprApMgmtIPv6IfAddrFsmStageEntry 6 }

cfprApMgmtIPv6IfAddrFsmStageOrder OBJECT-TYPE
    SYNTAX       Gauge32
    MAX-ACCESS   read-only
    STATUS       current
    DESCRIPTION
        "Cisco Firepower mgmt:IPv6IfAddrFsmStage:order
        managed object property"
    ::= { cfprApMgmtIPv6IfAddrFsmStageEntry 7 }

cfprApMgmtIPv6IfAddrFsmStageRetry OBJECT-TYPE
    SYNTAX       Gauge32
    MAX-ACCESS   read-only
    STATUS       current
    DESCRIPTION
        "Cisco Firepower mgmt:IPv6IfAddrFsmStage:retry
        managed object property"
    ::= { cfprApMgmtIPv6IfAddrFsmStageEntry 8 }

cfprApMgmtIPv6IfAddrFsmStageStageStatus OBJECT-TYPE
    SYNTAX       CfprApFsmFsmStageStatus
    MAX-ACCESS   read-only
    STATUS       current
    DESCRIPTION
        "Cisco Firepower mgmt:IPv6IfAddrFsmStage:stageStatus
        managed object property"
    ::= { cfprApMgmtIPv6IfAddrFsmStageEntry 9 }

cfprApMgmtIPv6IfAddrFsmTaskTable OBJECT-TYPE
    SYNTAX           SEQUENCE OF CfprApMgmtIPv6IfAddrFsmTaskEntry
    MAX-ACCESS       not-accessible
    STATUS           current
    DESCRIPTION
        "Cisco Firepower mgmt:IPv6IfAddrFsmTask managed object table"
    ::= { cfprApMgmtObjects 29 }

cfprApMgmtIPv6IfAddrFsmTaskEntry OBJECT-TYPE
    SYNTAX           CfprApMgmtIPv6IfAddrFsmTaskEntry
    MAX-ACCESS       not-accessible
    STATUS           current
    DESCRIPTION
        "Entry for the cfprApMgmtIPv6IfAddrFsmTaskTable table."
    INDEX { cfprApMgmtIPv6IfAddrFsmTaskInstanceId }
    ::= { cfprApMgmtIPv6IfAddrFsmTaskTable 1 }

CfprApMgmtIPv6IfAddrFsmTaskEntry ::= SEQUENCE {
    cfprApMgmtIPv6IfAddrFsmTaskInstanceId                            CfprApManagedObjectId,
    cfprApMgmtIPv6IfAddrFsmTaskDn                                    CfprApManagedObjectDn,
    cfprApMgmtIPv6IfAddrFsmTaskRn                                    SnmpAdminString,
    cfprApMgmtIPv6IfAddrFsmTaskCompletion                            CfprApFsmCompletion,
    cfprApMgmtIPv6IfAddrFsmTaskFlags                                 CfprApFsmFlags,
    cfprApMgmtIPv6IfAddrFsmTaskItem                                  CfprApMgmtIPv6IfAddrFsmTaskItem,
    cfprApMgmtIPv6IfAddrFsmTaskSeqId                                 Gauge32
}

cfprApMgmtIPv6IfAddrFsmTaskInstanceId OBJECT-TYPE
    SYNTAX       CfprApManagedObjectId
    MAX-ACCESS   not-accessible
    STATUS       current
    DESCRIPTION
        "Instance identifier of the managed object."
    ::= { cfprApMgmtIPv6IfAddrFsmTaskEntry 1 }

cfprApMgmtIPv6IfAddrFsmTaskDn OBJECT-TYPE
    SYNTAX       CfprApManagedObjectDn
    MAX-ACCESS   read-only
    STATUS       current
    DESCRIPTION
        "Cisco Firepower mgmt:IPv6IfAddrFsmTask:dn managed
        object property"
    ::= { cfprApMgmtIPv6IfAddrFsmTaskEntry 2 }

cfprApMgmtIPv6IfAddrFsmTaskRn OBJECT-TYPE
    SYNTAX       SnmpAdminString
    MAX-ACCESS   read-only
    STATUS       current
    DESCRIPTION
        "Cisco Firepower mgmt:IPv6IfAddrFsmTask:rn managed
        object property"
    ::= { cfprApMgmtIPv6IfAddrFsmTaskEntry 3 }

cfprApMgmtIPv6IfAddrFsmTaskCompletion OBJECT-TYPE
    SYNTAX       CfprApFsmCompletion
    MAX-ACCESS   read-only
    STATUS       current
    DESCRIPTION
        "Cisco Firepower mgmt:IPv6IfAddrFsmTask:completion
        managed object property"
    ::= { cfprApMgmtIPv6IfAddrFsmTaskEntry 4 }

cfprApMgmtIPv6IfAddrFsmTaskFlags OBJECT-TYPE
    SYNTAX       CfprApFsmFlags
    MAX-ACCESS   read-only
    STATUS       current
    DESCRIPTION
        "Cisco Firepower mgmt:IPv6IfAddrFsmTask:flags managed
        object property"
    ::= { cfprApMgmtIPv6IfAddrFsmTaskEntry 5 }

cfprApMgmtIPv6IfAddrFsmTaskItem OBJECT-TYPE
    SYNTAX       CfprApMgmtIPv6IfAddrFsmTaskItem
    MAX-ACCESS   read-only
    STATUS       current
    DESCRIPTION
        "Cisco Firepower mgmt:IPv6IfAddrFsmTask:item managed
        object property"
    ::= { cfprApMgmtIPv6IfAddrFsmTaskEntry 6 }

cfprApMgmtIPv6IfAddrFsmTaskSeqId OBJECT-TYPE
    SYNTAX       Gauge32
    MAX-ACCESS   read-only
    STATUS       current
    DESCRIPTION
        "Cisco Firepower mgmt:IPv6IfAddrFsmTask:seqId managed
        object property"
    ::= { cfprApMgmtIPv6IfAddrFsmTaskEntry 7 }

cfprApMgmtIPv6IfConfigTable OBJECT-TYPE
    SYNTAX           SEQUENCE OF CfprApMgmtIPv6IfConfigEntry
    MAX-ACCESS       not-accessible
    STATUS           current
    DESCRIPTION
        "Cisco Firepower mgmt:IPv6IfConfig managed object table"
    ::= { cfprApMgmtObjects 30 }

cfprApMgmtIPv6IfConfigEntry OBJECT-TYPE
    SYNTAX           CfprApMgmtIPv6IfConfigEntry
    MAX-ACCESS       not-accessible
    STATUS           current
    DESCRIPTION
        "Entry for the cfprApMgmtIPv6IfConfigTable table."
    INDEX { cfprApMgmtIPv6IfConfigInstanceId }
    ::= { cfprApMgmtIPv6IfConfigTable 1 }

CfprApMgmtIPv6IfConfigEntry ::= SEQUENCE {
    cfprApMgmtIPv6IfConfigInstanceId                                 CfprApManagedObjectId,
    cfprApMgmtIPv6IfConfigDn                                         CfprApManagedObjectDn,
    cfprApMgmtIPv6IfConfigRn                                         SnmpAdminString
}

cfprApMgmtIPv6IfConfigInstanceId OBJECT-TYPE
    SYNTAX       CfprApManagedObjectId
    MAX-ACCESS   not-accessible
    STATUS       current
    DESCRIPTION
        "Instance identifier of the managed object."
    ::= { cfprApMgmtIPv6IfConfigEntry 1 }

cfprApMgmtIPv6IfConfigDn OBJECT-TYPE
    SYNTAX       CfprApManagedObjectDn
    MAX-ACCESS   read-only
    STATUS       current
    DESCRIPTION
        "Cisco Firepower mgmt:IPv6IfConfig:dn managed object property"
    ::= { cfprApMgmtIPv6IfConfigEntry 2 }

cfprApMgmtIPv6IfConfigRn OBJECT-TYPE
    SYNTAX       SnmpAdminString
    MAX-ACCESS   read-only
    STATUS       current
    DESCRIPTION
        "Cisco Firepower mgmt:IPv6IfConfig:rn managed object property"
    ::= { cfprApMgmtIPv6IfConfigEntry 3 }

cfprApMgmtIfTable OBJECT-TYPE
    SYNTAX           SEQUENCE OF CfprApMgmtIfEntry
    MAX-ACCESS       not-accessible
    STATUS           current
    DESCRIPTION
        "Cisco Firepower mgmt:If managed object table"
    ::= { cfprApMgmtObjects 31 }

cfprApMgmtIfEntry OBJECT-TYPE
    SYNTAX           CfprApMgmtIfEntry
    MAX-ACCESS       not-accessible
    STATUS           current
    DESCRIPTION
        "Entry for the cfprApMgmtIfTable table."
    INDEX { cfprApMgmtIfInstanceId }
    ::= { cfprApMgmtIfTable 1 }

CfprApMgmtIfEntry ::= SEQUENCE {
    cfprApMgmtIfInstanceId                                           CfprApManagedObjectId,
    cfprApMgmtIfDn                                                   CfprApManagedObjectDn,
    cfprApMgmtIfRn                                                   SnmpAdminString,
    cfprApMgmtIfAccess                                               CfprApMgmtAccess,
    cfprApMgmtIfAdminState                                           CfprApMgmtAdminState,
    cfprApMgmtIfAggrPortId                                           Gauge32,
    cfprApMgmtIfChassisId                                            Gauge32,
    cfprApMgmtIfDiscovery                                            CfprApEtherSatelliteConnectionDisc,
    cfprApMgmtIfEpDn                                                 SnmpAdminString,
    cfprApMgmtIfExtBroadcast                                         InetAddressIPv4,
    cfprApMgmtIfExtGw                                                InetAddressIPv4,
    cfprApMgmtIfExtIp                                                InetAddressIPv4,
    cfprApMgmtIfExtMask                                              InetAddressIPv4,
    cfprApMgmtIfFsmDescr                                             SnmpAdminString,
    cfprApMgmtIfFsmPrev                                              SnmpAdminString,
    cfprApMgmtIfFsmProgr                                             Gauge32,
    cfprApMgmtIfFsmRmtInvErrCode                                     Gauge32,
    cfprApMgmtIfFsmRmtInvErrDescr                                    SnmpAdminString,
    cfprApMgmtIfFsmRmtInvRslt                                        CfprApConditionRemoteInvRslt,
    cfprApMgmtIfFsmStageDescr                                        SnmpAdminString,
    cfprApMgmtIfFsmStamp                                             DateAndTime,
    cfprApMgmtIfFsmStatus                                            SnmpAdminString,
    cfprApMgmtIfFsmTry                                               Gauge32,
    cfprApMgmtIfId                                                   Gauge32,
    cfprApMgmtIfIfRole                                               CfprApNetworkPortRole,
    cfprApMgmtIfIfType                                               CfprApNetworkPhysEpIfType,
    cfprApMgmtIfIp                                                   InetAddressIPv4,
    cfprApMgmtIfLocale                                               CfprApNetworkLocale,
    cfprApMgmtIfMac                                                  MacAddress,
    cfprApMgmtIfMask                                                 InetAddressIPv4,
    cfprApMgmtIfName                                                 SnmpAdminString,
    cfprApMgmtIfPeerAggrPortId                                       Gauge32,
    cfprApMgmtIfPeerChassisId                                        Gauge32,
    cfprApMgmtIfPeerDn                                               SnmpAdminString,
    cfprApMgmtIfPeerPortId                                           Gauge32,
    cfprApMgmtIfPeerSlotId                                           Gauge32,
    cfprApMgmtIfPortId                                               Gauge32,
    cfprApMgmtIfSlotId                                               Gauge32,
    cfprApMgmtIfStateQual                                            CfprApMgmtStateQual,
    cfprApMgmtIfSubject                                              CfprApMgmtSubject,
    cfprApMgmtIfSwitchId                                             CfprApNetworkSwitchId,
    cfprApMgmtIfTransport                                            CfprApNetworkTransport,
    cfprApMgmtIfType                                                 CfprApNetworkConnectionType,
    cfprApMgmtIfVnet                                                 Gauge32
}

cfprApMgmtIfInstanceId OBJECT-TYPE
    SYNTAX       CfprApManagedObjectId
    MAX-ACCESS   not-accessible
    STATUS       current
    DESCRIPTION
        "Instance identifier of the managed object."
    ::= { cfprApMgmtIfEntry 1 }

cfprApMgmtIfDn OBJECT-TYPE
    SYNTAX       CfprApManagedObjectDn
    MAX-ACCESS   read-only
    STATUS       current
    DESCRIPTION
        "Cisco Firepower mgmt:If:dn managed object property"
    ::= { cfprApMgmtIfEntry 2 }

cfprApMgmtIfRn OBJECT-TYPE
    SYNTAX       SnmpAdminString
    MAX-ACCESS   read-only
    STATUS       current
    DESCRIPTION
        "Cisco Firepower mgmt:If:rn managed object property"
    ::= { cfprApMgmtIfEntry 3 }

cfprApMgmtIfAccess OBJECT-TYPE
    SYNTAX       CfprApMgmtAccess
    MAX-ACCESS   read-only
    STATUS       current
    DESCRIPTION
        "Cisco Firepower mgmt:If:access managed object property"
    ::= { cfprApMgmtIfEntry 4 }

cfprApMgmtIfAdminState OBJECT-TYPE
    SYNTAX       CfprApMgmtAdminState
    MAX-ACCESS   read-only
    STATUS       current
    DESCRIPTION
        "Cisco Firepower mgmt:If:adminState managed object property"
    ::= { cfprApMgmtIfEntry 5 }

cfprApMgmtIfAggrPortId OBJECT-TYPE
    SYNTAX       Gauge32
    MAX-ACCESS   read-only
    STATUS       current
    DESCRIPTION
        "Cisco Firepower mgmt:If:aggrPortId managed object property"
    ::= { cfprApMgmtIfEntry 6 }

cfprApMgmtIfChassisId OBJECT-TYPE
    SYNTAX       Gauge32
    MAX-ACCESS   read-only
    STATUS       current
    DESCRIPTION
        "Cisco Firepower mgmt:If:chassisId managed object property"
    ::= { cfprApMgmtIfEntry 7 }

cfprApMgmtIfDiscovery OBJECT-TYPE
    SYNTAX       CfprApEtherSatelliteConnectionDisc
    MAX-ACCESS   read-only
    STATUS       current
    DESCRIPTION
        "Cisco Firepower mgmt:If:discovery managed object property"
    ::= { cfprApMgmtIfEntry 8 }

cfprApMgmtIfEpDn OBJECT-TYPE
    SYNTAX       SnmpAdminString
    MAX-ACCESS   read-only
    STATUS       current
    DESCRIPTION
        "Cisco Firepower mgmt:If:epDn managed object property"
    ::= { cfprApMgmtIfEntry 9 }

cfprApMgmtIfExtBroadcast OBJECT-TYPE
    SYNTAX       InetAddressIPv4
    MAX-ACCESS   read-only
    STATUS       current
    DESCRIPTION
        "Cisco Firepower mgmt:If:extBroadcast managed object property"
    ::= { cfprApMgmtIfEntry 10 }

cfprApMgmtIfExtGw OBJECT-TYPE
    SYNTAX       InetAddressIPv4
    MAX-ACCESS   read-only
    STATUS       current
    DESCRIPTION
        "Cisco Firepower mgmt:If:extGw managed object property"
    ::= { cfprApMgmtIfEntry 11 }

cfprApMgmtIfExtIp OBJECT-TYPE
    SYNTAX       InetAddressIPv4
    MAX-ACCESS   read-only
    STATUS       current
    DESCRIPTION
        "Cisco Firepower mgmt:If:extIp managed object property"
    ::= { cfprApMgmtIfEntry 12 }

cfprApMgmtIfExtMask OBJECT-TYPE
    SYNTAX       InetAddressIPv4
    MAX-ACCESS   read-only
    STATUS       current
    DESCRIPTION
        "Cisco Firepower mgmt:If:extMask managed object property"
    ::= { cfprApMgmtIfEntry 13 }

cfprApMgmtIfFsmDescr OBJECT-TYPE
    SYNTAX       SnmpAdminString
    MAX-ACCESS   read-only
    STATUS       current
    DESCRIPTION
        "Cisco Firepower mgmt:If:fsmDescr managed object property"
    ::= { cfprApMgmtIfEntry 14 }

cfprApMgmtIfFsmPrev OBJECT-TYPE
    SYNTAX       SnmpAdminString
    MAX-ACCESS   read-only
    STATUS       current
    DESCRIPTION
        "Cisco Firepower mgmt:If:fsmPrev managed object property"
    ::= { cfprApMgmtIfEntry 15 }

cfprApMgmtIfFsmProgr OBJECT-TYPE
    SYNTAX       Gauge32
    MAX-ACCESS   read-only
    STATUS       current
    DESCRIPTION
        "Cisco Firepower mgmt:If:fsmProgr managed object property"
    ::= { cfprApMgmtIfEntry 16 }

cfprApMgmtIfFsmRmtInvErrCode OBJECT-TYPE
    SYNTAX       Gauge32
    MAX-ACCESS   read-only
    STATUS       current
    DESCRIPTION
        "Cisco Firepower mgmt:If:fsmRmtInvErrCode managed object property"
    ::= { cfprApMgmtIfEntry 17 }

cfprApMgmtIfFsmRmtInvErrDescr OBJECT-TYPE
    SYNTAX       SnmpAdminString
    MAX-ACCESS   read-only
    STATUS       current
    DESCRIPTION
        "Cisco Firepower mgmt:If:fsmRmtInvErrDescr managed
        object property"
    ::= { cfprApMgmtIfEntry 18 }

cfprApMgmtIfFsmRmtInvRslt OBJECT-TYPE
    SYNTAX       CfprApConditionRemoteInvRslt
    MAX-ACCESS   read-only
    STATUS       current
    DESCRIPTION
        "Cisco Firepower mgmt:If:fsmRmtInvRslt managed object property"
    ::= { cfprApMgmtIfEntry 19 }

cfprApMgmtIfFsmStageDescr OBJECT-TYPE
    SYNTAX       SnmpAdminString
    MAX-ACCESS   read-only
    STATUS       current
    DESCRIPTION
        "Cisco Firepower mgmt:If:fsmStageDescr managed object property"
    ::= { cfprApMgmtIfEntry 20 }

cfprApMgmtIfFsmStamp OBJECT-TYPE
    SYNTAX       DateAndTime
    MAX-ACCESS   read-only
    STATUS       current
    DESCRIPTION
        "Cisco Firepower mgmt:If:fsmStamp managed object property"
    ::= { cfprApMgmtIfEntry 21 }

cfprApMgmtIfFsmStatus OBJECT-TYPE
    SYNTAX       SnmpAdminString
    MAX-ACCESS   read-only
    STATUS       current
    DESCRIPTION
        "Cisco Firepower mgmt:If:fsmStatus managed object property"
    ::= { cfprApMgmtIfEntry 22 }

cfprApMgmtIfFsmTry OBJECT-TYPE
    SYNTAX       Gauge32
    MAX-ACCESS   read-only
    STATUS       current
    DESCRIPTION
        "Cisco Firepower mgmt:If:fsmTry managed object property"
    ::= { cfprApMgmtIfEntry 23 }

cfprApMgmtIfId OBJECT-TYPE
    SYNTAX       Gauge32
    MAX-ACCESS   read-only
    STATUS       current
    DESCRIPTION
        "Cisco Firepower mgmt:If:id managed object property"
    ::= { cfprApMgmtIfEntry 24 }

cfprApMgmtIfIfRole OBJECT-TYPE
    SYNTAX       CfprApNetworkPortRole
    MAX-ACCESS   read-only
    STATUS       current
    DESCRIPTION
        "Cisco Firepower mgmt:If:ifRole managed object property"
    ::= { cfprApMgmtIfEntry 25 }

cfprApMgmtIfIfType OBJECT-TYPE
    SYNTAX       CfprApNetworkPhysEpIfType
    MAX-ACCESS   read-only
    STATUS       current
    DESCRIPTION
        "Cisco Firepower mgmt:If:ifType managed object property"
    ::= { cfprApMgmtIfEntry 26 }

cfprApMgmtIfIp OBJECT-TYPE
    SYNTAX       InetAddressIPv4
    MAX-ACCESS   read-only
    STATUS       current
    DESCRIPTION
        "Cisco Firepower mgmt:If:ip managed object property"
    ::= { cfprApMgmtIfEntry 27 }

cfprApMgmtIfLocale OBJECT-TYPE
    SYNTAX       CfprApNetworkLocale
    MAX-ACCESS   read-only
    STATUS       current
    DESCRIPTION
        "Cisco Firepower mgmt:If:locale managed object property"
    ::= { cfprApMgmtIfEntry 28 }

cfprApMgmtIfMac OBJECT-TYPE
    SYNTAX       MacAddress
    MAX-ACCESS   read-only
    STATUS       current
    DESCRIPTION
        "Cisco Firepower mgmt:If:mac managed object property"
    ::= { cfprApMgmtIfEntry 29 }

cfprApMgmtIfMask OBJECT-TYPE
    SYNTAX       InetAddressIPv4
    MAX-ACCESS   read-only
    STATUS       current
    DESCRIPTION
        "Cisco Firepower mgmt:If:mask managed object property"
    ::= { cfprApMgmtIfEntry 30 }

cfprApMgmtIfName OBJECT-TYPE
    SYNTAX       SnmpAdminString
    MAX-ACCESS   read-only
    STATUS       current
    DESCRIPTION
        "Cisco Firepower mgmt:If:name managed object property"
    ::= { cfprApMgmtIfEntry 31 }

cfprApMgmtIfPeerAggrPortId OBJECT-TYPE
    SYNTAX       Gauge32
    MAX-ACCESS   read-only
    STATUS       current
    DESCRIPTION
        "Cisco Firepower mgmt:If:peerAggrPortId managed object property"
    ::= { cfprApMgmtIfEntry 32 }

cfprApMgmtIfPeerChassisId OBJECT-TYPE
    SYNTAX       Gauge32
    MAX-ACCESS   read-only
    STATUS       current
    DESCRIPTION
        "Cisco Firepower mgmt:If:peerChassisId managed object property"
    ::= { cfprApMgmtIfEntry 33 }

cfprApMgmtIfPeerDn OBJECT-TYPE
    SYNTAX       SnmpAdminString
    MAX-ACCESS   read-only
    STATUS       current
    DESCRIPTION
        "Cisco Firepower mgmt:If:peerDn managed object property"
    ::= { cfprApMgmtIfEntry 34 }

cfprApMgmtIfPeerPortId OBJECT-TYPE
    SYNTAX       Gauge32
    MAX-ACCESS   read-only
    STATUS       current
    DESCRIPTION
        "Cisco Firepower mgmt:If:peerPortId managed object property"
    ::= { cfprApMgmtIfEntry 35 }

cfprApMgmtIfPeerSlotId OBJECT-TYPE
    SYNTAX       Gauge32
    MAX-ACCESS   read-only
    STATUS       current
    DESCRIPTION
        "Cisco Firepower mgmt:If:peerSlotId managed object property"
    ::= { cfprApMgmtIfEntry 36 }

cfprApMgmtIfPortId OBJECT-TYPE
    SYNTAX       Gauge32
    MAX-ACCESS   read-only
    STATUS       current
    DESCRIPTION
        "Cisco Firepower mgmt:If:portId managed object property"
    ::= { cfprApMgmtIfEntry 37 }

cfprApMgmtIfSlotId OBJECT-TYPE
    SYNTAX       Gauge32
    MAX-ACCESS   read-only
    STATUS       current
    DESCRIPTION
        "Cisco Firepower mgmt:If:slotId managed object property"
    ::= { cfprApMgmtIfEntry 38 }

cfprApMgmtIfStateQual OBJECT-TYPE
    SYNTAX       CfprApMgmtStateQual
    MAX-ACCESS   read-only
    STATUS       current
    DESCRIPTION
        "Cisco Firepower mgmt:If:stateQual managed object property"
    ::= { cfprApMgmtIfEntry 39 }

cfprApMgmtIfSubject OBJECT-TYPE
    SYNTAX       CfprApMgmtSubject
    MAX-ACCESS   read-only
    STATUS       current
    DESCRIPTION
        "Cisco Firepower mgmt:If:subject managed object property"
    ::= { cfprApMgmtIfEntry 40 }

cfprApMgmtIfSwitchId OBJECT-TYPE
    SYNTAX       CfprApNetworkSwitchId
    MAX-ACCESS   read-only
    STATUS       current
    DESCRIPTION
        "Cisco Firepower mgmt:If:switchId managed object property"
    ::= { cfprApMgmtIfEntry 41 }

cfprApMgmtIfTransport OBJECT-TYPE
    SYNTAX       CfprApNetworkTransport
    MAX-ACCESS   read-only
    STATUS       current
    DESCRIPTION
        "Cisco Firepower mgmt:If:transport managed object property"
    ::= { cfprApMgmtIfEntry 42 }

cfprApMgmtIfType OBJECT-TYPE
    SYNTAX       CfprApNetworkConnectionType
    MAX-ACCESS   read-only
    STATUS       current
    DESCRIPTION
        "Cisco Firepower mgmt:If:type managed object property"
    ::= { cfprApMgmtIfEntry 43 }

cfprApMgmtIfVnet OBJECT-TYPE
    SYNTAX       Gauge32
    MAX-ACCESS   read-only
    STATUS       current
    DESCRIPTION
        "Cisco Firepower mgmt:If:vnet managed object property"
    ::= { cfprApMgmtIfEntry 44 }

cfprApMgmtIfFsmTable OBJECT-TYPE
    SYNTAX           SEQUENCE OF CfprApMgmtIfFsmEntry
    MAX-ACCESS       not-accessible
    STATUS           current
    DESCRIPTION
        "Cisco Firepower mgmt:IfFsm managed object table"
    ::= { cfprApMgmtObjects 32 }

cfprApMgmtIfFsmEntry OBJECT-TYPE
    SYNTAX           CfprApMgmtIfFsmEntry
    MAX-ACCESS       not-accessible
    STATUS           current
    DESCRIPTION
        "Entry for the cfprApMgmtIfFsmTable table."
    INDEX { cfprApMgmtIfFsmInstanceId }
    ::= { cfprApMgmtIfFsmTable 1 }

CfprApMgmtIfFsmEntry ::= SEQUENCE {
    cfprApMgmtIfFsmInstanceId                                        CfprApManagedObjectId,
    cfprApMgmtIfFsmDn                                                CfprApManagedObjectDn,
    cfprApMgmtIfFsmRn                                                SnmpAdminString,
    cfprApMgmtIfFsmCompletionTime                                    DateAndTime,
    cfprApMgmtIfFsmCurrentFsm                                        CfprApMgmtIfFsmCurrentFsm,
    cfprApMgmtIfFsmDescrData                                         SnmpAdminString,
    cfprApMgmtIfFsmFsmStatus                                         CfprApFsmFsmStageStatus,
    cfprApMgmtIfFsmProgress                                          Gauge32,
    cfprApMgmtIfFsmRmtErrCode                                        Gauge32,
    cfprApMgmtIfFsmRmtErrDescr                                       SnmpAdminString,
    cfprApMgmtIfFsmRmtRslt                                           CfprApConditionRemoteInvRslt
}

cfprApMgmtIfFsmInstanceId OBJECT-TYPE
    SYNTAX       CfprApManagedObjectId
    MAX-ACCESS   not-accessible
    STATUS       current
    DESCRIPTION
        "Instance identifier of the managed object."
    ::= { cfprApMgmtIfFsmEntry 1 }

cfprApMgmtIfFsmDn OBJECT-TYPE
    SYNTAX       CfprApManagedObjectDn
    MAX-ACCESS   read-only
    STATUS       current
    DESCRIPTION
        "Cisco Firepower mgmt:IfFsm:dn managed object property"
    ::= { cfprApMgmtIfFsmEntry 2 }

cfprApMgmtIfFsmRn OBJECT-TYPE
    SYNTAX       SnmpAdminString
    MAX-ACCESS   read-only
    STATUS       current
    DESCRIPTION
        "Cisco Firepower mgmt:IfFsm:rn managed object property"
    ::= { cfprApMgmtIfFsmEntry 3 }

cfprApMgmtIfFsmCompletionTime OBJECT-TYPE
    SYNTAX       DateAndTime
    MAX-ACCESS   read-only
    STATUS       current
    DESCRIPTION
        "Cisco Firepower mgmt:IfFsm:completionTime managed
        object property"
    ::= { cfprApMgmtIfFsmEntry 4 }

cfprApMgmtIfFsmCurrentFsm OBJECT-TYPE
    SYNTAX       CfprApMgmtIfFsmCurrentFsm
    MAX-ACCESS   read-only
    STATUS       current
    DESCRIPTION
        "Cisco Firepower mgmt:IfFsm:currentFsm managed object property"
    ::= { cfprApMgmtIfFsmEntry 5 }

cfprApMgmtIfFsmDescrData OBJECT-TYPE
    SYNTAX       SnmpAdminString
    MAX-ACCESS   read-only
    STATUS       current
    DESCRIPTION
        "Cisco Firepower mgmt:IfFsm:descr managed object property"
    ::= { cfprApMgmtIfFsmEntry 6 }

cfprApMgmtIfFsmFsmStatus OBJECT-TYPE
    SYNTAX       CfprApFsmFsmStageStatus
    MAX-ACCESS   read-only
    STATUS       current
    DESCRIPTION
        "Cisco Firepower mgmt:IfFsm:fsmStatus managed object property"
    ::= { cfprApMgmtIfFsmEntry 7 }

cfprApMgmtIfFsmProgress OBJECT-TYPE
    SYNTAX       Gauge32
    MAX-ACCESS   read-only
    STATUS       current
    DESCRIPTION
        "Cisco Firepower mgmt:IfFsm:progress managed object property"
    ::= { cfprApMgmtIfFsmEntry 8 }

cfprApMgmtIfFsmRmtErrCode OBJECT-TYPE
    SYNTAX       Gauge32
    MAX-ACCESS   read-only
    STATUS       current
    DESCRIPTION
        "Cisco Firepower mgmt:IfFsm:rmtErrCode managed object property"
    ::= { cfprApMgmtIfFsmEntry 9 }

cfprApMgmtIfFsmRmtErrDescr OBJECT-TYPE
    SYNTAX       SnmpAdminString
    MAX-ACCESS   read-only
    STATUS       current
    DESCRIPTION
        "Cisco Firepower mgmt:IfFsm:rmtErrDescr managed object property"
    ::= { cfprApMgmtIfFsmEntry 10 }

cfprApMgmtIfFsmRmtRslt OBJECT-TYPE
    SYNTAX       CfprApConditionRemoteInvRslt
    MAX-ACCESS   read-only
    STATUS       current
    DESCRIPTION
        "Cisco Firepower mgmt:IfFsm:rmtRslt managed object property"
    ::= { cfprApMgmtIfFsmEntry 11 }

cfprApMgmtIfFsmStageTable OBJECT-TYPE
    SYNTAX           SEQUENCE OF CfprApMgmtIfFsmStageEntry
    MAX-ACCESS       not-accessible
    STATUS           current
    DESCRIPTION
        "Cisco Firepower mgmt:IfFsmStage managed object table"
    ::= { cfprApMgmtObjects 33 }

cfprApMgmtIfFsmStageEntry OBJECT-TYPE
    SYNTAX           CfprApMgmtIfFsmStageEntry
    MAX-ACCESS       not-accessible
    STATUS           current
    DESCRIPTION
        "Entry for the cfprApMgmtIfFsmStageTable table."
    INDEX { cfprApMgmtIfFsmStageInstanceId }
    ::= { cfprApMgmtIfFsmStageTable 1 }

CfprApMgmtIfFsmStageEntry ::= SEQUENCE {
    cfprApMgmtIfFsmStageInstanceId                                   CfprApManagedObjectId,
    cfprApMgmtIfFsmStageDn                                           CfprApManagedObjectDn,
    cfprApMgmtIfFsmStageRn                                           SnmpAdminString,
    cfprApMgmtIfFsmStageDescrData                                    SnmpAdminString,
    cfprApMgmtIfFsmStageLastUpdateTime                               DateAndTime,
    cfprApMgmtIfFsmStageName                                         CfprApMgmtIfFsmStageName,
    cfprApMgmtIfFsmStageOrder                                        Gauge32,
    cfprApMgmtIfFsmStageRetry                                        Gauge32,
    cfprApMgmtIfFsmStageStageStatus                                  CfprApFsmFsmStageStatus
}

cfprApMgmtIfFsmStageInstanceId OBJECT-TYPE
    SYNTAX       CfprApManagedObjectId
    MAX-ACCESS   not-accessible
    STATUS       current
    DESCRIPTION
        "Instance identifier of the managed object."
    ::= { cfprApMgmtIfFsmStageEntry 1 }

cfprApMgmtIfFsmStageDn OBJECT-TYPE
    SYNTAX       CfprApManagedObjectDn
    MAX-ACCESS   read-only
    STATUS       current
    DESCRIPTION
        "Cisco Firepower mgmt:IfFsmStage:dn managed object property"
    ::= { cfprApMgmtIfFsmStageEntry 2 }

cfprApMgmtIfFsmStageRn OBJECT-TYPE
    SYNTAX       SnmpAdminString
    MAX-ACCESS   read-only
    STATUS       current
    DESCRIPTION
        "Cisco Firepower mgmt:IfFsmStage:rn managed object property"
    ::= { cfprApMgmtIfFsmStageEntry 3 }

cfprApMgmtIfFsmStageDescrData OBJECT-TYPE
    SYNTAX       SnmpAdminString
    MAX-ACCESS   read-only
    STATUS       current
    DESCRIPTION
        "Cisco Firepower mgmt:IfFsmStage:descr managed object property"
    ::= { cfprApMgmtIfFsmStageEntry 4 }

cfprApMgmtIfFsmStageLastUpdateTime OBJECT-TYPE
    SYNTAX       DateAndTime
    MAX-ACCESS   read-only
    STATUS       current
    DESCRIPTION
        "Cisco Firepower mgmt:IfFsmStage:lastUpdateTime
        managed object property"
    ::= { cfprApMgmtIfFsmStageEntry 5 }

cfprApMgmtIfFsmStageName OBJECT-TYPE
    SYNTAX       CfprApMgmtIfFsmStageName
    MAX-ACCESS   read-only
    STATUS       current
    DESCRIPTION
        "Cisco Firepower mgmt:IfFsmStage:name managed object property"
    ::= { cfprApMgmtIfFsmStageEntry 6 }

cfprApMgmtIfFsmStageOrder OBJECT-TYPE
    SYNTAX       Gauge32
    MAX-ACCESS   read-only
    STATUS       current
    DESCRIPTION
        "Cisco Firepower mgmt:IfFsmStage:order managed object property"
    ::= { cfprApMgmtIfFsmStageEntry 7 }

cfprApMgmtIfFsmStageRetry OBJECT-TYPE
    SYNTAX       Gauge32
    MAX-ACCESS   read-only
    STATUS       current
    DESCRIPTION
        "Cisco Firepower mgmt:IfFsmStage:retry managed object property"
    ::= { cfprApMgmtIfFsmStageEntry 8 }

cfprApMgmtIfFsmStageStageStatus OBJECT-TYPE
    SYNTAX       CfprApFsmFsmStageStatus
    MAX-ACCESS   read-only
    STATUS       current
    DESCRIPTION
        "Cisco Firepower mgmt:IfFsmStage:stageStatus managed
        object property"
    ::= { cfprApMgmtIfFsmStageEntry 9 }

cfprApMgmtIfFsmTaskTable OBJECT-TYPE
    SYNTAX           SEQUENCE OF CfprApMgmtIfFsmTaskEntry
    MAX-ACCESS       not-accessible
    STATUS           current
    DESCRIPTION
        "Cisco Firepower mgmt:IfFsmTask managed object table"
    ::= { cfprApMgmtObjects 34 }

cfprApMgmtIfFsmTaskEntry OBJECT-TYPE
    SYNTAX           CfprApMgmtIfFsmTaskEntry
    MAX-ACCESS       not-accessible
    STATUS           current
    DESCRIPTION
        "Entry for the cfprApMgmtIfFsmTaskTable table."
    INDEX { cfprApMgmtIfFsmTaskInstanceId }
    ::= { cfprApMgmtIfFsmTaskTable 1 }

CfprApMgmtIfFsmTaskEntry ::= SEQUENCE {
    cfprApMgmtIfFsmTaskInstanceId                                    CfprApManagedObjectId,
    cfprApMgmtIfFsmTaskDn                                            CfprApManagedObjectDn,
    cfprApMgmtIfFsmTaskRn                                            SnmpAdminString,
    cfprApMgmtIfFsmTaskCompletion                                    CfprApFsmCompletion,
    cfprApMgmtIfFsmTaskFlags                                         CfprApFsmFlags,
    cfprApMgmtIfFsmTaskItem                                          CfprApMgmtIfFsmTaskItem,
    cfprApMgmtIfFsmTaskSeqId                                         Gauge32
}

cfprApMgmtIfFsmTaskInstanceId OBJECT-TYPE
    SYNTAX       CfprApManagedObjectId
    MAX-ACCESS   not-accessible
    STATUS       current
    DESCRIPTION
        "Instance identifier of the managed object."
    ::= { cfprApMgmtIfFsmTaskEntry 1 }

cfprApMgmtIfFsmTaskDn OBJECT-TYPE
    SYNTAX       CfprApManagedObjectDn
    MAX-ACCESS   read-only
    STATUS       current
    DESCRIPTION
        "Cisco Firepower mgmt:IfFsmTask:dn managed object property"
    ::= { cfprApMgmtIfFsmTaskEntry 2 }

cfprApMgmtIfFsmTaskRn OBJECT-TYPE
    SYNTAX       SnmpAdminString
    MAX-ACCESS   read-only
    STATUS       current
    DESCRIPTION
        "Cisco Firepower mgmt:IfFsmTask:rn managed object property"
    ::= { cfprApMgmtIfFsmTaskEntry 3 }

cfprApMgmtIfFsmTaskCompletion OBJECT-TYPE
    SYNTAX       CfprApFsmCompletion
    MAX-ACCESS   read-only
    STATUS       current
    DESCRIPTION
        "Cisco Firepower mgmt:IfFsmTask:completion managed
        object property"
    ::= { cfprApMgmtIfFsmTaskEntry 4 }

cfprApMgmtIfFsmTaskFlags OBJECT-TYPE
    SYNTAX       CfprApFsmFlags
    MAX-ACCESS   read-only
    STATUS       current
    DESCRIPTION
        "Cisco Firepower mgmt:IfFsmTask:flags managed object property"
    ::= { cfprApMgmtIfFsmTaskEntry 5 }

cfprApMgmtIfFsmTaskItem OBJECT-TYPE
    SYNTAX       CfprApMgmtIfFsmTaskItem
    MAX-ACCESS   read-only
    STATUS       current
    DESCRIPTION
        "Cisco Firepower mgmt:IfFsmTask:item managed object property"
    ::= { cfprApMgmtIfFsmTaskEntry 6 }

cfprApMgmtIfFsmTaskSeqId OBJECT-TYPE
    SYNTAX       Gauge32
    MAX-ACCESS   read-only
    STATUS       current
    DESCRIPTION
        "Cisco Firepower mgmt:IfFsmTask:seqId managed object property"
    ::= { cfprApMgmtIfFsmTaskEntry 7 }

cfprApMgmtImportConfigInfoTable OBJECT-TYPE
    SYNTAX           SEQUENCE OF CfprApMgmtImportConfigInfoEntry
    MAX-ACCESS       not-accessible
    STATUS           current
    DESCRIPTION
        "Cisco Firepower mgmt:ImportConfigInfo managed object table"
    ::= { cfprApMgmtObjects 35 }

cfprApMgmtImportConfigInfoEntry OBJECT-TYPE
    SYNTAX           CfprApMgmtImportConfigInfoEntry
    MAX-ACCESS       not-accessible
    STATUS           current
    DESCRIPTION
        "Entry for the cfprApMgmtImportConfigInfoTable table."
    INDEX { cfprApMgmtImportConfigInfoInstanceId }
    ::= { cfprApMgmtImportConfigInfoTable 1 }

CfprApMgmtImportConfigInfoEntry ::= SEQUENCE {
    cfprApMgmtImportConfigInfoInstanceId                             CfprApManagedObjectId,
    cfprApMgmtImportConfigInfoDn                                     CfprApManagedObjectDn,
    cfprApMgmtImportConfigInfoRn                                     SnmpAdminString,
    cfprApMgmtImportConfigInfoImportDate                             DateAndTime
}

cfprApMgmtImportConfigInfoInstanceId OBJECT-TYPE
    SYNTAX       CfprApManagedObjectId
    MAX-ACCESS   not-accessible
    STATUS       current
    DESCRIPTION
        "Instance identifier of the managed object."
    ::= { cfprApMgmtImportConfigInfoEntry 1 }

cfprApMgmtImportConfigInfoDn OBJECT-TYPE
    SYNTAX       CfprApManagedObjectDn
    MAX-ACCESS   read-only
    STATUS       current
    DESCRIPTION
        "Cisco Firepower mgmt:ImportConfigInfo:dn managed object property"
    ::= { cfprApMgmtImportConfigInfoEntry 2 }

cfprApMgmtImportConfigInfoRn OBJECT-TYPE
    SYNTAX       SnmpAdminString
    MAX-ACCESS   read-only
    STATUS       current
    DESCRIPTION
        "Cisco Firepower mgmt:ImportConfigInfo:rn managed object property"
    ::= { cfprApMgmtImportConfigInfoEntry 3 }

cfprApMgmtImportConfigInfoImportDate OBJECT-TYPE
    SYNTAX       DateAndTime
    MAX-ACCESS   read-only
    STATUS       current
    DESCRIPTION
        "Cisco Firepower mgmt:ImportConfigInfo:importDate
        managed object property"
    ::= { cfprApMgmtImportConfigInfoEntry 4 }

cfprApMgmtImporterTable OBJECT-TYPE
    SYNTAX           SEQUENCE OF CfprApMgmtImporterEntry
    MAX-ACCESS       not-accessible
    STATUS           current
    DESCRIPTION
        "Cisco Firepower mgmt:Importer managed object table"
    ::= { cfprApMgmtObjects 36 }

cfprApMgmtImporterEntry OBJECT-TYPE
    SYNTAX           CfprApMgmtImporterEntry
    MAX-ACCESS       not-accessible
    STATUS           current
    DESCRIPTION
        "Entry for the cfprApMgmtImporterTable table."
    INDEX { cfprApMgmtImporterInstanceId }
    ::= { cfprApMgmtImporterTable 1 }

CfprApMgmtImporterEntry ::= SEQUENCE {
    cfprApMgmtImporterInstanceId                                     CfprApManagedObjectId,
    cfprApMgmtImporterDn                                             CfprApManagedObjectDn,
    cfprApMgmtImporterRn                                             SnmpAdminString,
    cfprApMgmtImporterAction                                         CfprApMgmtImportAction,
    cfprApMgmtImporterAdminState                                     CfprApCommClientAdminState,
    cfprApMgmtImporterApplyingBreakoutCfg                            TruthValue,
    cfprApMgmtImporterDescr                                          SnmpAdminString,
    cfprApMgmtImporterFsmDescr                                       SnmpAdminString,
    cfprApMgmtImporterFsmPrev                                        SnmpAdminString,
    cfprApMgmtImporterFsmProgr                                       Gauge32,
    cfprApMgmtImporterFsmRmtInvErrCode                               Gauge32,
    cfprApMgmtImporterFsmRmtInvErrDescr                              SnmpAdminString,
    cfprApMgmtImporterFsmRmtInvRslt                                  CfprApConditionRemoteInvRslt,
    cfprApMgmtImporterFsmStageDescr                                  SnmpAdminString,
    cfprApMgmtImporterFsmStamp                                       DateAndTime,
    cfprApMgmtImporterFsmStatus                                      SnmpAdminString,
    cfprApMgmtImporterFsmTry                                         Gauge32,
    cfprApMgmtImporterHostname                                       SnmpAdminString,
    cfprApMgmtImporterIntId                                          SnmpAdminString,
    cfprApMgmtImporterName                                           SnmpAdminString,
    cfprApMgmtImporterOperStatus                                     CfprApMgmtImportStatus,
    cfprApMgmtImporterPolicyLevel                                    Gauge32,
    cfprApMgmtImporterPolicyOwner                                    CfprApPolicyPolicyOwner,
    cfprApMgmtImporterPort                                           Gauge32,
    cfprApMgmtImporterPostAction                                     CfprApMgmtImporterPostAction,
    cfprApMgmtImporterProto                                          CfprApMgmtImporterProto,
    cfprApMgmtImporterPwd                                            SnmpAdminString,
    cfprApMgmtImporterRemoteFile                                     SnmpAdminString,
    cfprApMgmtImporterUser                                           SnmpAdminString
}

cfprApMgmtImporterInstanceId OBJECT-TYPE
    SYNTAX       CfprApManagedObjectId
    MAX-ACCESS   not-accessible
    STATUS       current
    DESCRIPTION
        "Instance identifier of the managed object."
    ::= { cfprApMgmtImporterEntry 1 }

cfprApMgmtImporterDn OBJECT-TYPE
    SYNTAX       CfprApManagedObjectDn
    MAX-ACCESS   read-only
    STATUS       current
    DESCRIPTION
        "Cisco Firepower mgmt:Importer:dn managed object property"
    ::= { cfprApMgmtImporterEntry 2 }

cfprApMgmtImporterRn OBJECT-TYPE
    SYNTAX       SnmpAdminString
    MAX-ACCESS   read-only
    STATUS       current
    DESCRIPTION
        "Cisco Firepower mgmt:Importer:rn managed object property"
    ::= { cfprApMgmtImporterEntry 3 }

cfprApMgmtImporterAction OBJECT-TYPE
    SYNTAX       CfprApMgmtImportAction
    MAX-ACCESS   read-only
    STATUS       current
    DESCRIPTION
        "Cisco Firepower mgmt:Importer:action managed object property"
    ::= { cfprApMgmtImporterEntry 4 }

cfprApMgmtImporterAdminState OBJECT-TYPE
    SYNTAX       CfprApCommClientAdminState
    MAX-ACCESS   read-only
    STATUS       current
    DESCRIPTION
        "Cisco Firepower mgmt:Importer:adminState managed object property"
    ::= { cfprApMgmtImporterEntry 5 }

cfprApMgmtImporterApplyingBreakoutCfg OBJECT-TYPE
    SYNTAX       TruthValue
    MAX-ACCESS   read-only
    STATUS       current
    DESCRIPTION
        "Cisco Firepower mgmt:Importer:applyingBreakoutCfg
        managed object property"
    ::= { cfprApMgmtImporterEntry 6 }

cfprApMgmtImporterDescr OBJECT-TYPE
    SYNTAX       SnmpAdminString
    MAX-ACCESS   read-only
    STATUS       current
    DESCRIPTION
        "Cisco Firepower mgmt:Importer:descr managed object property"
    ::= { cfprApMgmtImporterEntry 7 }

cfprApMgmtImporterFsmDescr OBJECT-TYPE
    SYNTAX       SnmpAdminString
    MAX-ACCESS   read-only
    STATUS       current
    DESCRIPTION
        "Cisco Firepower mgmt:Importer:fsmDescr managed object property"
    ::= { cfprApMgmtImporterEntry 8 }

cfprApMgmtImporterFsmPrev OBJECT-TYPE
    SYNTAX       SnmpAdminString
    MAX-ACCESS   read-only
    STATUS       current
    DESCRIPTION
        "Cisco Firepower mgmt:Importer:fsmPrev managed object property"
    ::= { cfprApMgmtImporterEntry 9 }

cfprApMgmtImporterFsmProgr OBJECT-TYPE
    SYNTAX       Gauge32
    MAX-ACCESS   read-only
    STATUS       current
    DESCRIPTION
        "Cisco Firepower mgmt:Importer:fsmProgr managed object property"
    ::= { cfprApMgmtImporterEntry 10 }

cfprApMgmtImporterFsmRmtInvErrCode OBJECT-TYPE
    SYNTAX       Gauge32
    MAX-ACCESS   read-only
    STATUS       current
    DESCRIPTION
        "Cisco Firepower mgmt:Importer:fsmRmtInvErrCode
        managed object property"
    ::= { cfprApMgmtImporterEntry 11 }

cfprApMgmtImporterFsmRmtInvErrDescr OBJECT-TYPE
    SYNTAX       SnmpAdminString
    MAX-ACCESS   read-only
    STATUS       current
    DESCRIPTION
        "Cisco Firepower mgmt:Importer:fsmRmtInvErrDescr
        managed object property"
    ::= { cfprApMgmtImporterEntry 12 }

cfprApMgmtImporterFsmRmtInvRslt OBJECT-TYPE
    SYNTAX       CfprApConditionRemoteInvRslt
    MAX-ACCESS   read-only
    STATUS       current
    DESCRIPTION
        "Cisco Firepower mgmt:Importer:fsmRmtInvRslt managed
        object property"
    ::= { cfprApMgmtImporterEntry 13 }

cfprApMgmtImporterFsmStageDescr OBJECT-TYPE
    SYNTAX       SnmpAdminString
    MAX-ACCESS   read-only
    STATUS       current
    DESCRIPTION
        "Cisco Firepower mgmt:Importer:fsmStageDescr managed
        object property"
    ::= { cfprApMgmtImporterEntry 14 }

cfprApMgmtImporterFsmStamp OBJECT-TYPE
    SYNTAX       DateAndTime
    MAX-ACCESS   read-only
    STATUS       current
    DESCRIPTION
        "Cisco Firepower mgmt:Importer:fsmStamp managed object property"
    ::= { cfprApMgmtImporterEntry 15 }

cfprApMgmtImporterFsmStatus OBJECT-TYPE
    SYNTAX       SnmpAdminString
    MAX-ACCESS   read-only
    STATUS       current
    DESCRIPTION
        "Cisco Firepower mgmt:Importer:fsmStatus managed object property"
    ::= { cfprApMgmtImporterEntry 16 }

cfprApMgmtImporterFsmTry OBJECT-TYPE
    SYNTAX       Gauge32
    MAX-ACCESS   read-only
    STATUS       current
    DESCRIPTION
        "Cisco Firepower mgmt:Importer:fsmTry managed object property"
    ::= { cfprApMgmtImporterEntry 17 }

cfprApMgmtImporterHostname OBJECT-TYPE
    SYNTAX       SnmpAdminString
    MAX-ACCESS   read-only
    STATUS       current
    DESCRIPTION
        "Cisco Firepower mgmt:Importer:hostname managed object property"
    ::= { cfprApMgmtImporterEntry 18 }

cfprApMgmtImporterIntId OBJECT-TYPE
    SYNTAX       SnmpAdminString
    MAX-ACCESS   read-only
    STATUS       current
    DESCRIPTION
        "Cisco Firepower mgmt:Importer:intId managed object property"
    ::= { cfprApMgmtImporterEntry 19 }

cfprApMgmtImporterName OBJECT-TYPE
    SYNTAX       SnmpAdminString
    MAX-ACCESS   read-only
    STATUS       current
    DESCRIPTION
        "Cisco Firepower mgmt:Importer:name managed object property"
    ::= { cfprApMgmtImporterEntry 20 }

cfprApMgmtImporterOperStatus OBJECT-TYPE
    SYNTAX       CfprApMgmtImportStatus
    MAX-ACCESS   read-only
    STATUS       current
    DESCRIPTION
        "Cisco Firepower mgmt:Importer:operStatus managed object property"
    ::= { cfprApMgmtImporterEntry 21 }

cfprApMgmtImporterPolicyLevel OBJECT-TYPE
    SYNTAX       Gauge32
    MAX-ACCESS   read-only
    STATUS       current
    DESCRIPTION
        "Cisco Firepower mgmt:Importer:policyLevel managed
        object property"
    ::= { cfprApMgmtImporterEntry 22 }

cfprApMgmtImporterPolicyOwner OBJECT-TYPE
    SYNTAX       CfprApPolicyPolicyOwner
    MAX-ACCESS   read-only
    STATUS       current
    DESCRIPTION
        "Cisco Firepower mgmt:Importer:policyOwner managed
        object property"
    ::= { cfprApMgmtImporterEntry 23 }

cfprApMgmtImporterPort OBJECT-TYPE
    SYNTAX       Gauge32
    MAX-ACCESS   read-only
    STATUS       current
    DESCRIPTION
        "Cisco Firepower mgmt:Importer:port managed object property"
    ::= { cfprApMgmtImporterEntry 24 }

cfprApMgmtImporterPostAction OBJECT-TYPE
    SYNTAX       CfprApMgmtImporterPostAction
    MAX-ACCESS   read-only
    STATUS       current
    DESCRIPTION
        "Cisco Firepower mgmt:Importer:postAction managed object property"
    ::= { cfprApMgmtImporterEntry 25 }

cfprApMgmtImporterProto OBJECT-TYPE
    SYNTAX       CfprApMgmtImporterProto
    MAX-ACCESS   read-only
    STATUS       current
    DESCRIPTION
        "Cisco Firepower mgmt:Importer:proto managed object property"
    ::= { cfprApMgmtImporterEntry 26 }

cfprApMgmtImporterPwd OBJECT-TYPE
    SYNTAX       SnmpAdminString
    MAX-ACCESS   read-only
    STATUS       current
    DESCRIPTION
        "Cisco Firepower mgmt:Importer:pwd managed object property"
    ::= { cfprApMgmtImporterEntry 27 }

cfprApMgmtImporterRemoteFile OBJECT-TYPE
    SYNTAX       SnmpAdminString
    MAX-ACCESS   read-only
    STATUS       current
    DESCRIPTION
        "Cisco Firepower mgmt:Importer:remoteFile managed object property"
    ::= { cfprApMgmtImporterEntry 28 }

cfprApMgmtImporterUser OBJECT-TYPE
    SYNTAX       SnmpAdminString
    MAX-ACCESS   read-only
    STATUS       current
    DESCRIPTION
        "Cisco Firepower mgmt:Importer:user managed object property"
    ::= { cfprApMgmtImporterEntry 29 }

cfprApMgmtImporterFsmTable OBJECT-TYPE
    SYNTAX           SEQUENCE OF CfprApMgmtImporterFsmEntry
    MAX-ACCESS       not-accessible
    STATUS           current
    DESCRIPTION
        "Cisco Firepower mgmt:ImporterFsm managed object table"
    ::= { cfprApMgmtObjects 37 }

cfprApMgmtImporterFsmEntry OBJECT-TYPE
    SYNTAX           CfprApMgmtImporterFsmEntry
    MAX-ACCESS       not-accessible
    STATUS           current
    DESCRIPTION
        "Entry for the cfprApMgmtImporterFsmTable table."
    INDEX { cfprApMgmtImporterFsmInstanceId }
    ::= { cfprApMgmtImporterFsmTable 1 }

CfprApMgmtImporterFsmEntry ::= SEQUENCE {
    cfprApMgmtImporterFsmInstanceId                                  CfprApManagedObjectId,
    cfprApMgmtImporterFsmDn                                          CfprApManagedObjectDn,
    cfprApMgmtImporterFsmRn                                          SnmpAdminString,
    cfprApMgmtImporterFsmCompletionTime                              DateAndTime,
    cfprApMgmtImporterFsmCurrentFsm                                  CfprApMgmtImporterFsmCurrentFsm,
    cfprApMgmtImporterFsmDescrData                                   SnmpAdminString,
    cfprApMgmtImporterFsmFsmStatus                                   CfprApFsmFsmStageStatus,
    cfprApMgmtImporterFsmProgress                                    Gauge32,
    cfprApMgmtImporterFsmRmtErrCode                                  Gauge32,
    cfprApMgmtImporterFsmRmtErrDescr                                 SnmpAdminString,
    cfprApMgmtImporterFsmRmtRslt                                     CfprApConditionRemoteInvRslt
}

cfprApMgmtImporterFsmInstanceId OBJECT-TYPE
    SYNTAX       CfprApManagedObjectId
    MAX-ACCESS   not-accessible
    STATUS       current
    DESCRIPTION
        "Instance identifier of the managed object."
    ::= { cfprApMgmtImporterFsmEntry 1 }

cfprApMgmtImporterFsmDn OBJECT-TYPE
    SYNTAX       CfprApManagedObjectDn
    MAX-ACCESS   read-only
    STATUS       current
    DESCRIPTION
        "Cisco Firepower mgmt:ImporterFsm:dn managed object property"
    ::= { cfprApMgmtImporterFsmEntry 2 }

cfprApMgmtImporterFsmRn OBJECT-TYPE
    SYNTAX       SnmpAdminString
    MAX-ACCESS   read-only
    STATUS       current
    DESCRIPTION
        "Cisco Firepower mgmt:ImporterFsm:rn managed object property"
    ::= { cfprApMgmtImporterFsmEntry 3 }

cfprApMgmtImporterFsmCompletionTime OBJECT-TYPE
    SYNTAX       DateAndTime
    MAX-ACCESS   read-only
    STATUS       current
    DESCRIPTION
        "Cisco Firepower mgmt:ImporterFsm:completionTime
        managed object property"
    ::= { cfprApMgmtImporterFsmEntry 4 }

cfprApMgmtImporterFsmCurrentFsm OBJECT-TYPE
    SYNTAX       CfprApMgmtImporterFsmCurrentFsm
    MAX-ACCESS   read-only
    STATUS       current
    DESCRIPTION
        "Cisco Firepower mgmt:ImporterFsm:currentFsm managed
        object property"
    ::= { cfprApMgmtImporterFsmEntry 5 }

cfprApMgmtImporterFsmDescrData OBJECT-TYPE
    SYNTAX       SnmpAdminString
    MAX-ACCESS   read-only
    STATUS       current
    DESCRIPTION
        "Cisco Firepower mgmt:ImporterFsm:descr managed object property"
    ::= { cfprApMgmtImporterFsmEntry 6 }

cfprApMgmtImporterFsmFsmStatus OBJECT-TYPE
    SYNTAX       CfprApFsmFsmStageStatus
    MAX-ACCESS   read-only
    STATUS       current
    DESCRIPTION
        "Cisco Firepower mgmt:ImporterFsm:fsmStatus managed
        object property"
    ::= { cfprApMgmtImporterFsmEntry 7 }

cfprApMgmtImporterFsmProgress OBJECT-TYPE
    SYNTAX       Gauge32
    MAX-ACCESS   read-only
    STATUS       current
    DESCRIPTION
        "Cisco Firepower mgmt:ImporterFsm:progress managed
        object property"
    ::= { cfprApMgmtImporterFsmEntry 8 }

cfprApMgmtImporterFsmRmtErrCode OBJECT-TYPE
    SYNTAX       Gauge32
    MAX-ACCESS   read-only
    STATUS       current
    DESCRIPTION
        "Cisco Firepower mgmt:ImporterFsm:rmtErrCode managed
        object property"
    ::= { cfprApMgmtImporterFsmEntry 9 }

cfprApMgmtImporterFsmRmtErrDescr OBJECT-TYPE
    SYNTAX       SnmpAdminString
    MAX-ACCESS   read-only
    STATUS       current
    DESCRIPTION
        "Cisco Firepower mgmt:ImporterFsm:rmtErrDescr managed
        object property"
    ::= { cfprApMgmtImporterFsmEntry 10 }

cfprApMgmtImporterFsmRmtRslt OBJECT-TYPE
    SYNTAX       CfprApConditionRemoteInvRslt
    MAX-ACCESS   read-only
    STATUS       current
    DESCRIPTION
        "Cisco Firepower mgmt:ImporterFsm:rmtRslt managed object property"
    ::= { cfprApMgmtImporterFsmEntry 11 }

cfprApMgmtImporterFsmStageTable OBJECT-TYPE
    SYNTAX           SEQUENCE OF CfprApMgmtImporterFsmStageEntry
    MAX-ACCESS       not-accessible
    STATUS           current
    DESCRIPTION
        "Cisco Firepower mgmt:ImporterFsmStage managed object table"
    ::= { cfprApMgmtObjects 38 }

cfprApMgmtImporterFsmStageEntry OBJECT-TYPE
    SYNTAX           CfprApMgmtImporterFsmStageEntry
    MAX-ACCESS       not-accessible
    STATUS           current
    DESCRIPTION
        "Entry for the cfprApMgmtImporterFsmStageTable table."
    INDEX { cfprApMgmtImporterFsmStageInstanceId }
    ::= { cfprApMgmtImporterFsmStageTable 1 }

CfprApMgmtImporterFsmStageEntry ::= SEQUENCE {
    cfprApMgmtImporterFsmStageInstanceId                             CfprApManagedObjectId,
    cfprApMgmtImporterFsmStageDn                                     CfprApManagedObjectDn,
    cfprApMgmtImporterFsmStageRn                                     SnmpAdminString,
    cfprApMgmtImporterFsmStageDescrData                              SnmpAdminString,
    cfprApMgmtImporterFsmStageLastUpdateTime                         DateAndTime,
    cfprApMgmtImporterFsmStageName                                   CfprApMgmtImporterFsmStageName,
    cfprApMgmtImporterFsmStageOrder                                  Gauge32,
    cfprApMgmtImporterFsmStageRetry                                  Gauge32,
    cfprApMgmtImporterFsmStageStageStatus                            CfprApFsmFsmStageStatus
}

cfprApMgmtImporterFsmStageInstanceId OBJECT-TYPE
    SYNTAX       CfprApManagedObjectId
    MAX-ACCESS   not-accessible
    STATUS       current
    DESCRIPTION
        "Instance identifier of the managed object."
    ::= { cfprApMgmtImporterFsmStageEntry 1 }

cfprApMgmtImporterFsmStageDn OBJECT-TYPE
    SYNTAX       CfprApManagedObjectDn
    MAX-ACCESS   read-only
    STATUS       current
    DESCRIPTION
        "Cisco Firepower mgmt:ImporterFsmStage:dn managed object property"
    ::= { cfprApMgmtImporterFsmStageEntry 2 }

cfprApMgmtImporterFsmStageRn OBJECT-TYPE
    SYNTAX       SnmpAdminString
    MAX-ACCESS   read-only
    STATUS       current
    DESCRIPTION
        "Cisco Firepower mgmt:ImporterFsmStage:rn managed object property"
    ::= { cfprApMgmtImporterFsmStageEntry 3 }

cfprApMgmtImporterFsmStageDescrData OBJECT-TYPE
    SYNTAX       SnmpAdminString
    MAX-ACCESS   read-only
    STATUS       current
    DESCRIPTION
        "Cisco Firepower mgmt:ImporterFsmStage:descr managed
        object property"
    ::= { cfprApMgmtImporterFsmStageEntry 4 }

cfprApMgmtImporterFsmStageLastUpdateTime OBJECT-TYPE
    SYNTAX       DateAndTime
    MAX-ACCESS   read-only
    STATUS       current
    DESCRIPTION
        "Cisco Firepower mgmt:ImporterFsmStage:lastUpdateTime
        managed object property"
    ::= { cfprApMgmtImporterFsmStageEntry 5 }

cfprApMgmtImporterFsmStageName OBJECT-TYPE
    SYNTAX       CfprApMgmtImporterFsmStageName
    MAX-ACCESS   read-only
    STATUS       current
    DESCRIPTION
        "Cisco Firepower mgmt:ImporterFsmStage:name managed
        object property"
    ::= { cfprApMgmtImporterFsmStageEntry 6 }

cfprApMgmtImporterFsmStageOrder OBJECT-TYPE
    SYNTAX       Gauge32
    MAX-ACCESS   read-only
    STATUS       current
    DESCRIPTION
        "Cisco Firepower mgmt:ImporterFsmStage:order managed
        object property"
    ::= { cfprApMgmtImporterFsmStageEntry 7 }

cfprApMgmtImporterFsmStageRetry OBJECT-TYPE
    SYNTAX       Gauge32
    MAX-ACCESS   read-only
    STATUS       current
    DESCRIPTION
        "Cisco Firepower mgmt:ImporterFsmStage:retry managed
        object property"
    ::= { cfprApMgmtImporterFsmStageEntry 8 }

cfprApMgmtImporterFsmStageStageStatus OBJECT-TYPE
    SYNTAX       CfprApFsmFsmStageStatus
    MAX-ACCESS   read-only
    STATUS       current
    DESCRIPTION
        "Cisco Firepower mgmt:ImporterFsmStage:stageStatus
        managed object property"
    ::= { cfprApMgmtImporterFsmStageEntry 9 }

cfprApMgmtImporterFsmTaskTable OBJECT-TYPE
    SYNTAX           SEQUENCE OF CfprApMgmtImporterFsmTaskEntry
    MAX-ACCESS       not-accessible
    STATUS           current
    DESCRIPTION
        "Cisco Firepower mgmt:ImporterFsmTask managed object table"
    ::= { cfprApMgmtObjects 39 }

cfprApMgmtImporterFsmTaskEntry OBJECT-TYPE
    SYNTAX           CfprApMgmtImporterFsmTaskEntry
    MAX-ACCESS       not-accessible
    STATUS           current
    DESCRIPTION
        "Entry for the cfprApMgmtImporterFsmTaskTable table."
    INDEX { cfprApMgmtImporterFsmTaskInstanceId }
    ::= { cfprApMgmtImporterFsmTaskTable 1 }

CfprApMgmtImporterFsmTaskEntry ::= SEQUENCE {
    cfprApMgmtImporterFsmTaskInstanceId                              CfprApManagedObjectId,
    cfprApMgmtImporterFsmTaskDn                                      CfprApManagedObjectDn,
    cfprApMgmtImporterFsmTaskRn                                      SnmpAdminString,
    cfprApMgmtImporterFsmTaskCompletion                              CfprApFsmCompletion,
    cfprApMgmtImporterFsmTaskFlags                                   CfprApFsmFlags,
    cfprApMgmtImporterFsmTaskItem                                    CfprApMgmtImporterFsmTaskItem,
    cfprApMgmtImporterFsmTaskSeqId                                   Gauge32
}

cfprApMgmtImporterFsmTaskInstanceId OBJECT-TYPE
    SYNTAX       CfprApManagedObjectId
    MAX-ACCESS   not-accessible
    STATUS       current
    DESCRIPTION
        "Instance identifier of the managed object."
    ::= { cfprApMgmtImporterFsmTaskEntry 1 }

cfprApMgmtImporterFsmTaskDn OBJECT-TYPE
    SYNTAX       CfprApManagedObjectDn
    MAX-ACCESS   read-only
    STATUS       current
    DESCRIPTION
        "Cisco Firepower mgmt:ImporterFsmTask:dn managed object property"
    ::= { cfprApMgmtImporterFsmTaskEntry 2 }

cfprApMgmtImporterFsmTaskRn OBJECT-TYPE
    SYNTAX       SnmpAdminString
    MAX-ACCESS   read-only
    STATUS       current
    DESCRIPTION
        "Cisco Firepower mgmt:ImporterFsmTask:rn managed object property"
    ::= { cfprApMgmtImporterFsmTaskEntry 3 }

cfprApMgmtImporterFsmTaskCompletion OBJECT-TYPE
    SYNTAX       CfprApFsmCompletion
    MAX-ACCESS   read-only
    STATUS       current
    DESCRIPTION
        "Cisco Firepower mgmt:ImporterFsmTask:completion
        managed object property"
    ::= { cfprApMgmtImporterFsmTaskEntry 4 }

cfprApMgmtImporterFsmTaskFlags OBJECT-TYPE
    SYNTAX       CfprApFsmFlags
    MAX-ACCESS   read-only
    STATUS       current
    DESCRIPTION
        "Cisco Firepower mgmt:ImporterFsmTask:flags managed
        object property"
    ::= { cfprApMgmtImporterFsmTaskEntry 5 }

cfprApMgmtImporterFsmTaskItem OBJECT-TYPE
    SYNTAX       CfprApMgmtImporterFsmTaskItem
    MAX-ACCESS   read-only
    STATUS       current
    DESCRIPTION
        "Cisco Firepower mgmt:ImporterFsmTask:item managed
        object property"
    ::= { cfprApMgmtImporterFsmTaskEntry 6 }

cfprApMgmtImporterFsmTaskSeqId OBJECT-TYPE
    SYNTAX       Gauge32
    MAX-ACCESS   read-only
    STATUS       current
    DESCRIPTION
        "Cisco Firepower mgmt:ImporterFsmTask:seqId managed
        object property"
    ::= { cfprApMgmtImporterFsmTaskEntry 7 }

cfprApMgmtInbandProfileTable OBJECT-TYPE
    SYNTAX           SEQUENCE OF CfprApMgmtInbandProfileEntry
    MAX-ACCESS       not-accessible
    STATUS           current
    DESCRIPTION
        "Cisco Firepower mgmt:InbandProfile managed object table"
    ::= { cfprApMgmtObjects 40 }

cfprApMgmtInbandProfileEntry OBJECT-TYPE
    SYNTAX           CfprApMgmtInbandProfileEntry
    MAX-ACCESS       not-accessible
    STATUS           current
    DESCRIPTION
        "Entry for the cfprApMgmtInbandProfileTable table."
    INDEX { cfprApMgmtInbandProfileInstanceId }
    ::= { cfprApMgmtInbandProfileTable 1 }

CfprApMgmtInbandProfileEntry ::= SEQUENCE {
    cfprApMgmtInbandProfileInstanceId                                CfprApManagedObjectId,
    cfprApMgmtInbandProfileDn                                        CfprApManagedObjectDn,
    cfprApMgmtInbandProfileRn                                        SnmpAdminString,
    cfprApMgmtInbandProfileDefaultVlanName                           SnmpAdminString,
    cfprApMgmtInbandProfileName                                      SnmpAdminString,
    cfprApMgmtInbandProfilePoolName                                  SnmpAdminString
}

cfprApMgmtInbandProfileInstanceId OBJECT-TYPE
    SYNTAX       CfprApManagedObjectId
    MAX-ACCESS   not-accessible
    STATUS       current
    DESCRIPTION
        "Instance identifier of the managed object."
    ::= { cfprApMgmtInbandProfileEntry 1 }

cfprApMgmtInbandProfileDn OBJECT-TYPE
    SYNTAX       CfprApManagedObjectDn
    MAX-ACCESS   read-only
    STATUS       current
    DESCRIPTION
        "Cisco Firepower mgmt:InbandProfile:dn managed object property"
    ::= { cfprApMgmtInbandProfileEntry 2 }

cfprApMgmtInbandProfileRn OBJECT-TYPE
    SYNTAX       SnmpAdminString
    MAX-ACCESS   read-only
    STATUS       current
    DESCRIPTION
        "Cisco Firepower mgmt:InbandProfile:rn managed object property"
    ::= { cfprApMgmtInbandProfileEntry 3 }

cfprApMgmtInbandProfileDefaultVlanName OBJECT-TYPE
    SYNTAX       SnmpAdminString
    MAX-ACCESS   read-only
    STATUS       current
    DESCRIPTION
        "Cisco Firepower mgmt:InbandProfile:defaultVlanName
        managed object property"
    ::= { cfprApMgmtInbandProfileEntry 4 }

cfprApMgmtInbandProfileName OBJECT-TYPE
    SYNTAX       SnmpAdminString
    MAX-ACCESS   read-only
    STATUS       current
    DESCRIPTION
        "Cisco Firepower mgmt:InbandProfile:name managed object property"
    ::= { cfprApMgmtInbandProfileEntry 5 }

cfprApMgmtInbandProfilePoolName OBJECT-TYPE
    SYNTAX       SnmpAdminString
    MAX-ACCESS   read-only
    STATUS       current
    DESCRIPTION
        "Cisco Firepower mgmt:InbandProfile:poolName managed
        object property"
    ::= { cfprApMgmtInbandProfileEntry 6 }

cfprApMgmtIntAuthPolicyTable OBJECT-TYPE
    SYNTAX           SEQUENCE OF CfprApMgmtIntAuthPolicyEntry
    MAX-ACCESS       not-accessible
    STATUS           current
    DESCRIPTION
        "Cisco Firepower mgmt:IntAuthPolicy managed object table"
    ::= { cfprApMgmtObjects 41 }

cfprApMgmtIntAuthPolicyEntry OBJECT-TYPE
    SYNTAX           CfprApMgmtIntAuthPolicyEntry
    MAX-ACCESS       not-accessible
    STATUS           current
    DESCRIPTION
        "Entry for the cfprApMgmtIntAuthPolicyTable table."
    INDEX { cfprApMgmtIntAuthPolicyInstanceId }
    ::= { cfprApMgmtIntAuthPolicyTable 1 }

CfprApMgmtIntAuthPolicyEntry ::= SEQUENCE {
    cfprApMgmtIntAuthPolicyInstanceId                                CfprApManagedObjectId,
    cfprApMgmtIntAuthPolicyDn                                        CfprApManagedObjectDn,
    cfprApMgmtIntAuthPolicyRn                                        SnmpAdminString,
    cfprApMgmtIntAuthPolicyMethod                                    CfprApMgmtIntAuthPolicyMethod,
    cfprApMgmtIntAuthPolicyName                                      SnmpAdminString,
    cfprApMgmtIntAuthPolicyPwd                                       SnmpAdminString
}

cfprApMgmtIntAuthPolicyInstanceId OBJECT-TYPE
    SYNTAX       CfprApManagedObjectId
    MAX-ACCESS   not-accessible
    STATUS       current
    DESCRIPTION
        "Instance identifier of the managed object."
    ::= { cfprApMgmtIntAuthPolicyEntry 1 }

cfprApMgmtIntAuthPolicyDn OBJECT-TYPE
    SYNTAX       CfprApManagedObjectDn
    MAX-ACCESS   read-only
    STATUS       current
    DESCRIPTION
        "Cisco Firepower mgmt:IntAuthPolicy:dn managed object property"
    ::= { cfprApMgmtIntAuthPolicyEntry 2 }

cfprApMgmtIntAuthPolicyRn OBJECT-TYPE
    SYNTAX       SnmpAdminString
    MAX-ACCESS   read-only
    STATUS       current
    DESCRIPTION
        "Cisco Firepower mgmt:IntAuthPolicy:rn managed object property"
    ::= { cfprApMgmtIntAuthPolicyEntry 3 }

cfprApMgmtIntAuthPolicyMethod OBJECT-TYPE
    SYNTAX       CfprApMgmtIntAuthPolicyMethod
    MAX-ACCESS   read-only
    STATUS       current
    DESCRIPTION
        "Cisco Firepower mgmt:IntAuthPolicy:method managed
        object property"
    ::= { cfprApMgmtIntAuthPolicyEntry 4 }

cfprApMgmtIntAuthPolicyName OBJECT-TYPE
    SYNTAX       SnmpAdminString
    MAX-ACCESS   read-only
    STATUS       current
    DESCRIPTION
        "Cisco Firepower mgmt:IntAuthPolicy:name managed object property"
    ::= { cfprApMgmtIntAuthPolicyEntry 5 }

cfprApMgmtIntAuthPolicyPwd OBJECT-TYPE
    SYNTAX       SnmpAdminString
    MAX-ACCESS   read-only
    STATUS       current
    DESCRIPTION
        "Cisco Firepower mgmt:IntAuthPolicy:pwd managed object property"
    ::= { cfprApMgmtIntAuthPolicyEntry 6 }

cfprApMgmtInterfaceTable OBJECT-TYPE
    SYNTAX           SEQUENCE OF CfprApMgmtInterfaceEntry
    MAX-ACCESS       not-accessible
    STATUS           current
    DESCRIPTION
        "Cisco Firepower mgmt:Interface managed object table"
    ::= { cfprApMgmtObjects 42 }

cfprApMgmtInterfaceEntry OBJECT-TYPE
    SYNTAX           CfprApMgmtInterfaceEntry
    MAX-ACCESS       not-accessible
    STATUS           current
    DESCRIPTION
        "Entry for the cfprApMgmtInterfaceTable table."
    INDEX { cfprApMgmtInterfaceInstanceId }
    ::= { cfprApMgmtInterfaceTable 1 }

CfprApMgmtInterfaceEntry ::= SEQUENCE {
    cfprApMgmtInterfaceInstanceId                                    CfprApManagedObjectId,
    cfprApMgmtInterfaceDn                                            CfprApManagedObjectDn,
    cfprApMgmtInterfaceRn                                            SnmpAdminString,
    cfprApMgmtInterfaceConfigMessage                                 SnmpAdminString,
    cfprApMgmtInterfaceConfigState                                   CfprApMgmtConfigState,
    cfprApMgmtInterfaceIpV4State                                     CfprApVnicExternalMgmtIPMode,
    cfprApMgmtInterfaceIpV6State                                     CfprApVnicExternalMgmtIPMode,
    cfprApMgmtInterfaceIsDefaultDerived                              TruthValue,
    cfprApMgmtInterfaceMode                                          CfprApMgmtMode,
    cfprApMgmtInterfaceOperState                                     CfprApMgmtOperState
}

cfprApMgmtInterfaceInstanceId OBJECT-TYPE
    SYNTAX       CfprApManagedObjectId
    MAX-ACCESS   not-accessible
    STATUS       current
    DESCRIPTION
        "Instance identifier of the managed object."
    ::= { cfprApMgmtInterfaceEntry 1 }

cfprApMgmtInterfaceDn OBJECT-TYPE
    SYNTAX       CfprApManagedObjectDn
    MAX-ACCESS   read-only
    STATUS       current
    DESCRIPTION
        "Cisco Firepower mgmt:Interface:dn managed object property"
    ::= { cfprApMgmtInterfaceEntry 2 }

cfprApMgmtInterfaceRn OBJECT-TYPE
    SYNTAX       SnmpAdminString
    MAX-ACCESS   read-only
    STATUS       current
    DESCRIPTION
        "Cisco Firepower mgmt:Interface:rn managed object property"
    ::= { cfprApMgmtInterfaceEntry 3 }

cfprApMgmtInterfaceConfigMessage OBJECT-TYPE
    SYNTAX       SnmpAdminString
    MAX-ACCESS   read-only
    STATUS       current
    DESCRIPTION
        "Cisco Firepower mgmt:Interface:configMessage managed
        object property"
    ::= { cfprApMgmtInterfaceEntry 4 }

cfprApMgmtInterfaceConfigState OBJECT-TYPE
    SYNTAX       CfprApMgmtConfigState
    MAX-ACCESS   read-only
    STATUS       current
    DESCRIPTION
        "Cisco Firepower mgmt:Interface:configState managed
        object property"
    ::= { cfprApMgmtInterfaceEntry 5 }

cfprApMgmtInterfaceIpV4State OBJECT-TYPE
    SYNTAX       CfprApVnicExternalMgmtIPMode
    MAX-ACCESS   read-only
    STATUS       current
    DESCRIPTION
        "Cisco Firepower mgmt:Interface:ipV4State managed object property"
    ::= { cfprApMgmtInterfaceEntry 6 }

cfprApMgmtInterfaceIpV6State OBJECT-TYPE
    SYNTAX       CfprApVnicExternalMgmtIPMode
    MAX-ACCESS   read-only
    STATUS       current
    DESCRIPTION
        "Cisco Firepower mgmt:Interface:ipV6State managed object property"
    ::= { cfprApMgmtInterfaceEntry 7 }

cfprApMgmtInterfaceIsDefaultDerived OBJECT-TYPE
    SYNTAX       TruthValue
    MAX-ACCESS   read-only
    STATUS       current
    DESCRIPTION
        "Cisco Firepower mgmt:Interface:isDefaultDerived
        managed object property"
    ::= { cfprApMgmtInterfaceEntry 8 }

cfprApMgmtInterfaceMode OBJECT-TYPE
    SYNTAX       CfprApMgmtMode
    MAX-ACCESS   read-only
    STATUS       current
    DESCRIPTION
        "Cisco Firepower mgmt:Interface:mode managed object property"
    ::= { cfprApMgmtInterfaceEntry 9 }

cfprApMgmtInterfaceOperState OBJECT-TYPE
    SYNTAX       CfprApMgmtOperState
    MAX-ACCESS   read-only
    STATUS       current
    DESCRIPTION
        "Cisco Firepower mgmt:Interface:operState managed object property"
    ::= { cfprApMgmtInterfaceEntry 10 }

cfprApMgmtPmonEntryTable OBJECT-TYPE
    SYNTAX           SEQUENCE OF CfprApMgmtPmonEntryEntry
    MAX-ACCESS       not-accessible
    STATUS           current
    DESCRIPTION
        "Cisco Firepower mgmt:PmonEntry managed object table"
    ::= { cfprApMgmtObjects 43 }

cfprApMgmtPmonEntryEntry OBJECT-TYPE
    SYNTAX           CfprApMgmtPmonEntryEntry
    MAX-ACCESS       not-accessible
    STATUS           current
    DESCRIPTION
        "Entry for the cfprApMgmtPmonEntryTable table."
    INDEX { cfprApMgmtPmonEntryInstanceId }
    ::= { cfprApMgmtPmonEntryTable 1 }

CfprApMgmtPmonEntryEntry ::= SEQUENCE {
    cfprApMgmtPmonEntryInstanceId                                    CfprApManagedObjectId,
    cfprApMgmtPmonEntryDn                                            CfprApManagedObjectDn,
    cfprApMgmtPmonEntryRn                                            SnmpAdminString,
    cfprApMgmtPmonEntryExitSignal                                    Gauge32,
    cfprApMgmtPmonEntryFullPathname                                  SnmpAdminString,
    cfprApMgmtPmonEntryHeapSize                                      Unsigned64,
    cfprApMgmtPmonEntryHeapSize16Gb                                  Unsigned64,
    cfprApMgmtPmonEntryLastExitCode                                  Gauge32,
    cfprApMgmtPmonEntryMaxRetries                                    Gauge32,
    cfprApMgmtPmonEntryName                                          SnmpAdminString,
    cfprApMgmtPmonEntryRetries                                       Gauge32,
    cfprApMgmtPmonEntrySpuriousRetries                               Gauge32,
    cfprApMgmtPmonEntryState                                         CfprApMgmtPmonEntryState,
    cfprApMgmtPmonEntrySwitchId                                      CfprApNetworkSwitchId,
    cfprApMgmtPmonEntryWorkingDirectory                              SnmpAdminString
}

cfprApMgmtPmonEntryInstanceId OBJECT-TYPE
    SYNTAX       CfprApManagedObjectId
    MAX-ACCESS   not-accessible
    STATUS       current
    DESCRIPTION
        "Instance identifier of the managed object."
    ::= { cfprApMgmtPmonEntryEntry 1 }

cfprApMgmtPmonEntryDn OBJECT-TYPE
    SYNTAX       CfprApManagedObjectDn
    MAX-ACCESS   read-only
    STATUS       current
    DESCRIPTION
        "Cisco Firepower mgmt:PmonEntry:dn managed object property"
    ::= { cfprApMgmtPmonEntryEntry 2 }

cfprApMgmtPmonEntryRn OBJECT-TYPE
    SYNTAX       SnmpAdminString
    MAX-ACCESS   read-only
    STATUS       current
    DESCRIPTION
        "Cisco Firepower mgmt:PmonEntry:rn managed object property"
    ::= { cfprApMgmtPmonEntryEntry 3 }

cfprApMgmtPmonEntryExitSignal OBJECT-TYPE
    SYNTAX       Gauge32
    MAX-ACCESS   read-only
    STATUS       current
    DESCRIPTION
        "Cisco Firepower mgmt:PmonEntry:exitSignal managed
        object property"
    ::= { cfprApMgmtPmonEntryEntry 4 }

cfprApMgmtPmonEntryFullPathname OBJECT-TYPE
    SYNTAX       SnmpAdminString
    MAX-ACCESS   read-only
    STATUS       current
    DESCRIPTION
        "Cisco Firepower mgmt:PmonEntry:fullPathname managed
        object property"
    ::= { cfprApMgmtPmonEntryEntry 5 }

cfprApMgmtPmonEntryHeapSize OBJECT-TYPE
    SYNTAX       Unsigned64
    MAX-ACCESS   read-only
    STATUS       current
    DESCRIPTION
        "Cisco Firepower mgmt:PmonEntry:heapSize managed object property"
    ::= { cfprApMgmtPmonEntryEntry 6 }

cfprApMgmtPmonEntryHeapSize16Gb OBJECT-TYPE
    SYNTAX       Unsigned64
    MAX-ACCESS   read-only
    STATUS       current
    DESCRIPTION
        "Cisco Firepower mgmt:PmonEntry:heapSize16Gb managed
        object property"
    ::= { cfprApMgmtPmonEntryEntry 7 }

cfprApMgmtPmonEntryLastExitCode OBJECT-TYPE
    SYNTAX       Gauge32
    MAX-ACCESS   read-only
    STATUS       current
    DESCRIPTION
        "Cisco Firepower mgmt:PmonEntry:lastExitCode managed
        object property"
    ::= { cfprApMgmtPmonEntryEntry 8 }

cfprApMgmtPmonEntryMaxRetries OBJECT-TYPE
    SYNTAX       Gauge32
    MAX-ACCESS   read-only
    STATUS       current
    DESCRIPTION
        "Cisco Firepower mgmt:PmonEntry:maxRetries managed
        object property"
    ::= { cfprApMgmtPmonEntryEntry 9 }

cfprApMgmtPmonEntryName OBJECT-TYPE
    SYNTAX       SnmpAdminString
    MAX-ACCESS   read-only
    STATUS       current
    DESCRIPTION
        "Cisco Firepower mgmt:PmonEntry:name managed object property"
    ::= { cfprApMgmtPmonEntryEntry 10 }

cfprApMgmtPmonEntryRetries OBJECT-TYPE
    SYNTAX       Gauge32
    MAX-ACCESS   read-only
    STATUS       current
    DESCRIPTION
        "Cisco Firepower mgmt:PmonEntry:retries managed object property"
    ::= { cfprApMgmtPmonEntryEntry 11 }

cfprApMgmtPmonEntrySpuriousRetries OBJECT-TYPE
    SYNTAX       Gauge32
    MAX-ACCESS   read-only
    STATUS       current
    DESCRIPTION
        "Cisco Firepower mgmt:PmonEntry:spuriousRetries
        managed object property"
    ::= { cfprApMgmtPmonEntryEntry 12 }

cfprApMgmtPmonEntryState OBJECT-TYPE
    SYNTAX       CfprApMgmtPmonEntryState
    MAX-ACCESS   read-only
    STATUS       current
    DESCRIPTION
        "Cisco Firepower mgmt:PmonEntry:state managed object property"
    ::= { cfprApMgmtPmonEntryEntry 13 }

cfprApMgmtPmonEntrySwitchId OBJECT-TYPE
    SYNTAX       CfprApNetworkSwitchId
    MAX-ACCESS   read-only
    STATUS       current
    DESCRIPTION
        "Cisco Firepower mgmt:PmonEntry:switchId managed object property"
    ::= { cfprApMgmtPmonEntryEntry 14 }

cfprApMgmtPmonEntryWorkingDirectory OBJECT-TYPE
    SYNTAX       SnmpAdminString
    MAX-ACCESS   read-only
    STATUS       current
    DESCRIPTION
        "Cisco Firepower mgmt:PmonEntry:workingDirectory
        managed object property"
    ::= { cfprApMgmtPmonEntryEntry 15 }

cfprApMgmtProfDerivedInterfaceTable OBJECT-TYPE
    SYNTAX           SEQUENCE OF CfprApMgmtProfDerivedInterfaceEntry
    MAX-ACCESS       not-accessible
    STATUS           current
    DESCRIPTION
        "Cisco Firepower mgmt:ProfDerivedInterface managed object table"
    ::= { cfprApMgmtObjects 44 }

cfprApMgmtProfDerivedInterfaceEntry OBJECT-TYPE
    SYNTAX           CfprApMgmtProfDerivedInterfaceEntry
    MAX-ACCESS       not-accessible
    STATUS           current
    DESCRIPTION
        "Entry for the cfprApMgmtProfDerivedInterfaceTable table."
    INDEX { cfprApMgmtProfDerivedInterfaceInstanceId }
    ::= { cfprApMgmtProfDerivedInterfaceTable 1 }

CfprApMgmtProfDerivedInterfaceEntry ::= SEQUENCE {
    cfprApMgmtProfDerivedInterfaceInstanceId                         CfprApManagedObjectId,
    cfprApMgmtProfDerivedInterfaceDn                                 CfprApManagedObjectDn,
    cfprApMgmtProfDerivedInterfaceRn                                 SnmpAdminString,
    cfprApMgmtProfDerivedInterfaceConfigMessage                      SnmpAdminString,
    cfprApMgmtProfDerivedInterfaceConfigState                        CfprApMgmtConfigState,
    cfprApMgmtProfDerivedInterfaceIpV4State                          CfprApVnicExternalMgmtIPMode,
    cfprApMgmtProfDerivedInterfaceIpV6State                          CfprApVnicExternalMgmtIPMode,
    cfprApMgmtProfDerivedInterfaceMode                               CfprApMgmtMode,
    cfprApMgmtProfDerivedInterfaceOperState                          CfprApMgmtOperState
}

cfprApMgmtProfDerivedInterfaceInstanceId OBJECT-TYPE
    SYNTAX       CfprApManagedObjectId
    MAX-ACCESS   not-accessible
    STATUS       current
    DESCRIPTION
        "Instance identifier of the managed object."
    ::= { cfprApMgmtProfDerivedInterfaceEntry 1 }

cfprApMgmtProfDerivedInterfaceDn OBJECT-TYPE
    SYNTAX       CfprApManagedObjectDn
    MAX-ACCESS   read-only
    STATUS       current
    DESCRIPTION
        "Cisco Firepower mgmt:ProfDerivedInterface:dn managed
        object property"
    ::= { cfprApMgmtProfDerivedInterfaceEntry 2 }

cfprApMgmtProfDerivedInterfaceRn OBJECT-TYPE
    SYNTAX       SnmpAdminString
    MAX-ACCESS   read-only
    STATUS       current
    DESCRIPTION
        "Cisco Firepower mgmt:ProfDerivedInterface:rn managed
        object property"
    ::= { cfprApMgmtProfDerivedInterfaceEntry 3 }

cfprApMgmtProfDerivedInterfaceConfigMessage OBJECT-TYPE
    SYNTAX       SnmpAdminString
    MAX-ACCESS   read-only
    STATUS       current
    DESCRIPTION
        "Cisco Firepower mgmt:ProfDerivedInterface:configMessage
        managed object property"
    ::= { cfprApMgmtProfDerivedInterfaceEntry 4 }

cfprApMgmtProfDerivedInterfaceConfigState OBJECT-TYPE
    SYNTAX       CfprApMgmtConfigState
    MAX-ACCESS   read-only
    STATUS       current
    DESCRIPTION
        "Cisco Firepower mgmt:ProfDerivedInterface:configState
        managed object property"
    ::= { cfprApMgmtProfDerivedInterfaceEntry 5 }

cfprApMgmtProfDerivedInterfaceIpV4State OBJECT-TYPE
    SYNTAX       CfprApVnicExternalMgmtIPMode
    MAX-ACCESS   read-only
    STATUS       current
    DESCRIPTION
        "Cisco Firepower mgmt:ProfDerivedInterface:ipV4State
        managed object property"
    ::= { cfprApMgmtProfDerivedInterfaceEntry 6 }

cfprApMgmtProfDerivedInterfaceIpV6State OBJECT-TYPE
    SYNTAX       CfprApVnicExternalMgmtIPMode
    MAX-ACCESS   read-only
    STATUS       current
    DESCRIPTION
        "Cisco Firepower mgmt:ProfDerivedInterface:ipV6State
        managed object property"
    ::= { cfprApMgmtProfDerivedInterfaceEntry 7 }

cfprApMgmtProfDerivedInterfaceMode OBJECT-TYPE
    SYNTAX       CfprApMgmtMode
    MAX-ACCESS   read-only
    STATUS       current
    DESCRIPTION
        "Cisco Firepower mgmt:ProfDerivedInterface:mode
        managed object property"
    ::= { cfprApMgmtProfDerivedInterfaceEntry 8 }

cfprApMgmtProfDerivedInterfaceOperState OBJECT-TYPE
    SYNTAX       CfprApMgmtOperState
    MAX-ACCESS   read-only
    STATUS       current
    DESCRIPTION
        "Cisco Firepower mgmt:ProfDerivedInterface:operState
        managed object property"
    ::= { cfprApMgmtProfDerivedInterfaceEntry 9 }

cfprApMgmtVnetTable OBJECT-TYPE
    SYNTAX           SEQUENCE OF CfprApMgmtVnetEntry
    MAX-ACCESS       not-accessible
    STATUS           current
    DESCRIPTION
        "Cisco Firepower mgmt:Vnet managed object table"
    ::= { cfprApMgmtObjects 45 }

cfprApMgmtVnetEntry OBJECT-TYPE
    SYNTAX           CfprApMgmtVnetEntry
    MAX-ACCESS       not-accessible
    STATUS           current
    DESCRIPTION
        "Entry for the cfprApMgmtVnetTable table."
    INDEX { cfprApMgmtVnetInstanceId }
    ::= { cfprApMgmtVnetTable 1 }

CfprApMgmtVnetEntry ::= SEQUENCE {
    cfprApMgmtVnetInstanceId                                         CfprApManagedObjectId,
    cfprApMgmtVnetDn                                                 CfprApManagedObjectDn,
    cfprApMgmtVnetRn                                                 SnmpAdminString,
    cfprApMgmtVnetConfigState                                        CfprApMgmtConfigState,
    cfprApMgmtVnetId                                                 Gauge32,
    cfprApMgmtVnetName                                               SnmpAdminString
}

cfprApMgmtVnetInstanceId OBJECT-TYPE
    SYNTAX       CfprApManagedObjectId
    MAX-ACCESS   not-accessible
    STATUS       current
    DESCRIPTION
        "Instance identifier of the managed object."
    ::= { cfprApMgmtVnetEntry 1 }

cfprApMgmtVnetDn OBJECT-TYPE
    SYNTAX       CfprApManagedObjectDn
    MAX-ACCESS   read-only
    STATUS       current
    DESCRIPTION
        "Cisco Firepower mgmt:Vnet:dn managed object property"
    ::= { cfprApMgmtVnetEntry 2 }

cfprApMgmtVnetRn OBJECT-TYPE
    SYNTAX       SnmpAdminString
    MAX-ACCESS   read-only
    STATUS       current
    DESCRIPTION
        "Cisco Firepower mgmt:Vnet:rn managed object property"
    ::= { cfprApMgmtVnetEntry 3 }

cfprApMgmtVnetConfigState OBJECT-TYPE
    SYNTAX       CfprApMgmtConfigState
    MAX-ACCESS   read-only
    STATUS       current
    DESCRIPTION
        "Cisco Firepower mgmt:Vnet:configState managed object property"
    ::= { cfprApMgmtVnetEntry 4 }

cfprApMgmtVnetId OBJECT-TYPE
    SYNTAX       Gauge32
    MAX-ACCESS   read-only
    STATUS       current
    DESCRIPTION
        "Cisco Firepower mgmt:Vnet:id managed object property"
    ::= { cfprApMgmtVnetEntry 5 }

cfprApMgmtVnetName OBJECT-TYPE
    SYNTAX       SnmpAdminString
    MAX-ACCESS   read-only
    STATUS       current
    DESCRIPTION
        "Cisco Firepower mgmt:Vnet:name managed object property"
    ::= { cfprApMgmtVnetEntry 6 }

END
