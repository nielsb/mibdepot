--  3Com Switching Systems Products Management Information Base
--  Version 1.0.0
--  February 13, 1998

--  3Com Corporation
--  80 Central Street
--  Boxborough, MA 01719 
--  (978) 264-1400

-------------------------------------------------------------------------------
--
--  02/13/98 - rgd      Originally created
--
-------------------------------------------------------------------------------

A3COM-SWITCHING-SYSTEMS-PRODUCTS-MIB DEFINITIONS ::= BEGIN

IMPORTS
    enterprises                FROM RFC1155-SMI;

--  Object Identifiers
--
    a3Com                      OBJECT IDENTIFIER ::= { enterprises 43 }
    products                   OBJECT IDENTIFIER ::= { a3Com 1 } 
    switches                   OBJECT IDENTIFIER ::= { products 16 }
    corebuilderProductsIII     OBJECT IDENTIFIER ::= { switches 1 }
    superstackProducts         OBJECT IDENTIFIER ::= { switches 2 }

--  CoreBuilder Products
--
    corebuilderModularProducts OBJECT IDENTIFIER ::= { corebuilderProductsIII 1 }
    corebuilderSystemProducts  OBJECT IDENTIFIER ::= { corebuilderProductsIII 2 }
    corebuilderChassisProducts OBJECT IDENTIFIER ::= { corebuilderProductsIII 3 }	

--  CoreBuilder Families
--
    cbModular3500Family        OBJECT IDENTIFIER ::= { corebuilderModularProducts 1  }
    cbSystem9400Family         OBJECT IDENTIFIER ::= { corebuilderSystemProducts 1 }

--  CoreBuilder Product Types
--
    cb3500                     OBJECT IDENTIFIER ::= { cbModular3500Family 1 }
    cb9400                     OBJECT IDENTIFIER ::= { cbSystem9400Family 1 }

--  SuperStack Products
--
    superstackModularProducts  OBJECT IDENTIFIER ::= { superstackProducts 1 }
    superstackSystemProducts   OBJECT IDENTIFIER ::= { superstackProducts 2 }
    superstackChassisProducts  OBJECT IDENTIFIER ::= { superstackProducts 3 }

--  SuperStack Families
--
    ssSystem3900Family         OBJECT IDENTIFIER ::= { superstackSystemProducts 1 }
    ssSystem9300Family         OBJECT IDENTIFIER ::= { superstackSystemProducts 2 }

--  SuperStack Product Types
--
    ss3900-24                  OBJECT IDENTIFIER ::= { ssSystem3900Family 1 }
    ss3900-36                  OBJECT IDENTIFIER ::= { ssSystem3900Family 2 }
    ss9300                     OBJECT IDENTIFIER ::= { ssSystem9300Family 1 }

END
