-- *******************************************************************
-- CISCO-LWAPP-NBAR-MIB.my 
-- June 2012, Venkatesh Puranik
--
-- Copyright (c) 2011-2012, 2015 by Cisco Systems, Inc.
-- All rights reserved.
-- *******************************************************************
--
CISCO-LWAPP-NBAR-MIB DEFINITIONS ::= BEGIN

IMPORTS 
        MODULE-IDENTITY, 
        OBJECT-TYPE,
        NOTIFICATION-TYPE,
        Unsigned32
                FROM SNMPv2-SMI
        MODULE-COMPLIANCE, 
        OBJECT-GROUP,
        NOTIFICATION-GROUP
                FROM SNMPv2-CONF
        RowStatus
                FROM SNMPv2-TC
        SnmpAdminString
                FROM SNMP-FRAMEWORK-MIB
        ciscoMgmt
                FROM CISCO-SMI;
                
--********************************************************************
--*  MODULE IDENTITY
--********************************************************************

ciscoLwappNbarMIB        MODULE-IDENTITY
        LAST-UPDATED   "201206120000Z"
        ORGANIZATION   "Cisco Systems Inc."
        CONTACT-INFO  
               "        Cisco Systems,
                        Customer Service

                Postal: 170 West Tasman Drive
                        San Jose, CA  95134
                        USA

                   Tel: +1 800 553-NETS

                 Email: cs-snmp@cisco.com"

        DESCRIPTION             
          "NBAR - Network Based Application Recognition is
	   an intelligent classification engine that recognizes 
	   applications that are static (which use fixed TCP or
	   UDP port numbers), and stateful (which dynamically 
	   assign TCP or UDP port numbers).
                       
                     GLOSSARY 
                 
           Access Point ( AP )

           An entity that contains an 802.11 medium access
           control ( MAC ) and physical layer ( PHY ) interface
           and provides access to the distribution services via
           the wireless medium for associated clients.  

           LWAPP APs encapsulate all the 802.11 frames in
           LWAPP frames and sends it to the controller to which
           it is logically connected to.

           Central Controller ( CC )

           The central entity that terminates the LWAPP protocol
           tunnel from the LWAPP APs.  Throughout this MIB,
           this entity also referred to as 'controller'.

           Light Weight Access Point Protocol ( LWAPP ) 

           This is a generic protocol that defines the
           communication between the Access Points and the
           controllers.

           Mobile Node ( MN )

           A roaming 802.11 wireless device in a wireless
           network associated with an access point.

           AVC - Application Visiblity and Control.
           The client application or protocol statistics and control."

        REVISION      "201206120000Z"
        DESCRIPTION
                "Initial version of this MIB module."
        ::= { ciscoMgmt 99995 }

ciscoLwappNbarMIBNotifs  OBJECT IDENTIFIER 
        ::= { ciscoLwappNbarMIB 0 }
ciscoLwappNbarMIBObjects OBJECT IDENTIFIER 
        ::= { ciscoLwappNbarMIB 1 }
ciscoLwappNbarMIBConform OBJECT IDENTIFIER 
        ::= { ciscoLwappNbarMIB 2 }
ciscoLwappNbarTableObjects OBJECT IDENTIFIER 
        ::= { ciscoLwappNbarMIBObjects 1 }
ciscoLwappNbarGlobalObjects  OBJECT IDENTIFIER
        ::= { ciscoLwappNbarMIBObjects 2 }

cLNbarAVCEngineVersion OBJECT-TYPE
    SYNTAX         OCTET STRING 
    MAX-ACCESS      read-only
    STATUS          current
    DESCRIPTION
        "This object reptresents the AVC Engine version
        "
    ::= { ciscoLwappNbarGlobalObjects 1 }

cLNbarAVCProtoPackName OBJECT-TYPE
    SYNTAX         OCTET STRING
    MAX-ACCESS      read-only
    STATUS          current
    DESCRIPTION
        "This object reptresents the AVC Protocol Pack Name
        "
    ::= { ciscoLwappNbarGlobalObjects 2 }


cLNbarAVCProtoPackVer OBJECT-TYPE
    SYNTAX         OCTET STRING
    MAX-ACCESS      read-only
    STATUS          current
    DESCRIPTION
        "This object represents the AVC Protocol Pack version
        "
    ::= { ciscoLwappNbarGlobalObjects 3 }

cLNbarAVCFlexEngineVersion OBJECT-TYPE
    SYNTAX         OCTET STRING
    MAX-ACCESS      read-only
    STATUS          current
    DESCRIPTION
        "This object reptresents the AVC Engine version
        "
    ::= { ciscoLwappNbarGlobalObjects 4 }

cLNbarAVCFlexProtoPackName OBJECT-TYPE
    SYNTAX         OCTET STRING
    MAX-ACCESS      read-only
    STATUS          current
    DESCRIPTION
        "This object reptresents the AVC Protocol Pack Name
        "
    ::= { ciscoLwappNbarGlobalObjects 5 }


cLNbarAVCFlexProtoPackVer OBJECT-TYPE
    SYNTAX         OCTET STRING
    MAX-ACCESS      read-only
    STATUS          current
    DESCRIPTION
        "This object represents the AVC Protocol Pack version
        "
    ::= { ciscoLwappNbarGlobalObjects 6 }

-- *******************************************************************
-- AVC Profile table
-- *******************************************************************

cLNbarAVCProfileTable OBJECT-TYPE
        SYNTAX     SEQUENCE OF CLNbarAVCProfileEntry
        MAX-ACCESS not-accessible
        STATUS     current
        DESCRIPTION
            " This table represents the information about 
              application visibility and control (AVC) profiles"
        ::= { ciscoLwappNbarTableObjects 1 }

cLNbarAVCProfileEntry OBJECT-TYPE
        SYNTAX     CLNbarAVCProfileEntry
        MAX-ACCESS not-accessible
        STATUS     current
        DESCRIPTION
            "An entry containing the configuration attributes
             of application visibility and control for NBAR."
        INDEX   { cLNbarAVCProfileName }
        ::= { cLNbarAVCProfileTable 1 }

CLNbarAVCProfileEntry ::= 
        SEQUENCE {
                cLNbarAVCProfileName       SnmpAdminString,  
                cLNbarAVCProfileRowStatus  RowStatus
        }

cLNbarAVCProfileName OBJECT-TYPE
        SYNTAX        SnmpAdminString (SIZE (1..32))
        MAX-ACCESS    not-accessible
        STATUS        current
        DESCRIPTION
                "This object represents the AVC profile name."
        ::= { cLNbarAVCProfileEntry 1 }

cLNbarAVCProfileRowStatus OBJECT-TYPE
        SYNTAX RowStatus
        MAX-ACCESS read-create
        STATUS current
        DESCRIPTION
                "This object creates or deletes an entry in this table."
        ::= { cLNbarAVCProfileEntry 2 }

-- *******************************************************************
-- AVC Rule table
-- *******************************************************************

cLNbarAVCRuleTable OBJECT-TYPE
        SYNTAX     SEQUENCE OF CLNbarAVCRuleEntry
        MAX-ACCESS not-accessible
        STATUS     current
        DESCRIPTION
            " This table represents the information about 
              AVC Rule"
        ::= { ciscoLwappNbarTableObjects 2 }

cLNbarAVCRuleEntry OBJECT-TYPE
        SYNTAX     CLNbarAVCRuleEntry
        MAX-ACCESS not-accessible
        STATUS     current
        DESCRIPTION
            "An entry containing the configuration attributes
             of AVC rule for NBAR."
        INDEX   { cLNbarAVCRuleProfileName,
                  cLNbarAVCRuleApplicationName }
        ::= { cLNbarAVCRuleTable 1 }

CLNbarAVCRuleEntry ::= 
        SEQUENCE {
                cLNbarAVCRuleProfileName            SnmpAdminString,  
                cLNbarAVCRuleApplicationName        SnmpAdminString,
                cLNbarAVCRuleApplicationGroupName   SnmpAdminString,
                cLNbarAVCRuleApplicationAction      INTEGER,
                cLNbarAVCRuleDscpValue              Unsigned32,
                cLNbarAVCRuleRowStatus              RowStatus,
                cLNbarAVCRuleAppAvgRateLimit        Unsigned32,
                cLNbarAVCRuleAppBurstRateLimit      Unsigned32
        }

cLNbarAVCRuleProfileName OBJECT-TYPE
        SYNTAX       SnmpAdminString (SIZE (1..32))
        MAX-ACCESS   not-accessible
        STATUS       current
        DESCRIPTION
                "This object represents the AVC profile name."
        ::= { cLNbarAVCRuleEntry 1 }

cLNbarAVCRuleApplicationName OBJECT-TYPE
        SYNTAX       SnmpAdminString 
        MAX-ACCESS   not-accessible
        STATUS       current
        DESCRIPTION
                "This object represents the name of application or protocol."
        ::= { cLNbarAVCRuleEntry 2 }

cLNbarAVCRuleApplicationGroupName OBJECT-TYPE
        SYNTAX       SnmpAdminString
        MAX-ACCESS   read-create
        STATUS       current
        DESCRIPTION
                "This object represents the name of application group."
        ::= { cLNbarAVCRuleEntry 3 }

cLNbarAVCRuleApplicationAction OBJECT-TYPE
        SYNTAX       INTEGER {
                        drop (2),
                        mark (3),
                        ratelimit (4)
                     }
        MAX-ACCESS   read-create 
        STATUS       current
        DESCRIPTION
                "This object represents the action for the application or protocol.
                 drop - the corresponding application or protocol packets will be dropped.
                 mark - the corresponding application or protocol packets will be marked
                        with DSCP value.
                 ratelimit - the corresponding application or protocol packets will be 
                        rate limited with Average and Burst rate limit values."
        ::= { cLNbarAVCRuleEntry 4 }

cLNbarAVCRuleDscpValue OBJECT-TYPE
        SYNTAX       Unsigned32
        MAX-ACCESS   read-create
        STATUS       current
        DESCRIPTION
                "This object represents the DSCP value."
        ::= { cLNbarAVCRuleEntry 5 }

cLNbarAVCRuleRowStatus OBJECT-TYPE
        SYNTAX       RowStatus
        MAX-ACCESS   read-create
        STATUS       current
        DESCRIPTION
                "This object creates or deletes an entry in this table."
        ::= { cLNbarAVCRuleEntry 6 }

cLNbarAVCRuleAppAvgRateLimit      OBJECT-TYPE
        SYNTAX       Unsigned32
        MAX-ACCESS   read-create
        STATUS       current
        DESCRIPTION
                "This object represents the Application Average data rate limit"
        ::= { cLNbarAVCRuleEntry 7 }

cLNbarAVCRuleAppBurstRateLimit      OBJECT-TYPE
        SYNTAX       Unsigned32
        MAX-ACCESS   read-create
        STATUS       current
        DESCRIPTION
                "This object represents the Application Burst data rate limit"
        ::= { cLNbarAVCRuleEntry 8 }

-- *******************************************************************
-- AVC FLEX Profile table
-- *******************************************************************

cLNbarAVCFlexProfileTable OBJECT-TYPE
        SYNTAX     SEQUENCE OF CLNbarAVCFlexProfileEntry
        MAX-ACCESS not-accessible
        STATUS     current
        DESCRIPTION
            " This table represents the information about
              application visibility and control (AVC) profiles"
        ::= { ciscoLwappNbarTableObjects 3 }

cLNbarAVCFlexProfileEntry OBJECT-TYPE
        SYNTAX     CLNbarAVCFlexProfileEntry
        MAX-ACCESS not-accessible
        STATUS     current
        DESCRIPTION
            "An entry containing the configuration attributes
             of application visibility and control for NBAR."
        INDEX   { cLNbarAVCFlexProfileName }
        ::= { cLNbarAVCFlexProfileTable 1 }

CLNbarAVCFlexProfileEntry ::=
        SEQUENCE {
                cLNbarAVCFlexProfileName       SnmpAdminString,
                cLNbarAVCFlexProfileApply      INTEGER,
                cLNbarAVCFlexProfileRowStatus  RowStatus
        }

cLNbarAVCFlexProfileName OBJECT-TYPE
        SYNTAX        SnmpAdminString (SIZE (1..32))
        MAX-ACCESS    not-accessible
        STATUS        current
        DESCRIPTION
                "This object represents the AVC profile name."
        ::= { cLNbarAVCFlexProfileEntry 1 }

cLNbarAVCFlexProfileApply OBJECT-TYPE
        SYNTAX       INTEGER {
                        modified (0),
                        apply (1)
                     }
        MAX-ACCESS    read-write
        STATUS        current
        DESCRIPTION
                "This object is used to push profile configured on controller to AP.
                 apply - Profile will be applied to AP. modified is not allowed to set."
        ::= { cLNbarAVCFlexProfileEntry 2 }

cLNbarAVCFlexProfileRowStatus OBJECT-TYPE
        SYNTAX RowStatus
        MAX-ACCESS read-create
        STATUS current
        DESCRIPTION
                "This object creates or deletes an entry in this table."
        ::= { cLNbarAVCFlexProfileEntry 3 }

-- *******************************************************************
-- AVC Flex Rule table
-- *******************************************************************
cLNbarAVCFlexRuleTable OBJECT-TYPE
        SYNTAX     SEQUENCE OF CLNbarAVCFlexRuleEntry
        MAX-ACCESS not-accessible
        STATUS     current
        DESCRIPTION
            " This table represents the information about
              AVC Rule"
        ::= { ciscoLwappNbarTableObjects 4 }

cLNbarAVCFlexRuleEntry OBJECT-TYPE
        SYNTAX     CLNbarAVCFlexRuleEntry
        MAX-ACCESS not-accessible
        STATUS     current
        DESCRIPTION
            "An entry containing the configuration attributes
             of AVC rule for NBAR."
        INDEX   { cLNbarAVCFlexRuleProfileName,
                  cLNbarAVCFlexRuleApplicationName }
        ::= { cLNbarAVCFlexRuleTable 1 }

CLNbarAVCFlexRuleEntry ::=
        SEQUENCE {
                cLNbarAVCFlexRuleProfileName            SnmpAdminString,
                cLNbarAVCFlexRuleApplicationName        SnmpAdminString,
                cLNbarAVCFlexRuleApplicationGroupName   SnmpAdminString,
                cLNbarAVCFlexRuleApplicationAction      INTEGER,
                cLNbarAVCFlexRuleDscpValue              Unsigned32,
                cLNbarAVCFlexRuleRowStatus              RowStatus,
                cLNbarAVCFlexRuleAppAvgRateLimit        Unsigned32,
                cLNbarAVCFlexRuleAppBurstRateLimit      Unsigned32
        }

cLNbarAVCFlexRuleProfileName OBJECT-TYPE
        SYNTAX       SnmpAdminString (SIZE (1..32))
        MAX-ACCESS   not-accessible
        STATUS       current
        DESCRIPTION
                "This object represents the AVC profile name."
        ::= { cLNbarAVCFlexRuleEntry 1 }

cLNbarAVCFlexRuleApplicationName OBJECT-TYPE
        SYNTAX       SnmpAdminString
        MAX-ACCESS   not-accessible
        STATUS       current
        DESCRIPTION
                "This object represents the name of application or protocol."
        ::= { cLNbarAVCFlexRuleEntry 2 }

cLNbarAVCFlexRuleApplicationGroupName OBJECT-TYPE
        SYNTAX       SnmpAdminString
        MAX-ACCESS   read-create
        STATUS       current
        DESCRIPTION
                "This object represents the name of application group."
        ::= { cLNbarAVCFlexRuleEntry 3 }

cLNbarAVCFlexRuleApplicationAction OBJECT-TYPE
        SYNTAX       INTEGER {
                        drop (2),
                        mark (3),
                        ratelimit (4)
                     }
        MAX-ACCESS   read-create
        STATUS       current
        DESCRIPTION
                "This object represents the action for the application or protocol.
                 drop - the corresponding application or protocol packets will be dropped.
                 mark - the corresponding application or protocol packets will be marked
                        with DSCP value.
                 ratelimit - the corresponding application or protocol packets will be
                        rate limited with Average and Burst rate limit values."
        ::= { cLNbarAVCFlexRuleEntry 4 }

cLNbarAVCFlexRuleDscpValue OBJECT-TYPE
        SYNTAX       Unsigned32
        MAX-ACCESS   read-create
        STATUS       current
        DESCRIPTION
                "This object represents the DSCP value."
        ::= { cLNbarAVCFlexRuleEntry 5 }

cLNbarAVCFlexRuleRowStatus OBJECT-TYPE
        SYNTAX       RowStatus
        MAX-ACCESS   read-create
        STATUS       current
        DESCRIPTION
                "This object creates or deletes an entry in this table."
        ::= { cLNbarAVCFlexRuleEntry 6 }

cLNbarAVCFlexRuleAppAvgRateLimit      OBJECT-TYPE
        SYNTAX       Unsigned32
        MAX-ACCESS   read-create
        STATUS       current
        DESCRIPTION
                "This object represents the Application Average data rate limit"
        ::= { cLNbarAVCFlexRuleEntry 7 }

cLNbarAVCFlexRuleAppBurstRateLimit      OBJECT-TYPE
        SYNTAX       Unsigned32
        MAX-ACCESS   read-create
        STATUS       current
        DESCRIPTION
                "This object represents the Application Burst data rate limit"
        ::= { cLNbarAVCFlexRuleEntry 8 }

--*******************************************************************

cLAVCProtoPackLoadNotifFailed NOTIFICATION-TYPE
    OBJECTS         {
                        cLNbarAVCProtoPackName,
                        cLNbarAVCProtoPackVer
                    }
    STATUS          current
    DESCRIPTION
        "This notification is generated whenever a protocol pack download 
        fails."
    ::= { ciscoLwappNbarMIBNotifs 1 }


cLAVCProtoPackLoadNotifSuccess NOTIFICATION-TYPE
    OBJECTS         {
                        cLNbarAVCProtoPackName,
                        cLNbarAVCProtoPackVer
                    }
    STATUS          current
    DESCRIPTION
        "This notification is generated whenever a protocol pack download
        succeeds."
    ::= { ciscoLwappNbarMIBNotifs 2 }






--*******************************************************************
--*   END OF -  NOTIFICATIONS
--*******************************************************************

--*******************************************************************
--*    Compliance statements  
--*******************************************************************

ciscoLwappNbarMIBCompliances OBJECT IDENTIFIER
        ::= { ciscoLwappNbarMIBConform 1 }

ciscoLwappNbarMIBGroups OBJECT IDENTIFIER
        ::= { ciscoLwappNbarMIBConform 2 }

ciscoLwappNbarMIBCompliance MODULE-COMPLIANCE
    STATUS         deprecated
 
    DESCRIPTION
        "The compliance statement for the SNMP entities that
        implement the ciscoLwappNbarMIB module."
    MODULE          -- this module
    MANDATORY-GROUPS { cLNbarConfigGroup }
    ::= { ciscoLwappNbarMIBCompliances 1 }


ciscoLwappNbarMIBComplianceRev1 MODULE-COMPLIANCE
    STATUS          current
    DESCRIPTION
        "The compliance statement for the SNMP entities that
        implement the ciscoLwappNbarMIB module."
    MODULE          -- this module
    MANDATORY-GROUPS { cLNbarConfigGroup, 
                       cLNbarGlobalGroup
                     }
    ::= { ciscoLwappNbarMIBCompliances 2 }


-- *******************************************************************
-- *    Units of conformance
-- *******************************************************************
cLNbarConfigGroup OBJECT-GROUP
    OBJECTS         {
                        cLNbarAVCProfileName, 
                        cLNbarAVCProfileRowStatus, 
                        cLNbarAVCRuleProfileName, 
                        cLNbarAVCRuleApplicationName,
                        cLNbarAVCRuleApplicationGroupName,
                        cLNbarAVCRuleApplicationAction,
                        cLNbarAVCRuleDscpValue,
                        cLNbarAVCRuleRowStatus,
                        cLNbarAVCFlexProfileName,
                        cLNbarAVCFlexProfileRowStatus,
                        cLNbarAVCFlexRuleProfileName,
                        cLNbarAVCFlexRuleApplicationName,
                        cLNbarAVCFlexRuleApplicationGroupName,
                        cLNbarAVCFlexRuleApplicationAction,
                        cLNbarAVCFlexRuleDscpValue,
                        cLNbarAVCFlexRuleRowStatus
                    }
    STATUS          current
    DESCRIPTION
        "This is a collection of objects which can
        be configured to control NBAR parameters."
    ::= { ciscoLwappNbarMIBGroups 1 }

cLNbarGlobalGroup OBJECT-GROUP
    OBJECTS         {
                        cLNbarAVCEngineVersion,
                        cLNbarAVCProtoPackVer,
                        cLNbarAVCProtoPackName,
                        cLNbarAVCFlexEngineVersion,
                        cLNbarAVCFlexProtoPackVer,
                        cLNbarAVCFlexProtoPackName
                    }
    STATUS          current
    DESCRIPTION
        "This is a collection of objects which can
        be configured to control NBAR parameters."
    ::= { ciscoLwappNbarMIBGroups 2 }

END
