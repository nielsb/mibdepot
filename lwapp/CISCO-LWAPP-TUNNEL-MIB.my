-- *******************************************************************
-- CISCO-LWAPP-PMIP-MIB.my 
-- 2014, Ramachandra Murthy 
-- Copyright (c) 2014 by Cisco Systems Inc.
-- All rights reserved.
-- *******************************************************************

CISCO-LWAPP-TUNNEL-MIB DEFINITIONS ::= BEGIN

IMPORTS 
        MODULE-IDENTITY, 
        OBJECT-TYPE,
        NOTIFICATION-TYPE,
        Unsigned32,
        Counter32,
        TimeTicks,
        Gauge32,
        Integer32
                FROM SNMPv2-SMI
        MODULE-COMPLIANCE, 
        NOTIFICATION-GROUP,
        OBJECT-GROUP
                FROM SNMPv2-CONF
        DisplayString,
        TruthValue,
        MacAddress,
        TimeInterval,
        RowStatus,
        TimeStamp
                FROM SNMPv2-TC 
        SnmpAdminString
                FROM SNMP-FRAMEWORK-MIB 
        InetAddressType,
        InetAddress,
        InetPortNumber
                FROM INET-ADDRESS-MIB
        cLWlanIndex
                FROM CISCO-LWAPP-WLAN-MIB 
        cldcClientMacAddress
                FROM CISCO-LWAPP-DOT11-CLIENT-MIB
        ciscoMgmt
                FROM CISCO-SMI;


--********************************************************************
--*  MODULE IDENTITY
--********************************************************************

ciscoLwappTunnelMIB       MODULE-IDENTITY
        LAST-UPDATED    "201112220000Z"
        ORGANIZATION    "Cisco Systems Inc."
        CONTACT-INFO  
               "        Cisco Systems,
                        Customer Service

                Postal: 170 West Tasman Drive
                        San Jose, CA  95134
                        USA

                   Tel: +1 800 553-NETS

                 Email: cs-snmp@cisco.com"

        DESCRIPTION             
                "This MIB is intended to be implemented on all those
                devices operating as Central Controllers (CC) that
                terminate the Light Weight Access Point Protocol
                tunnel from Light-weight LWAPP Access Points.

                This MIB provides configuration and status information
                about local mobility anchor to which the controller has 
                the joined.                  

                The relationship between CC and the LWAPP APs
                can be depicted as follows:

        +......+     +......+     +......+           +......+
        +      +     +      +     +      +           +      +
        +  LMA +     + LMA  +     + LMA  +           + LMA  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  WLC + + WLC  +     + WLC  +      + WLC  +          + WLC  +
   +      + +      +     +      +      +      +          +      +
   +......+ +......+     +......+      +......+          +......+
              .              .             .                 .
            .  .              .             .                 .
           .    .              .             .                 .
          .      .              .             .                 .
         .        .              .             .                 .
   +......+ +......+     +......+      +......+          +......+
   +      + +      +     +      +      +      +          +      +
   +  AP  + +  AP  +     +  AP  +      +  AP  +          +  AP  +
   +      + +      +     +      +      +      +          +      +
   +......+ +......+     +......+      +......+          +......+
             .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.
               
                                   GLOSSARY
 
                Access Point ( AP )

                An entity that contains an 802.11 medium access
                control ( MAC ) and physical layer ( PHY ) interface
                and provides access to the distribution services via
                the wireless medium for associated clients.  

                LWAPP APs encapsulate all the 802.11 frames in
                LWAPP frames and sends it to the controller to which
                it is logically connected.

                Central Controller ( CC )

                The central entity that terminates the LWAPP protocol
                tunnel from the LWAPP APs.  Throughout this MIB,
                this entity also referred to as 'controller'. 

                Light Weight Access Point Protocol ( LWAPP ) 

                This is a generic protocol that defines the 
                communication between the Access Points and the
                Central Controller. 

                Mobile Node ( MN )

                A roaming 802.11 wireless device in a wireless
                network associated with an access point. 

                Gateway
           
                Service provider node which assigns IP and maintains the
                tunneled clients.
              
                Tunnel
            
                Connection from Wireless LAN controller to the Gateway.

                REFERENCE
 
                [1] Part 11 Wireless LAN Medium Access Control ( MAC )
                and Physical Layer ( PHY ) Specifications.
  
                [2] Draft-obara-capwap-lwapp-00.txt, IETF Light 
                Weight Access Point Protocol. "
        
        REVISION      "201112220000Z"
        DESCRIPTION
                "Initial version of this MIB module. "
        ::= { ciscoMgmt 9878 }

ciscoLwappTunnelNotifs  OBJECT IDENTIFIER ::= { ciscoLwappTunnelMIB 0 }
ciscoLwappTunnelMIBObjects OBJECT IDENTIFIER      ::= { ciscoLwappTunnelMIB 1 }

--********************************************************************
--*    Notification Objects
--********************************************************************
cLWATunnelStatusChangeReasonCode OBJECT-TYPE
    SYNTAX          INTEGER  {
                        down(0),
                        up(1),
                        progress(2)
                    }
    MAX-ACCESS      accessible-for-notify 
    STATUS          current
    DESCRIPTION
        "This object represents Tunnel status reason code
        Down                  - Tunnel is Down 
        Up                    - Tunnel is Up
        Progress              - Client Deletion for that Tunnel in progress."
        ::= { ciscoLwappTunnelMIBObjects 1 }

cLWATunnelGwIP OBJECT-TYPE
    SYNTAX          InetAddress 
    MAX-ACCESS      accessible-for-notify 
    STATUS          current
    DESCRIPTION
        "This object represents Tunnel Gateway IP."
        ::= { ciscoLwappTunnelMIBObjects 2 }

cLWATunnelGwName OBJECT-TYPE
    SYNTAX          SnmpAdminString
    MAX-ACCESS      accessible-for-notify 
    STATUS          current
    DESCRIPTION
        "This object represents Tunnel Gateway Name."
        ::= { ciscoLwappTunnelMIBObjects 3 }

cLWATunnelType OBJECT-TYPE
    SYNTAX          INTEGER  {
                    none(0),
                    pmipv6(1),
                    gtpv2(2),
                    eogre(3)
                    }
    MAX-ACCESS      accessible-for-notify 
    STATUS          current
    DESCRIPTION
        "This object represents tunnel type.
        none                  - unknown tunnel
        pmipv6                - pmipv6 tunnel type 
        gtpv2                 - gtpv2 tunnel type 
        eogre                 - eogre tunnel type." 
        ::= { ciscoLwappTunnelMIBObjects 4 }

cLWATunnelDomainName OBJECT-TYPE
    SYNTAX          SnmpAdminString
    MAX-ACCESS      accessible-for-notify 
    STATUS          current
    DESCRIPTION
        "This object represents Tunnel Domain Name."
        ::= { ciscoLwappTunnelMIBObjects 5 }

cLWATunnelActiveGwIP OBJECT-TYPE
    SYNTAX          InetAddress 
    MAX-ACCESS      accessible-for-notify 
    STATUS          current
    DESCRIPTION
        "This object represents Tunnel Active Tunnel Gateway IP in Domain."
        ::= { ciscoLwappTunnelMIBObjects 6 }

cLWATunnelActiveGwName OBJECT-TYPE
    SYNTAX          SnmpAdminString
    MAX-ACCESS      accessible-for-notify 
    STATUS          current
    DESCRIPTION
        "This object represents Tunnel Active Gateway Name in Domain."
        ::= { ciscoLwappTunnelMIBObjects 7 }

cLWATunnelProfileName OBJECT-TYPE
    SYNTAX          SnmpAdminString
    MAX-ACCESS      accessible-for-notify
    STATUS          current
    DESCRIPTION
         "This object represents Tunnel Profile Name."
         ::= { ciscoLwappTunnelMIBObjects 8 }

cLWATunnelRealm OBJECT-TYPE
    SYNTAX          SnmpAdminString
    MAX-ACCESS      accessible-for-notify
    STATUS          current
    DESCRIPTION
        "This object represents Realm of
        the user.
        eg. In airtel@a.com username, a.com is realm of the user"
        ::= { ciscoLwappTunnelMIBObjects 9 }

cLWATunnelVlanId    OBJECT-TYPE
    SYNTAX          Unsigned32 
    MAX-ACCESS      accessible-for-notify
    STATUS          current
    DESCRIPTION
        "This object represents Tunnel Vlan Id."
        ::= { ciscoLwappTunnelMIBObjects 10 }

cLWATunnelClientMacAddress OBJECT-TYPE
     SYNTAX     MacAddress
     MAX-ACCESS not-accessible
     STATUS     current
     DESCRIPTION
         "This object specifies the MAC address of the
         client for this entry  and uniquely identifies
         this entry. "
         ::= { ciscoLwappTunnelMIBObjects 11 }

cLWATunnelClientTypeChangeReasonCode OBJECT-TYPE
    SYNTAX          INTEGER  {
                    staticProfile(1),
                    aaaOveride(2), 
                    dot1xAuthentication(3),
                    mobilityHandoff(4)
                   }
    MAX-ACCESS      accessible-for-notify
    STATUS          current
    DESCRIPTION
        "This object represents Tunnel Client Type change reason code
         staticProfile       - when wlan static profile applied. 
         AAAOveride          - when AAA override parameters are applied. 
         dot1xAuthentication - when dot1x authentication completes. 
         mobilityHandoff     - when mobility handoff happens."
        ::= { ciscoLwappTunnelMIBObjects 11 }

--********************************************************************
--*    Notifications
--********************************************************************
cLWATunnelStatusChange     NOTIFICATION-TYPE
        OBJECTS {
               cLWATunnelGwName,
               cLWATunnelGwIP,
               cLWATunnelType,
               cLWATunnelStatusChangeReasonCode 
        }
        STATUS  current
        DESCRIPTION
             " This notification is to send when Tunnel status Changes."
        ::= { ciscoLwappTunnelNotifs 1 }

cLWATunnelDomainStatusChange     NOTIFICATION-TYPE
        OBJECTS {
               cLWATunnelDomainName,
               cLWATunnelType,
               cLWATunnelActiveGwIP,
               cLWATunnelActiveGwName
        }
        STATUS  current
        DESCRIPTION
             " This notification is to send when Active Gateway is changed in a Domain."
        ::= { ciscoLwappTunnelNotifs 2 }
  
cLWATunnelClientTypeChange     NOTIFICATION-TYPE
       OBJECTS {
              cLWATunnelClientMacAddress,
              cLWATunnelProfileName,
              cLWATunnelRealm,
              cLWATunnelVlanId,
              cLWATunnelDomainName,
              cLWATunnelType,
              cLWATunnelActiveGwIP,
              cLWATunnelActiveGwName,
              cLWATunnelClientTypeChangeReasonCode
       }
       STATUS  current
       DESCRIPTION
            " This notification is to send when client type is marked as 
            eogre tunnel user."
       ::= { ciscoLwappTunnelNotifs 3 }

--***************************************************************************
--* Tunnel Gateway Tables
--***************************************************************************
ciscoLwappGatewayTunnel OBJECT IDENTIFIER
             ::= { ciscoLwappTunnelMIB 2 }

clGatewayTunnelTable  OBJECT-TYPE
        SYNTAX              SEQUENCE OF  ClGatewayTunnelEntry
        MAX-ACCESS          not-accessible
        STATUS              current
        DESCRIPTION
             "The table list the tunnel gateways ."
        ::= { ciscoLwappGatewayTunnel 1 }

clGatewayTunnelEntry OBJECT-TYPE
        SYNTAX              ClGatewayTunnelEntry
        MAX-ACCESS          not-accessible
        STATUS              current
        DESCRIPTION
             "Each entry represents a conceptual row in this table.
              For each tunnel created to the gateway, there will be a row. "
        INDEX      { clGatewayTunnelName, 
                     clGatewayTunnelType }
        ::= { clGatewayTunnelTable 1 }

ClGatewayTunnelEntry ::= SEQUENCE {
        clGatewayTunnelName                OCTET STRING,
        clGatewayTunnelType                INTEGER,
        clGatewayTunnelIpv4Address         IpAddress,
        clGatewayTunnelIpAddressType       InetAddressType,
        clGatewayTunnelIpv6Address         InetAddress,
        clGatewayTunnelStatus              TruthValue,
        clGatewayTunnelRowStatus           RowStatus
        }

clGatewayTunnelName    OBJECT-TYPE
        SYNTAX         OCTET STRING(SIZE(1..128))
        MAX-ACCESS     not-accessible 
        STATUS         current
        DESCRIPTION
             "This object defines name of the tunnel and it is unique."
        ::= { clGatewayTunnelEntry 1 }

clGatewayTunnelType OBJECT-TYPE
        SYNTAX            INTEGER {
                          none (1),
                          pmipv6 (2),     
                          gtpv2 (3),
                          eogre (4)
                          }
        MAX-ACCESS      not-accessible 
        STATUS          current
        DESCRIPTION
             "The object defines type of the gateway tunnel "
        ::= { clGatewayTunnelEntry 2 }

clGatewayTunnelIpv4Address        OBJECT-TYPE
        SYNTAX              IpAddress
        MAX-ACCESS          read-create
        STATUS              current
        DESCRIPTION
             "The object defines the ipv4 address of the tunnel gateway "
        ::= { clGatewayTunnelEntry 3 }

clGatewayTunnelIpAddressType  OBJECT-TYPE
        SYNTAX                InetAddressType
        MAX-ACCESS            read-create
        STATUS                current
        DESCRIPTION
             "The object defines the type of the IP address "
        ::= { clGatewayTunnelEntry 4 }

clGatewayTunnelIpv6Address        OBJECT-TYPE
        SYNTAX              InetAddress
        MAX-ACCESS          read-create
        STATUS              current
        DESCRIPTION
             "The object defines the ipv6 address of the tunnel gateway"
        ::= { clGatewayTunnelEntry 5 }

clGatewayTunnelStatus          OBJECT-TYPE
        SYNTAX                 TruthValue 
        MAX-ACCESS             read-create
        STATUS                 current
        DESCRIPTION
             "The object defines the tunnel status"
             ::= { clGatewayTunnelEntry 6 }

clGatewayTunnelRowStatus      OBJECT-TYPE
       SYNTAX           RowStatus
       MAX-ACCESS       read-create
       STATUS           current
       DESCRIPTION
            "Used to add or delete an entry in this table."
      ::= { clGatewayTunnelEntry 7 }

clGatewayDomainTable  OBJECT-TYPE
        SYNTAX SEQUENCE OF  ClGatewayDomainEntry
        MAX-ACCESS          not-accessible
        STATUS              current
        DESCRIPTION
             "The table list the domains created which contains gateways .
              Maximum gateways in domain is 2. Table contains the Active Gateway. 
              at anytime only one gateway is Active in the domain."
        ::= { ciscoLwappGatewayTunnel 2 }

clGatewayDomainEntry OBJECT-TYPE
        SYNTAX                 ClGatewayDomainEntry
        MAX-ACCESS             not-accessible
        STATUS                 current
        DESCRIPTION
             "Each entry represents a conceptual row in this table.
             For each domain created will be a row. "
        INDEX      { clGatewayDomainName, clGatewayDomainTunnelType }
        ::= { clGatewayDomainTable 1 }

ClGatewayDomainEntry ::= SEQUENCE {
        clGatewayDomainName                OCTET STRING,
        clGatewayDomainTunnelType          INTEGER,
        clGatewayDomainActiveGateway       OCTET STRING,
        clGatewayDomainRowStatus           RowStatus
        }

clGatewayDomainName    OBJECT-TYPE
        SYNTAX         OCTET STRING(SIZE(1..128))
        MAX-ACCESS     not-accessible 
        STATUS         current
        DESCRIPTION
             "This object defines name of the domain and it is unique."
        ::= { clGatewayDomainEntry 1 }

clGatewayDomainTunnelType OBJECT-TYPE
        SYNTAX                 INTEGER {
                               none (1),
                               pmipv6 (2),     
                               gtpv2 (3),
                               eogre (4)
                               }
        MAX-ACCESS      not-accessible 
        STATUS          current
        DESCRIPTION
             "The object defines type of the gateway tunnel "
        ::= { clGatewayDomainEntry 2 }
        
clGatewayDomainActiveGateway     OBJECT-TYPE
        SYNTAX                   OCTET STRING(SIZE(1..128))
        MAX-ACCESS               read-only
        STATUS                   current
        DESCRIPTION
             "This object defines name of the active gateway in the domain."
        ::= { clGatewayDomainEntry 3 }

clGatewayDomainRowStatus       OBJECT-TYPE
        SYNTAX                 RowStatus
        MAX-ACCESS             read-create
        STATUS                 current
        DESCRIPTION
             "Used to add or delete an entry in this table."
        ::= { clGatewayDomainEntry 4 }

clGatewayDomainGatewayListTable  OBJECT-TYPE
        SYNTAX SEQUENCE OF       ClGatewayDomainGatewayListEntry
        MAX-ACCESS               not-accessible
        STATUS                   current
        DESCRIPTION
             "The table list the gateways attached to the domain .
             Maximum gateways in domain is 2."
        ::= { ciscoLwappGatewayTunnel 3 }

clGatewayDomainGatewayListEntry OBJECT-TYPE
        SYNTAX                  ClGatewayDomainGatewayListEntry
        MAX-ACCESS              not-accessible
        STATUS                  current
        DESCRIPTION
             "Each entry represents a conceptual row in this table.
             For each gateway added to the domain will be a row. "
        INDEX      { clGatewayDomainName, clGatewayDomainTunnelType, clGatewayTunnelName }
       ::= { clGatewayDomainGatewayListTable 1 }

ClGatewayDomainGatewayListEntry ::= SEQUENCE {
        clGatewayDomainGatewayListRowStatus         RowStatus
        }

clGatewayDomainGatewayListRowStatus    OBJECT-TYPE
        SYNTAX                     RowStatus
        MAX-ACCESS                 read-create
        STATUS                     current
        DESCRIPTION
             "Used to add or delete an entry in this table."
        ::= { clGatewayDomainGatewayListEntry 2 }

clGatewayProfileTable  OBJECT-TYPE
        SYNTAX SEQUENCE OF  ClGatewayProfileEntry
        MAX-ACCESS          not-accessible
        STATUS              current
        DESCRIPTION
             "The table list the profiles created. rules are attached to the profile .
             Maximum rules attached to per profile is 32."
        ::= { ciscoLwappGatewayTunnel 4 }

clGatewayProfileEntry       OBJECT-TYPE
        SYNTAX              ClGatewayProfileEntry
        MAX-ACCESS          not-accessible
        STATUS              current
        DESCRIPTION
             "Each entry represents a conceptual row in this table.
              For each profile created will be a row. "
        INDEX      { clGatewayProfileName }
        ::= { clGatewayProfileTable 1 }

ClGatewayProfileEntry ::= SEQUENCE {
        clGatewayProfileName                OCTET STRING,
        clGatewayProfileDhcpOpt82Status     TruthValue,
        clGatewayProfileDhcpOpt82Format     Unsigned32,
        clGatewayProfileDhcpOpt82Delimiter  OCTET STRING, 
        clGatewayProfileCircuitId           OCTET STRING,
        clGatewayProfileRemoteId            OCTET STRING,
        clGatewayProfileRowStatus           RowStatus
        }

clGatewayProfileName    OBJECT-TYPE
        SYNTAX          OCTET STRING(SIZE(1..128))
        MAX-ACCESS      not-accessible 
        STATUS          current
        DESCRIPTION
             "This object defines name of the profile and it is unique."
        ::= { clGatewayProfileEntry 1 }

clGatewayProfileDhcpOpt82Status     OBJECT-TYPE
        SYNTAX                      TruthValue 
        MAX-ACCESS                  read-create
        STATUS                      current
        DESCRIPTION
             "This object defines status of dhcp option 82 of the profile."
             ::= { clGatewayProfileEntry 2 }

clGatewayProfileDhcpOpt82Format     OBJECT-TYPE
        SYNTAX                      Unsigned32 
        MAX-ACCESS                  read-create
        STATUS                      current
        DESCRIPTION
             "This object defines binary or ASCII format of the DHCP data."
             ::= { clGatewayProfileEntry 3 }

clGatewayProfileDhcpOpt82Delimiter      OBJECT-TYPE
        SYNTAX                          OCTET STRING(SIZE(0..2))
        MAX-ACCESS                      read-create
        STATUS                          current
        DESCRIPTION
             "This object defines delimiter between the attributes of dhcp option."
             ::= { clGatewayProfileEntry 4 }

clGatewayProfileCircuitId    OBJECT-TYPE
        SYNTAX               OCTET STRING(SIZE(0..128))
        MAX-ACCESS           read-create
        STATUS               current
        DESCRIPTION
             "This object defines of CircuitId attributes per profile. 
             Maximum circuitId per profile supported is 5."
             ::= { clGatewayProfileEntry 5 }

clGatewayProfileRemoteId    OBJECT-TYPE
        SYNTAX              OCTET STRING(SIZE(0..128))
        MAX-ACCESS          read-create
        STATUS              current
        DESCRIPTION
             "This object defines of remoteId attributes per profile.
              Maximum remoteId per profile supported is 5."
             ::= { clGatewayProfileEntry 6 }

clGatewayProfileRowStatus       OBJECT-TYPE
        SYNTAX                  RowStatus
        MAX-ACCESS              read-create
        STATUS                  current
        DESCRIPTION
             "Used to add or delete an entry in this table."
        ::= { clGatewayProfileEntry  7}

clGatewayRuleTable  OBJECT-TYPE
        SYNTAX SEQUENCE OF  ClGatewayRuleEntry
        MAX-ACCESS          not-accessible
        STATUS              current
        DESCRIPTION
             "The table list the rules created. rules are attached to the profile."
        ::= { ciscoLwappGatewayTunnel 5 }

clGatewayRuleEntry      OBJECT-TYPE
        SYNTAX          ClGatewayRuleEntry
        MAX-ACCESS      not-accessible
        STATUS          current
        DESCRIPTION
             "Each entry represents a conceptual row in this table.
              For each Rule created will be a row. "
        INDEX      { clGatewayProfileName, clGatewayRuleName }
        ::= { clGatewayRuleTable 1 }

ClGatewayRuleEntry ::= SEQUENCE {
       clGatewayRuleName          OCTET STRING,
       clGatewayRuleTunnelType    INTEGER,
       clGatewayRuleVlanId        Unsigned32,
       clGatewayRuleDomainName    OCTET STRING,
       clGatewayRuleRowStatus     RowStatus
       }

clGatewayRuleName    OBJECT-TYPE
        SYNTAX               OCTET STRING(SIZE(1..128))
        MAX-ACCESS           not-accessible 
        STATUS               current
        DESCRIPTION
             "This object defines name of the rule and it is unique per profile."
        ::= { clGatewayRuleEntry 1 }


clGatewayRuleTunnelType OBJECT-TYPE
        SYNTAX                 INTEGER {
                               none (1),
                               pmipv6 (2),     
                               gtpv2 (3),
                               eogre (4)
                               }
        MAX-ACCESS      read-create
        STATUS              current
        DESCRIPTION
             "The object defines type of the gateway tunnel "
        ::= { clGatewayRuleEntry 2 }

clGatewayRuleVlanId    OBJECT-TYPE
        SYNTAX               Unsigned32
        MAX-ACCESS           read-create
        STATUS               current
        DESCRIPTION
             "This object defines vlan attached to rule."
        ::= { clGatewayRuleEntry 3 }

clGatewayRuleDomainName    OBJECT-TYPE
        SYNTAX             OCTET STRING(SIZE(1..128))
        MAX-ACCESS         read-create
        STATUS             current
        DESCRIPTION
             "This object defines domain attached to the rule."
        ::= { clGatewayRuleEntry 4 }

clGatewayRuleRowStatus      OBJECT-TYPE
        SYNTAX              RowStatus
        MAX-ACCESS          read-create
        STATUS              current
        DESCRIPTION
             "Used to add or delete an entry in this table."
        ::= { clGatewayRuleEntry 5 }

END
