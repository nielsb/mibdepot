-- *******************************************************************
-- CISCO-LWAPP-HA-MIB.my : 
-- Jan 2012, Gayathri
--
-- Copyright (c) 2007, 2014-2015 by Cisco Systems, Inc.
-- All rights reserved.
-- *******************************************************************
--
CISCO-LWAPP-HA-MIB DEFINITIONS ::= BEGIN

IMPORTS 
        MODULE-IDENTITY, 
        NOTIFICATION-TYPE,
        OBJECT-TYPE,
        Unsigned32,
	IpAddress
                FROM SNMPv2-SMI
        OBJECT-GROUP,
        NOTIFICATION-GROUP
                FROM SNMPv2-CONF
        TruthValue,
	TimeStamp, MacAddress, RowStatus
                FROM SNMPv2-TC 
        InetAddressType,
        InetAddress
                FROM INET-ADDRESS-MIB
        CiscoURLString
                FROM CISCO-TC
        SnmpAdminString
                FROM SNMP-FRAMEWORK-MIB
        Counter32, Counter64
                FROM SNMPv2-SMI
        sysName 
                FROM RFC1213-MIB
        ciscoMgmt
                FROM CISCO-SMI
        cRFStatusPeerUnitState,
        cRFStatusUnitState
                FROM CISCO-RF-MIB;

--********************************************************************
--*  MODULE IDENTITY
--********************************************************************

ciscoLwappHaMIB    MODULE-IDENTITY
        LAST-UPDATED    "201201051150Z"
        ORGANIZATION    "Cisco Systems Inc."
        CONTACT-INFO  
               "        Cisco Systems,
                        Customer Service
                Postal: 170 West Tasman Drive
                        San Jose, CA  95134
                        USA
                   Tel: +1 800 553-NETS

                 Email: cs-wnbu-snmp@cisco.com"

        DESCRIPTION             
                "This MIB is intended to be implemented on all those
                devices operating as Central controllers, that
                terminate the Light Weight Access Point Protocol
                tunnel from Cisco Light-weight LWAPP Access Points.

                This MIB is used to show and configure High availability 
		(HA) related statistics.


                The relationship between CC and the LWAPP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Central Controller ( CC )

                The central entity that terminates the LWAPP protocol
                tunnel from the LWAPP APs.  Throughout this MIB,
                this entity also referred to as 'controller'. 

                Light Weight Access Point Protocol ( LWAPP ) 

                This is a generic protocol that defines the 
                communication between the Access Points and the
                Central Controller.

                Mobile Node ( MN )

                A roaming 802.11 wireless device in a wireless
                network associated with an access point. Mobile Node,
                Mobile Station(Ms) and client are used interchangeably. 
                
                REFERENCE
 
                [1] Wireless LAN Medium Access Control ( MAC ) and
                Physical Layer ( PHY ) Specifications.
  
                [2] Draft-obara-capwap-lwapp-00.txt, IETF Light 
                Weight Access Point Protocol "
        
        REVISION      "201201241150Z"
        DESCRIPTION
                "Initial version of this MIB module. "
        ::= { ciscoMgmt 198888 }

ciscoLwappHaMIBObjects OBJECT IDENTIFIER 
        ::= { ciscoLwappHaMIB 0 }

ciscoLwappHaGlobalConfig OBJECT IDENTIFIER
	::= { ciscoLwappHaMIBObjects 1 }

ciscoLwappHaNetworkConfig OBJECT IDENTIFIER
	::= { ciscoLwappHaMIBObjects 2 }

ciscoLwappHaMIBNotifs OBJECT IDENTIFIER 
        ::= { ciscoLwappHaMIBObjects 3 }

	
--*************************************************
--HA Global Config
--*************************************************

cLHaApSsoConfig OBJECT-TYPE
	SYNTAX	    TruthValue
	MAX-ACCESS  read-write
	STATUS	    current
	DESCRIPTION
        ""
	::= { ciscoLwappHaGlobalConfig  1 }

cLHaPeerIpAddressType  OBJECT-TYPE
        SYNTAX          InetAddressType
        MAX-ACCESS      read-write
        STATUS          current
        DESCRIPTION
        ""
        ::= { ciscoLwappHaGlobalConfig 2 }

cLHaPeerIpAddress  OBJECT-TYPE
        SYNTAX          InetAddress
        MAX-ACCESS      read-write 
        STATUS          current
        DESCRIPTION
        ""
	::= { ciscoLwappHaGlobalConfig  3 }


cLHaServicePortPeerIpAddressType  OBJECT-TYPE
        SYNTAX          InetAddressType
        MAX-ACCESS      read-write
        STATUS          current
        DESCRIPTION
        ""
        ::= { ciscoLwappHaGlobalConfig  4 }

cLHaServicePortPeerIpAddress  OBJECT-TYPE
        SYNTAX          InetAddress
        MAX-ACCESS      read-write
        STATUS          current
        DESCRIPTION
        ""
        ::= { ciscoLwappHaGlobalConfig  5 }

cLHaServicePortPeerIpNetMaskType  OBJECT-TYPE
        SYNTAX          InetAddressType
        MAX-ACCESS      read-write
        STATUS          current
        DESCRIPTION
        ""
        ::= { ciscoLwappHaGlobalConfig  6 }


cLHaServicePortPeerIpNetMask  OBJECT-TYPE
        SYNTAX          InetAddress
        MAX-ACCESS      read-write
        STATUS          current
        DESCRIPTION
        ""
        ::= { ciscoLwappHaGlobalConfig  7 }

cLHaRedundancyIpAddressType  OBJECT-TYPE
        SYNTAX          InetAddressType
        MAX-ACCESS      read-only
        STATUS          current
        DESCRIPTION
        ""
        ::= { ciscoLwappHaGlobalConfig  8 }


cLHaRedundancyIpAddress  OBJECT-TYPE
        SYNTAX          InetAddress
        MAX-ACCESS      read-only
        STATUS          current
        DESCRIPTION
        ""
        ::= { ciscoLwappHaGlobalConfig  9 }

cLHaPeerMacAddress  OBJECT-TYPE
        SYNTAX          MacAddress
        MAX-ACCESS      read-only
        STATUS          current
        DESCRIPTION
        ""
        ::= { ciscoLwappHaGlobalConfig  10 }

cLHaVirtualMacAddress  OBJECT-TYPE
        SYNTAX          MacAddress
        MAX-ACCESS      read-write
        STATUS          current
        DESCRIPTION
        ""
        ::= { ciscoLwappHaGlobalConfig  11 }

cLHaPrimaryUnit OBJECT-TYPE
    SYNTAX          TruthValue
    MAX-ACCESS      read-write
    STATUS          current
    DESCRIPTION
        "Indicates whether this is the primary redundant unit or
        not. If this unit is the primary unit, this object is true. If
        this unit is the secondary unit, this object is false."
        ::= { ciscoLwappHaGlobalConfig  12 }

cLHaLinkEncryption OBJECT-TYPE
    SYNTAX          TruthValue
    MAX-ACCESS      read-write
    STATUS          current
    DESCRIPTION
        "Indicates whether link encryption is enabled or not."
        ::= { ciscoLwappHaGlobalConfig  13 }

cLHaNetworkFailOver OBJECT-TYPE
    SYNTAX          TruthValue
    MAX-ACCESS      read-write
    STATUS          current
    DESCRIPTION
        "Indicates whether network failover is enabled or not."
        ::= { ciscoLwappHaGlobalConfig  14 }

cLHaRFStatusUnitIp OBJECT-TYPE
    SYNTAX          InetAddress
    MAX-ACCESS      read-only
    STATUS          current
    DESCRIPTION
        "The description of the ip address of unit" 
        ::= { ciscoLwappHaGlobalConfig  15 }

cLHaKATimeout OBJECT-TYPE
    SYNTAX          Unsigned32
    MAX-ACCESS      read-write
    STATUS          current
    DESCRIPTION
        "Keep-Alive timeout value in milli seconds between 100 and 1000.
 		To alter the config value should be specified in multiples of 50"
    DEFVAL   { 100 }		
        ::= { ciscoLwappHaGlobalConfig  16 }

cLHaKARetryCount OBJECT-TYPE
    SYNTAX          Unsigned32
    MAX-ACCESS      read-write
    STATUS          current
    DESCRIPTION
        "This object is used to configure Keep-Alive retry count and 
		the configurable values are between 3 and 10"
    DEFVAL   { 3 }		
        ::= { ciscoLwappHaGlobalConfig  17 }

cLHaGwRetryCount OBJECT-TYPE
    SYNTAX          Unsigned32
    MAX-ACCESS      read-write
    STATUS          current
    DESCRIPTION
        "This object is used to configure Default Gateway reachability 
		retry count and the configurable values are between 6 and 12"
    DEFVAL   { 12 }		
        ::= { ciscoLwappHaGlobalConfig  18 }
		
cLHaPeerSearchTimeout OBJECT-TYPE
    SYNTAX          Unsigned32
    MAX-ACCESS      read-write
    STATUS          current
    DESCRIPTION
        "This object is used to configure peer search timeout and the 
		configurable values range from 60 and 300 seconds."
    DEFVAL   { 200 }		
        ::= { ciscoLwappHaGlobalConfig  19 }		

--********************************************************************
-- cLHaNeworkRoutePeerTable
--********************************************************************


     cLHaNetworkRoutePeerConfigTable OBJECT-TYPE
         SYNTAX      SEQUENCE OF CLHaNetworkRoutePeerConfigEntry
         MAX-ACCESS  not-accessible
         STATUS      current
         DESCRIPTION
                     "A table of the switch's Network Route Peer entries"
         ::= { ciscoLwappHaNetworkConfig 1 }

    cLHaNetworkRoutePeerConfigEntry OBJECT-TYPE
         SYNTAX      CLHaNetworkRoutePeerConfigEntry
         MAX-ACCESS  not-accessible
         STATUS      current
         DESCRIPTION
                     "Switch's Network Route Peer entry"
         INDEX       {cLHaNetworkRoutePeerIPAddressType, cLHaNetworkRoutePeerIPAddress }
         ::= { cLHaNetworkRoutePeerConfigTable 1 }

    CLHaNetworkRoutePeerConfigEntry ::= SEQUENCE {
           cLHaNetworkRoutePeerIPAddressType  InetAddressType,
           cLHaNetworkRoutePeerIPAddress      InetAddress,
           cLHaNetworkRoutePeerIPNetmaskType  InetAddressType,
           cLHaNetworkRoutePeerIPNetmask      InetAddress,
           cLHaNetworkRoutePeerGatewayType    InetAddressType,
           cLHaNetworkRoutePeerGateway        InetAddress,
           cLHaNetworkRoutePeerTransferStatus INTEGER,
           cLHaNetworkRoutePeerRowStatus      RowStatus
       }
    cLHaNetworkRoutePeerIPAddressType OBJECT-TYPE
         SYNTAX      InetAddressType
         MAX-ACCESS  not-accessible 
         STATUS      current
         DESCRIPTION
                "Network Route IP Address type of the standby."
         ::= { cLHaNetworkRoutePeerConfigEntry 1 }

    cLHaNetworkRoutePeerIPAddress OBJECT-TYPE
         SYNTAX      InetAddress
         MAX-ACCESS  not-accessible 
         STATUS      current
         DESCRIPTION
                "Network Route IP Address of the standby."
         ::= { cLHaNetworkRoutePeerConfigEntry 2 }


    cLHaNetworkRoutePeerIPNetmaskType OBJECT-TYPE
         SYNTAX      InetAddressType
         MAX-ACCESS  read-create
         STATUS      current
         DESCRIPTION
           "   Network Route IP Netmask type of the standby."
         ::= { cLHaNetworkRoutePeerConfigEntry 3 }

    cLHaNetworkRoutePeerIPNetmask OBJECT-TYPE
         SYNTAX      InetAddress
         MAX-ACCESS  read-create
         STATUS      current
         DESCRIPTION
           "   Network Route IP Netmask of the standby."
         ::= { cLHaNetworkRoutePeerConfigEntry 4 }


    cLHaNetworkRoutePeerGatewayType OBJECT-TYPE
         SYNTAX      InetAddressType
         MAX-ACCESS  read-create
         STATUS      current
         DESCRIPTION
           "  Network Route IP Gateway type of the standby."
         ::= { cLHaNetworkRoutePeerConfigEntry 5 }

    cLHaNetworkRoutePeerGateway OBJECT-TYPE
         SYNTAX      InetAddress
         MAX-ACCESS  read-create
         STATUS      current
         DESCRIPTION
           "  Network Route IP Gateway  of the standby."
         ::= { cLHaNetworkRoutePeerConfigEntry 6 }


    cLHaNetworkRoutePeerTransferStatus OBJECT-TYPE
         SYNTAX      INTEGER  {
                        initiate(1),
                        inProgress(2),
                        success(3),
                        failure(4),
                        timeout(5)
                    }

         MAX-ACCESS  read-write
         STATUS      current
         DESCRIPTION
                     "Network Route transfer status from standby."
         ::= { cLHaNetworkRoutePeerConfigEntry 7 }

    cLHaNetworkRoutePeerRowStatus OBJECT-TYPE
         SYNTAX    RowStatus
         MAX-ACCESS  read-create
         STATUS      current
         DESCRIPTION
                     "Network Route Peer Row Status."
         ::= { cLHaNetworkRoutePeerConfigEntry 8 }


--********************************************************************
--*    NOTIFICATION Variable
--********************************************************************

ciscoLwappHaNotificationVariable OBJECT IDENTIFIER ::= { ciscoLwappHaMIBObjects 4 }
cLHaSecondaryControllerUsageTrapType OBJECT-TYPE
         SYNTAX      INTEGER  {
                        usageStart(1),
                        usageComplete(2),
                        overUsage(3)
                    }

    MAX-ACCESS read-only 
    STATUS current
    DESCRIPTION
       "This object represents the usage of secondary controller. After the usuage of 90 days, one trap is generated per day for over usage.
        usageStart - start of secondary controller usage.
        usageComplete - completion of secondary controller usage period of 90 days.
        overUsage - Secondary controller overusage."
    ::= {  ciscoLwappHaNotificationVariable 1 }


cLHaSecondaryControllerUsageDayCounter OBJECT-TYPE
    SYNTAX      Counter32 
    MAX-ACCESS  read-only 
    STATUS current
    DESCRIPTION
       "This object represents the number of days the secondary controller is used."
    ::= {  ciscoLwappHaNotificationVariable 2 }

cLHaBulkSyncCompleteEventStr OBJECT-TYPE
    SYNTAX          OCTET STRING 
    MAX-ACCESS      read-only
    STATUS          current
    DESCRIPTION
       "This object represents the time when the Bulksync was complete."
    ::= {  ciscoLwappHaNotificationVariable 3 }

cLHaPeerHotStandbyEventStr OBJECT-TYPE
    SYNTAX          OCTET STRING
    MAX-ACCESS      read-only
    STATUS          current
    DESCRIPTION
       "This object represents that the peer has turned Hot-Standby."
    ::= {  ciscoLwappHaNotificationVariable 4 }


cLHaSecondaryControllerUsageTrap NOTIFICATION-TYPE
    OBJECTS {
        cLHaSecondaryControllerUsageTrapType,
        cLHaSecondaryControllerUsageDayCounter,
        sysName
         }
    STATUS current
    DESCRIPTION
        "This notification is sent on the event of a generic failure
          between the active and standby unit"
    ::= { ciscoLwappHaMIBNotifs 1 }

cLHaRFSwapInfoTrap NOTIFICATION-TYPE
    OBJECTS         {
                        cLHaRFStatusUnitIp,
                        cRFStatusUnitState,
                        cLHaPeerIpAddress,
                        cRFStatusPeerUnitState
                    }
    STATUS          current
    DESCRIPTION
        "The notification is sent by the active redundant
        unit whenever its RF state changes or the RF state of the peer
        unit changes.

        To avoid a flurry of notifications for all state transitions,
        notifications will only be sent for transitions to the
        following RF states:
            disabled (for the peer state)
            standbyCold
            standbyHot
            active
            activeExtraload"
    ::= { ciscoLwappHaMIBNotifs 2 }

cLHaBulkSyncCompleteTrap NOTIFICATION-TYPE
    OBJECTS         {
                       cLHaBulkSyncCompleteEventStr 
                    }
    STATUS          current
    DESCRIPTION
        "The notification is sent by the Active redundant
        unit whenever the BulkSync to peer is complete"
    ::= { ciscoLwappHaMIBNotifs 3 }

cLHaPeerHotStandbyTrap NOTIFICATION-TYPE
    OBJECTS         {
                      cLHaPeerHotStandbyEventStr 
                    }
    STATUS          current
    DESCRIPTION
        "The notification is sent by the Active redundant
        unit whenever its peer unit turned Hot-Standby"
    ::= { ciscoLwappHaMIBNotifs 4 }

--********************************************************************
--*    Peer Statistics Variable
--********************************************************************

ciscoLwappHaPeerStatisticsVariable OBJECT IDENTIFIER ::= { ciscoLwappHaMIBObjects 5 }
cLHaSystemStatistics OBJECT IDENTIFIER ::= { ciscoLwappHaPeerStatisticsVariable 1 }

cLHaCpuStatistics OBJECT IDENTIFIER ::= { cLHaSystemStatistics 1 }



cLHaAllCpuUsage OBJECT-TYPE
     SYNTAX DisplayString
     MAX-ACCESS  read-only
     STATUS      current
     DESCRIPTION
        "This object specifies the HA peer all CPUs usage 
		consuructed as a string."
     DEFVAL { "" }
     ::= {cLHaCpuStatistics 1 }

cLHaPowerSupplyStatistics OBJECT IDENTIFIER ::= { cLHaSystemStatistics 2 }	 
cLHaPowerSupply1Present OBJECT-TYPE
     SYNTAX      INTEGER {
                 false(0),
                 true(1)
              }
     MAX-ACCESS  read-only
     STATUS      current
     DESCRIPTION
                 "This is to indicate if the Peer switch has Power
                  Supply 1 present on it.  This is applicable to
                  the 4200 series and will always return true for
                  the earlier device versions."
     DEFVAL { false }
     ::= { cLHaPowerSupplyStatistics 1 }

cLHaPowerSupply1Operational OBJECT-TYPE
     SYNTAX      INTEGER {
                 false(0),
                 true(1)
              }
     MAX-ACCESS  read-only
     STATUS      current
     DESCRIPTION
                 "This is to indicate if the Peer switch's Power Supply
                  1 is operational.  This is applicable to the
                  4200 series and will always return true for the
                  earlier device versions."
     DEFVAL { false }
     ::= { cLHaPowerSupplyStatistics 2 }

cLHaPowerSupply2Present OBJECT-TYPE
     SYNTAX      INTEGER {
                 false(0),
                 true(1)
              }
     MAX-ACCESS  read-only
     STATUS      current
     DESCRIPTION
                 "This is to indicate if the Peer switch has Power
                  Supply 2 present on it.  This is applicable to
                  the 4200 series and will always return false for
                  the earlier device versions."
     DEFVAL { false }
     ::= { cLHaPowerSupplyStatistics 3 }

cLHaPowerSupply2Operational OBJECT-TYPE
     SYNTAX      INTEGER {
                 false(0),
                 true(1)
              }
     MAX-ACCESS  read-only
     STATUS      current
     DESCRIPTION
                 "This is to indicate if the Peer switch's Power Supply
                  2 is operational.This is applicable to the 4200
                  series and will always return false for the
                  earlier device versions."
     DEFVAL { false }
     ::= { cLHaPowerSupplyStatistics 4 }

cLHaMemoryStatistics OBJECT IDENTIFIER ::= { cLHaSystemStatistics 3 }

cLHaTotalSystemMemory  OBJECT-TYPE
    SYNTAX      Integer32 
    MAX-ACCESS  read-only 
    STATUS current
    DESCRIPTION
       "This object represents the total system memory in Kbytes "
    DEFVAL { 0 }
    ::= {  cLHaMemoryStatistics 1 } 

cLHaFreeSystemMemory  OBJECT-TYPE
    SYNTAX      Integer32 
    MAX-ACCESS  read-only 
    STATUS current
    DESCRIPTION
       "This object represents the free system memory in Kbytes "
    DEFVAL { 0 }
    ::= {  cLHaMemoryStatistics 2 }
	
cLHaUsedSystemMemory  OBJECT-TYPE
    SYNTAX      Integer32 
    MAX-ACCESS  read-only 
    STATUS current
    DESCRIPTION
       "This object represents the used system memory in Kbytes"
    DEFVAL { 0 }
    ::= {  cLHaMemoryStatistics 3 }

cLHaAllocatedFromRtos  OBJECT-TYPE
    SYNTAX      Integer32 
    MAX-ACCESS  read-only 
    STATUS current
    DESCRIPTION
       "This object represents the number of bytes allocated
         from RTOS in Kbytes"
    DEFVAL { 0 }
    ::= {  cLHaMemoryStatistics 4 }

cLHaChunksFree   OBJECT-TYPE
    SYNTAX      Integer32 
    MAX-ACCESS  read-only 
    STATUS current
    DESCRIPTION
       "This object represents the number of chunks free"
    DEFVAL { 0 }
    ::= {  cLHaMemoryStatistics 5 }

cLHaMmappedRegions   OBJECT-TYPE
    SYNTAX      Integer32 
    MAX-ACCESS  read-only 
    STATUS current
    DESCRIPTION
       "This object represents the number of memory mapped regions"
    DEFVAL { 0 }
    ::= {  cLHaMemoryStatistics 6 }

cLHaSpaceInMmappedRegions   OBJECT-TYPE
    SYNTAX      Integer32 
    MAX-ACCESS  read-only 
    STATUS current
    DESCRIPTION
       "This object represents the space in the memory mapped 
        regions in Kbytes"
    DEFVAL { 0 }
    ::= {  cLHaMemoryStatistics 7 }

cLHaTotalAllocatedSpace   OBJECT-TYPE
    SYNTAX      Integer32 
    MAX-ACCESS  read-only 
    STATUS current
    DESCRIPTION
       "This object represents the total allocated space in bytes in Kbytes"
    DEFVAL { 0 }
    ::= {  cLHaMemoryStatistics 8 }

cLHaTotalNotInUseSpace   OBJECT-TYPE
    SYNTAX      Integer32 
    MAX-ACCESS  read-only 
    STATUS current
    DESCRIPTION
       "This object represents the total space not in-use in Kbytes"
    DEFVAL { 0 }
    ::= {  cLHaMemoryStatistics 9 }

cLHaTopMostReleasableSpace  OBJECT-TYPE
    SYNTAX      Integer32 
    MAX-ACCESS  read-only 
    STATUS current
    DESCRIPTION
       "This object represents the top most releasable space in Kbytes"
    DEFVAL { 0 }	   
    ::= {  cLHaMemoryStatistics 10 }

cLHaTotalAllocatedInclMmap   OBJECT-TYPE
    SYNTAX      Integer32 
    MAX-ACCESS  read-only 
    STATUS current
    DESCRIPTION
       "This object represents the total memory allocated including 
        memory map in Kbytes"
    DEFVAL { 0 }
    ::= {  cLHaMemoryStatistics 11 }

cLHaTotalUsedInclMmap   OBJECT-TYPE
    SYNTAX      Integer32 
    MAX-ACCESS  read-only 
    STATUS current
    DESCRIPTION
       "This object represents the total memory in-use including 
        memory map in Kbytes"
    DEFVAL { 0 }		
    ::= {  cLHaMemoryStatistics 12 }

cLHaTotalFreeInclMmap   OBJECT-TYPE
    SYNTAX      Integer32 
    MAX-ACCESS  read-only 
    STATUS current
    DESCRIPTION
       "This object represents the total free memory including 
        memory map in Kbytes"
    DEFVAL { 0 }		
    ::= {  cLHaMemoryStatistics 13 }

--********************************************************************
--*    HA statistics Variable
--********************************************************************
ciscoLwappHaStatisticsVariable OBJECT IDENTIFIER ::= { ciscoLwappHaMIBObjects 6 }

cLHaAvgPeerReachLatency OBJECT-TYPE
     SYNTAX Integer32
     MAX-ACCESS  read-only
     STATUS      current
     DESCRIPTION
        "This object specifies average value of peer controller 
		reachable Latency in micro seconds"
     DEFVAL { 0 }
     ::= {ciscoLwappHaStatisticsVariable 1 }

cLHaAvgGwReachLatency OBJECT-TYPE
     SYNTAX Integer32
     MAX-ACCESS  read-only
     STATUS      current
     DESCRIPTION
        "This object specifies average value of default GW  
		reachable Latency in micro seconds"
     DEFVAL { 0 }
     ::= {ciscoLwappHaStatisticsVariable 2 }

cLHaBulkSyncStatus OBJECT-TYPE
     SYNTAX DisplayString
     MAX-ACCESS  read-only
     STATUS      current
     DESCRIPTION
        "This object specifies current status of Bulk Sync"
     DEFVAL { "" }
     ::= {ciscoLwappHaStatisticsVariable 3 }
	 

END
