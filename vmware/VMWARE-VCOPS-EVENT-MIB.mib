-- **********************************************************
-- Copyright 2012 VMware, Inc.  All rights reserved.
-- **********************************************************

VMWARE-VCOPS-EVENT-MIB DEFINITIONS ::= BEGIN

IMPORTS
   MODULE-COMPLIANCE, OBJECT-GROUP, NOTIFICATION-GROUP
        FROM SNMPv2-CONF
   enterprises, Counter32, OBJECT-TYPE,
   MODULE-IDENTITY, OBJECT-IDENTITY, NOTIFICATION-TYPE
      FROM SNMPv2-SMI;

-- 1.3.6.1.4.1.19004
vmwVcopsMIB MODULE-IDENTITY
   LAST-UPDATED
      "201110190000Z"
   ORGANIZATION "VMware, Inc"
   CONTACT-INFO
   "VMware, Inc
   3401 Hillview Ave
   Palo Alto, CA 94304
   Tel: 1-877-486-9273 or 650-427-5000
   Fax: 650-427-5001
   Web: http://communities.vmware.com/community/developer/forums/managementapi
   "
   DESCRIPTION
      "The MIB Module for VMware Corporation entities"
   REVISION "201110190000Z"
   DESCRIPTION "Re-named Integrien to VMware"
   REVISION "200901260000Z"
   DESCRIPTION "Rewrite Integrien MIB for Alive v7.0 aka 'Carbon'"
   ::= { enterprises 19004 }


--
-- Top-level MIB groups
--

-- Group 0: Alerts sent as traps
-- 1.3.6.1.4.1.19004.0
intgrnAlertTrap OBJECT-IDENTITY
        STATUS  current
        DESCRIPTION
         "This group is acutally the prefix one uses when creating
          enterprise-specific trap OID's for an SNMPv2 trap.  It is
          used in the VMware MIB when defining traps."
        ::= { vmwVcopsMIB 0 }


--
-- Group 2: Generic data sent in All Alerts
-- Generic data, in var-binds, that is associated with EVERY Alert
--
-- intgrnGenericAlertData
--   |
--   + intgrnAlertAliveServerName (the name of the VCOPs Server from which this trap comes)
--   + intgrnAlertEntityName (Entity name on which the alert was issued)
--   + intgrnAlertEntityType (Entity type on which the alert was issued)
--   + intgrnAlertTimestamp (which is Start in "Active", Cancel in "Clear" and Updated in "Change")
--   + intgrnAlertCriticality (Alert criticality)
--   + intgrnAlertRootCause (Textual description of the root cause. Can we do better than that?)
--   + intgrnAlertURL (A URL to launch the Alert Summary landing page)
--   + intgrnAlertID (The unique VCOPs ID of the Alert)
--   + intgrnAlertMessage (Alert info message)
--   + intgrnAlertType (Textual description of alert type)
--   + intgrnAlertSubtype (Textual description of alert subtype)
--
-- 1.3.6.1.4.1.19004.2
intgrnGenericAlertData OBJECT-IDENTITY
        STATUS  current
        DESCRIPTION
         "This members of this group are the OIDs for VarBinds
     that contain data for ALL Alerts."
        ::= { vmwVcopsMIB 2 }

-- 1.3.6.1.4.1.19004.2.1
intgrnAlertAliveServerName OBJECT-TYPE
   SYNTAX OCTET STRING
   MAX-ACCESS accessible-for-notify
   STATUS   current
   DESCRIPTION
   "The name of the VCOPs server that generated this alert."
   ::= { intgrnGenericAlertData 1 }

-- 1.3.6.1.4.1.19004.2.2
intgrnAlertEntityName OBJECT-TYPE
   SYNTAX OCTET STRING
   MAX-ACCESS accessible-for-notify
   STATUS   current
   DESCRIPTION
   "The Entity name about which this alert was generated."
   ::= { intgrnGenericAlertData 2 }

-- 1.3.6.1.4.1.19004.2.3
intgrnAlertEntityType OBJECT-TYPE
   SYNTAX OCTET STRING
   MAX-ACCESS accessible-for-notify
   STATUS   current
   DESCRIPTION
   "The Entity type about which this alert was generated."
   ::= { intgrnGenericAlertData 3 }

-- 1.3.6.1.4.1.19004.2.4
intgrnAlertTimestamp OBJECT-TYPE
   SYNTAX Counter32
   MAX-ACCESS accessible-for-notify
   STATUS   current
   DESCRIPTION
   "The timestamp of the alert in UTC format."
   ::= { intgrnGenericAlertData 4 }

-- 1.3.6.1.4.1.19004.2.5
intgrnAlertCriticality OBJECT-TYPE
   SYNTAX OCTET STRING
   MAX-ACCESS accessible-for-notify
   STATUS   current
   DESCRIPTION
   "A text string describing the alert criticality level."
   ::= { intgrnGenericAlertData 5 }

-- 1.3.6.1.4.1.19004.2.6
intgrnAlertRootCause OBJECT-TYPE
   SYNTAX OCTET STRING
   MAX-ACCESS accessible-for-notify
   STATUS   current
   DESCRIPTION
   "A text string describing the root-cause of the alert that was generated."
   ::= { intgrnGenericAlertData 6 }

-- 1.3.6.1.4.1.19004.2.7
intgrnAlertURL OBJECT-TYPE
   SYNTAX OCTET STRING
   MAX-ACCESS accessible-for-notify
   STATUS   current
   DESCRIPTION
   "The URL of the 'Alert Summary' page of the alert that was generated."
   ::= { intgrnGenericAlertData 7 }

-- 1.3.6.1.4.1.19004.2.8
intgrnAlertID OBJECT-TYPE
   SYNTAX OCTET STRING
   MAX-ACCESS accessible-for-notify
   STATUS   current
   DESCRIPTION
   "The unique VCOPs identifier of the alert that was generated."
   ::= { intgrnGenericAlertData 8 }

-- 1.3.6.1.4.1.19004.2.9
intgrnAlertMessage OBJECT-TYPE
   SYNTAX OCTET STRING
   MAX-ACCESS accessible-for-notify
   STATUS   current
   DESCRIPTION
   "The info message of the alert that was generated."
   ::= { intgrnGenericAlertData 9 }

-- 1.3.6.1.4.1.19004.2.10
intgrnAlertType OBJECT-TYPE
   SYNTAX OCTET STRING
   MAX-ACCESS accessible-for-notify
   STATUS   current
   DESCRIPTION
   "The textual type description of the alert that was generated."
   ::= { intgrnGenericAlertData 10 }


-- 1.3.6.1.4.1.19004.2.11
intgrnAlertSubtype OBJECT-TYPE
   SYNTAX OCTET STRING
   MAX-ACCESS accessible-for-notify
   STATUS   current
   DESCRIPTION
   "The textual subtype description of the alert that was generated."
   ::= { intgrnGenericAlertData 11 }



--
-- Trap types that correspond to the different types of SmartAlerts 
-- that can be generated. The data sent in these traps will be a
-- combination of generic data and trap-specific data, depending
-- on the trap type.
-- These are the enterprise-specific trap codes courrently in-use in
-- VMware's software. The funal sub-OID of each objects is the code
-- sent in the "specific-trap" field of an SNMPv1 Trap-PDU.
--
-- The definition of these objects mimics the SNMPv2 convention for
-- sending traps:
-- Take the enterprise OID, append 0, then append the trap code.
-- Trap number usage:
-- Trap code 0 is reserved (by SNMP)
-- Trap codes 1-9 are used for Smart Alerts
-- Trap codes 10-18 are used for Classic Alerts
-- Trap codes 19-27 are used for Badge Health Alerts
-- Trap codes 28-36 are used for Badge Risk Alerts
-- Trap codes 37-42 are used for Badge Efficiency Alerts
-- Trap codes 101-199 are used for Administrative Alerts
-- Trap code 200 is used for functionality testing
--
-- intgrnSmartAlertTrap
--   |
--   +- intgrnTrapKPIBreachActive (A KPI Breach was detected by VCOPs)
--   +- intgrnTrapKPIBreachClear (The above condition was cleared)
--   +- intgrnTrapKPIBreachChange (or Update? The KPI Breach was updated. Not sure we need this?)
--   +- intgrnTrapKPIPredictionActive (A KPI Breach was predicted by VCOPs, aka 'Fingerprint')
--   +- intgrnTrapKPIPredictionClear (The above condition was cleared)
--   +- intgrnTrapKPIPredictionChange (The above condition was updated)
--   +- intgrnTrapAggregateAnomalyActive (An aggregate anomaly was detected by VCOPs)
--   +- intgrnTrapAggregateAnomalyClear (The above condition was cleared)
--   +- intgrnTrapAggregateAnomalyChange (or Update? The above condition was updated. Not sure we need this?)
--   +- intgrnTrapKPIHTBreachActive (A KPI HT Breach was detected by VCOPs)
--   +- intgrnTrapKPIHTBreachClear (The above condition was cleared)
--   +- intgrnTrapKPIHTBreachChange (The above condition was updated)
--   +- intgrnTrapNotificationActive (A Notification was detected by VCOPs)
--   +- intgrnTrapNotificationClear (The above condition was cleared)
--   +- intgrnTrapNotificationChange (The above condition was updated)
--   +- intgrnTrapAbnormalityActive (An Abnormality was detected by VCOPs)
--   +- intgrnTrapAbnormalityClear (The above condition was cleared)
--   +- intgrnTrapAbnormalityChange (The above condition was updated)
--   +- intgrnTrapWorkloadActive (A Badge Workload was detected by VCOPs)
--   +- intgrnTrapWorkloadClear (The above condition was cleared)
--   +- intgrnTrapWorkloadChange (The above condition was updated)
--   +- intgrnTrapAnomalyActive (A Badge Anomaly was detected by VCOPs)
--   +- intgrnTrapAnomalyClear (The above condition was cleared)
--   +- intgrnTrapAnomalyChange (The above condition was updated)
--   +- intgrnTrapFaultActive (A Badge Fault was detected by VCOPs)
--   +- intgrnTrapFaultClear (The above condition was cleared)
--   +- intgrnTrapFaultChange (The above condition was updated)
--   +- intgrnTrapTimeRemainingActive (A Badge TimeRemaining was detected by VCOPs)
--   +- intgrnTrapTimeRemainingClear (The above condition was cleared)
--   +- intgrnTrapTimeRemainingChange (The above condition was updated)
--   +- intgrnTrapCapacityRemainingActive (A Badge CapacityRemaining was detected by VCOPs)
--   +- intgrnTrapCapacityRemainingClear (The above condition was cleared)
--   +- intgrnTrapCapacityRemainingChange (The above condition was updated)
--   +- intgrnTrapStressActive (A Badge Stress was detected by VCOPs)
--   +- intgrnTrapStressClear (The above condition was cleared)
--   +- intgrnTrapStressChange (The above condition was updated)
--   +- intgrnTrapWasteActive (A Waste Stress was detected by VCOPs)
--   +- intgrnTrapWasteClear (The above condition was cleared)
--   +- intgrnTrapWasteChange (The above condition was updated)
--   +- intgrnTrapDensityActive (A Badge Density was detected by VCOPs)
--   +- intgrnTrapDensityClear (The above condition was cleared)
--   +- intgrnTrapDensityChange (The above condition was updated)
--
-- 1.3.6.1.4.1.19004.0.1
intgrnTrapKPIBreachActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that indicates a KPI Breach condition
    became active."
   ::= { intgrnAlertTrap 1 }

-- 1.3.6.1.4.1.19004.0.2
intgrnTrapKPIBreachClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that indicates a KPI Breach condition
    became inactive."
   ::= { intgrnAlertTrap 2 }

-- 1.3.6.1.4.1.19004.0.3
intgrnTrapKPIBreachChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that indicates a KPI Breach condition
    has changed one of its parameters' value."
   ::= { intgrnAlertTrap 3 }

-- 1.3.6.1.4.1.19004.0.4
intgrnTrapKPIPredictionActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that predicts a KPI Breach condition
    (also know as 'Fingerprint') became active."
   ::= { intgrnAlertTrap 4 }

-- 1.3.6.1.4.1.19004.0.5
intgrnTrapKPIPredictionClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that predicts a KPI Breach condition
    (also know as 'Fingerprint') became inactive."
   ::= { intgrnAlertTrap 5 }

-- 1.3.6.1.4.1.19004.0.6
intgrnTrapKPIPredictionChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that predicts a KPI Breach condition
    (also know as 'Fingerprint') that experiences a change in one or more
    of the following values:
    - Prediction probability
    - Prediction projected time
    - Predicition reason."
   ::= { intgrnAlertTrap 6 }

-- 1.3.6.1.4.1.19004.0.7
intgrnTrapAggregateAnomalyActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that indicates an Aggregate Anomaly condition
    became active."
   ::= { intgrnAlertTrap 7 }

-- 1.3.6.1.4.1.19004.0.8
intgrnTrapAggregateAnomalyClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Smart Alert that indicates an Aggregate Anomaly condition
    became inactive."
   ::= { intgrnAlertTrap 8 }

-- 1.3.6.1.4.1.19004.0.9
--intgrnTrapAggregateAnomalyChange NOTIFICATION-TYPE
-- OBJECTS {
--    intgrnAlertAliveServerName,
--    intgrnAlertEntityName,
--    intgrnAlertEntityType,
--    intgrnAlertTimestamp,
--    intgrnAlertCriticality,
--    intgrnAlertRootCause,
--    intgrnAlertURL,
--    intgrnAlertID,
--    intgrnAlertMessage,
--    intgrnAlertType,
--    intgrnAlertSubtype
-- }
-- STATUS current
-- DESCRIPTION
-- "A trap describing a Smart Alert that indicates an Aggregate Anomaly condition
--  has changed one of its parameters' value."
-- ::= { intgrnAlertTrap 9 }

-- 1.3.6.1.4.1.19004.0.10
intgrnTrapKPIHTBreachActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a KPI HT Breach condition
    became active."
   ::= { intgrnAlertTrap 10 }

-- 1.3.6.1.4.1.19004.0.11
intgrnTrapKPIHTBreachClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a KPI HT Breach condition
    became inactive."
   ::= { intgrnAlertTrap 11 }

-- 1.3.6.1.4.1.19004.0.12
intgrnTrapKPIHTBreachChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a KPI HT Breach condition
    has changed one of its parameters' value."
   ::= { intgrnAlertTrap 12 }

-- 1.3.6.1.4.1.19004.0.13
intgrnTrapNotificationActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Notification condition
    became active."
   ::= { intgrnAlertTrap 13 }

-- 1.3.6.1.4.1.19004.0.14
intgrnTrapNotificationClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Notification condition
    became inactive."
   ::= { intgrnAlertTrap 14 }

-- 1.3.6.1.4.1.19004.0.15
intgrnTrapNotificationChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Notification condition
    has changed one of its parameters' value."
   ::= { intgrnAlertTrap 15 }

-- 1.3.6.1.4.1.19004.0.16
intgrnTrapAbnormalityActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Abnormality condition
    became active."
   ::= { intgrnAlertTrap 16 }

-- 1.3.6.1.4.1.19004.0.17
intgrnTrapAbnormalityClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Abnormality condition
    became inactive."
   ::= { intgrnAlertTrap 17 }

-- 1.3.6.1.4.1.19004.0.18
intgrnTrapAbnormalityChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Classic Alert that indicates a Abnormality condition
    has changed one of its parameters' value."
   ::= { intgrnAlertTrap 18 }

 -- 1.3.6.1.4.1.19004.0.19
intgrnTrapWorkloadActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Workload condition
    became active."
   ::= { intgrnAlertTrap 19 }

-- 1.3.6.1.4.1.19004.0.20
intgrnTrapWorkloadClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Workload condition
    became inactive."
   ::= { intgrnAlertTrap 20 }

-- 1.3.6.1.4.1.19004.0.21
intgrnTrapWorkloadChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Workload condition
    has changed one of its parameters' value."
   ::= { intgrnAlertTrap 21 }
 
-- 1.3.6.1.4.1.19004.0.22
intgrnTrapAnomalyActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates an Anomaly condition
    became active."
   ::= { intgrnAlertTrap 22 }

-- 1.3.6.1.4.1.19004.0.23
intgrnTrapAnomalyClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates an Anomaly condition
    became inactive."
   ::= { intgrnAlertTrap 23 }

-- 1.3.6.1.4.1.19004.0.24
intgrnTrapAnomalyChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates an Anomaly condition
    has changed one of its parameters' value."
   ::= { intgrnAlertTrap 24 }
 
-- 1.3.6.1.4.1.19004.0.25
intgrnTrapFaultActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Fault condition
    became active."
   ::= { intgrnAlertTrap 25 }

-- 1.3.6.1.4.1.19004.0.26
intgrnTrapFaultClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Fault condition
    became inactive."
   ::= { intgrnAlertTrap 26 }

-- 1.3.6.1.4.1.19004.0.27
intgrnTrapFaultChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Health Alert that indicates a Fault condition
    has changed one of its parameters' value."
   ::= { intgrnAlertTrap 27 }

-- 1.3.6.1.4.1.19004.0.28
intgrnTrapTimeRemainingActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Time Remaining condition
    became active."
   ::= { intgrnAlertTrap 28 }

-- 1.3.6.1.4.1.19004.0.29
intgrnTrapTimeRemainingClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Time Remaining condition
    became inactive."
   ::= { intgrnAlertTrap 29 }

-- 1.3.6.1.4.1.19004.0.30
intgrnTrapTimeRemainingChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Time Remaining condition
    has changed one of its parameters' value."
   ::= { intgrnAlertTrap 30 }

-- 1.3.6.1.4.1.19004.0.31
intgrnTrapCapacityRemainingActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Capacity Remaining condition
    became active."
   ::= { intgrnAlertTrap 31 }

-- 1.3.6.1.4.1.19004.0.32
intgrnTrapCapacityRemainingClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Capacity Remaining condition
    became inactive."
   ::= { intgrnAlertTrap 32 }

-- 1.3.6.1.4.1.19004.0.33
intgrnTrapCapacityRemainingChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Capacity Remaining condition
    has changed one of its parameters' value."
   ::= { intgrnAlertTrap 33 }

-- 1.3.6.1.4.1.19004.0.34
intgrnTrapStressActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Stress condition
    became active."
   ::= { intgrnAlertTrap 34 }

-- 1.3.6.1.4.1.19004.0.35
intgrnTrapStressClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Stress condition
    became inactive."
   ::= { intgrnAlertTrap 35 }

-- 1.3.6.1.4.1.19004.0.36
intgrnTrapStressChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Risk Alert that indicates a Stress condition
    has changed one of its parameters' value."
   ::= { intgrnAlertTrap 36 }

-- 1.3.6.1.4.1.19004.0.37
intgrnTrapWasteActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Waste condition
    became active."
   ::= { intgrnAlertTrap 37 }

-- 1.3.6.1.4.1.19004.0.38
intgrnTrapWasteClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Waste condition
    became inactive."
   ::= { intgrnAlertTrap 38 }

-- 1.3.6.1.4.1.19004.0.39
intgrnTrapWasteChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Waste condition
    has changed one of its parameters' value."
   ::= { intgrnAlertTrap 39 }

-- 1.3.6.1.4.1.19004.0.40
intgrnTrapDensityActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Density condition
    became active."
   ::= { intgrnAlertTrap 40 }

-- 1.3.6.1.4.1.19004.0.41
intgrnTrapDensityClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Density condition
    became inactive."
   ::= { intgrnAlertTrap 41 }

-- 1.3.6.1.4.1.19004.0.42
intgrnTrapDensityChange NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing a Efficiency Alert that indicates a Density condition
    has changed one of its parameters' value."
   ::= { intgrnAlertTrap 42 }




--
-- Trap types that correspond to the different types of Administrative 
-- Alerts that can be generated. The data in the Admin. Alerts will be
-- only the generic data. Entity names and types will need to refelct
-- the VCOPs/Collector/Data Source components the alert pertains to.
-- 
-- intgrnAdminAlertTrap
--   |
--   +- intgrnTrapAliveComponentFailureActive (The VCOPs component has failed)
--   +- intgrnTrapAliveComponentFailureClear (The above condition has cleared)
--   +- intgrnTrapResourceDisconnectedActive (A resource was disconnected from VCOPs)
--   +- intgrnTrapResourceDIsconnectedClear (A disconnected resource has re-connected to VCOPs)
--

-- 1.3.6.1.4.1.19004.0.101
intgrnTrapAliveComponentFailureActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing an Administrative Alert that indicates an VCOPs Component failure
    became active."
   ::= { intgrnAlertTrap 101 }

-- 1.3.6.1.4.1.19004.0.102
intgrnTrapAliveComponentFailureClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing an Administrative Alert that indicates an VCOPs Component failure
    became inactive."
   ::= { intgrnAlertTrap 102 }

-- 1.3.6.1.4.1.19004.0.103
intgrnTrapResourceDisconnectedActive NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing an Administrative Alert that indicates a resource has disconnected
    from VCOPs."
   ::= { intgrnAlertTrap 103 }

-- 1.3.6.1.4.1.19004.0.104
intgrnTrapResourceDisconnectedClear NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "A trap describing an Administrative Alert that indicates that a disconnected
    resource has re-connected to VCOPs."
   ::= { intgrnAlertTrap 104 }


-- Trap for functional testing.
-- 
-- intgrnAdminAlertTrap
--   |
--   +- intgrnTrapTest (The test trap has succeeded)

-- 1.3.6.1.4.1.19004.0.200
intgrnTrapTest NOTIFICATION-TYPE
   OBJECTS {
      intgrnAlertAliveServerName,
      intgrnAlertEntityName,
      intgrnAlertEntityType,
      intgrnAlertTimestamp,
      intgrnAlertCriticality,
      intgrnAlertRootCause,
      intgrnAlertURL,
      intgrnAlertID,
      intgrnAlertMessage,
      intgrnAlertType,
      intgrnAlertSubtype
   }
   STATUS current
   DESCRIPTION
   "Trap for testing purposes."
   ::= { intgrnAlertTrap 200 }

-- conformance information
vmwVCOPSMIBConformance OBJECT IDENTIFIER ::= { vmwVcopsMIB 99 }
vmwVCOPSMIBCompliances OBJECT IDENTIFIER ::= { vmwVCOPSMIBConformance 1 }
vmwVCOPSMIBGroups OBJECT IDENTIFIER ::= { vmwVCOPSMIBConformance 2 }

-- compliance statements
vmwVCOPSMIBBasicCompliance MODULE-COMPLIANCE
    STATUS     current
    DESCRIPTION
        "The compliance statement for entities which implement VMWARE-VCOPS-EVENT-MIB."
    MODULE -- this module
    MANDATORY-GROUPS { vmwVCOPSNotificationInfoGroup, vmwVCOPSNotificationGroup }
    ::= { vmwVCOPSMIBCompliances 2 }

vmwVCOPSNotificationInfoGroup OBJECT-GROUP
    OBJECTS {
       intgrnAlertAliveServerName,
       intgrnAlertEntityName,
       intgrnAlertEntityType,
       intgrnAlertTimestamp,
       intgrnAlertCriticality,
       intgrnAlertRootCause,
       intgrnAlertURL,
       intgrnAlertID,
       intgrnAlertMessage,
       intgrnAlertType,
       intgrnAlertSubtype
    }
    STATUS current
    DESCRIPTION
	"These objects provide details in VCOPS notifications."
    ::= { vmwVCOPSMIBGroups 1 }

vmwVCOPSNotificationGroup NOTIFICATION-GROUP
       NOTIFICATIONS {
       intgrnTrapTest,
       intgrnTrapKPIBreachActive,
       intgrnTrapKPIBreachClear,
       intgrnTrapKPIBreachChange,
       intgrnTrapKPIPredictionActive,
       intgrnTrapKPIPredictionClear,
       intgrnTrapKPIPredictionChange,
       intgrnTrapAggregateAnomalyActive,
       intgrnTrapAggregateAnomalyClear,
       intgrnTrapKPIHTBreachActive,
       intgrnTrapKPIHTBreachClear,
       intgrnTrapKPIHTBreachChange,
       intgrnTrapNotificationActive,
       intgrnTrapNotificationClear,
       intgrnTrapNotificationChange,
       intgrnTrapAbnormalityActive,
       intgrnTrapAbnormalityClear,
       intgrnTrapAbnormalityChange,
       intgrnTrapWorkloadActive,
       intgrnTrapWorkloadClear,
       intgrnTrapWorkloadChange,
       intgrnTrapAnomalyActive,
       intgrnTrapAnomalyClear,
       intgrnTrapAnomalyChange,
       intgrnTrapFaultActive,
       intgrnTrapFaultClear,
       intgrnTrapFaultChange,
       intgrnTrapTimeRemainingActive,
       intgrnTrapTimeRemainingClear,
       intgrnTrapTimeRemainingChange,
       intgrnTrapCapacityRemainingActive,
       intgrnTrapCapacityRemainingClear,
       intgrnTrapCapacityRemainingChange,
       intgrnTrapStressActive,
       intgrnTrapStressClear,
       intgrnTrapStressChange,
       intgrnTrapWasteActive,
       intgrnTrapWasteClear,
       intgrnTrapWasteChange,
       intgrnTrapDensityActive,
       intgrnTrapDensityClear,
       intgrnTrapDensityChange,
       intgrnTrapAliveComponentFailureActive,
       intgrnTrapAliveComponentFailureClear,
       intgrnTrapResourceDisconnectedActive,
       intgrnTrapResourceDisconnectedClear
       }
       STATUS current
       DESCRIPTION
           "Group of objects describing notifications (traps)."
       ::= { vmwVCOPSMIBGroups 2 }

END
