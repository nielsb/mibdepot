MEF-SOAM-FM-MIB DEFINITIONS ::= BEGIN

-- *****************************************************************************
-- MEF ETHERNET SERVICE OAM (SOAM) MIB for Fault Management (FM)
-- *****************************************************************************

IMPORTS
    NOTIFICATION-TYPE, MODULE-IDENTITY, OBJECT-TYPE,
    Unsigned32, Counter32, Counter64, enterprises
        FROM SNMPv2-SMI         -- RFC 2578
    TruthValue, MacAddress, DateAndTime, TimeInterval
        FROM SNMPv2-TC          -- RFC 2579
    OBJECT-GROUP, NOTIFICATION-GROUP, MODULE-COMPLIANCE
        FROM SNMPv2-CONF        -- RFC 2580
    dot1agCfmMepEntry, Dot1agCfmPortStatus, Dot1agCfmInterfaceStatus,
    Dot1agCfmMDLevel, Dot1agCfmMepIdOrZero, Dot1agCfmMepDefects, 
    dot1agCfmMepDefects, dot1agCfmMepDbRMepState, dot1agCfmMepActive,
    dot1agCfmMdIndex, dot1agCfmMaIndex, dot1agCfmMepIdentifier,
    dot1agCfmMaNetEntry
        FROM IEEE8021-CFM-MIB   -- IEEE 802.1ag
    ieee8021CfmMaCompEntry, ieee8021CfmConfigErrorListErrorType
        FROM IEEE8021-CFM-V2-MIB --IEEE 802.1ap
    IEEE8021PriorityValue
        FROM IEEE8021-TC-MIB    -- IEEE 802.1ap
    MefSoamTcConnectivityStatusType, MefSoamTcDataPatternType,
    MefSoamTcIntervalTypeAisLck, MefSoamTcOperationTimeType, 
    MefSoamTcTestPatternType, MefSoamTcMegIdType
        FROM MEF-SOAM-TC-MIB
    EntityAdminState, EntityOperState
       FROM ENTITY-STATE-TC-MIB;  -- RFC 4268   

mefSoamFmMib MODULE-IDENTITY
    LAST-UPDATED    "201012160000Z" -- December 16, 2010
    ORGANIZATION    "Metro Ethernet Forum"
    CONTACT-INFO
       "Web URL: http://metroethernetforum.org/
        E-mail:  mibs@metroethernetforum.org
        Postal:  Metro Ethernet Forum
                 6033 W. Century Boulevard, Suite 830
                 Los Angeles, CA 90045
                 U.S.A.
        Phone:   +1 310-642-2800
        Fax:     +1 310-642-2808"
    DESCRIPTION
       "This MIB module contains the management objects for the
        management of Ethernet Services Operations, Administration
        and Maintenance for Fault Management and extends the
        Connectivity Fault Management IEEE 802.1 MIBs. Those areas
        that need no enhancements are not included
        as the existing IEEE MIBs support SOAM-FM functionality.

        Copyright 2010 Metro Ethernet Forum.
        All rights reserved."
    REVISION        "201012160000Z" -- December 16, 2010
    DESCRIPTION
            "Initial Version."
    ::= { enterprises mef(15007) mefSoam(1) 2 }

-- *****************************************************************************
--  Reference Overview
--
--  A number of base documents have been used to create the Textual Conventions
--  MIB, the SOAM-PM MIB and SOAM-FM MIB. The following are the 
--  abbreviations for the baseline documents:
--
--  [CFM] refers to 'Connectivity Fault Management', IEEE 802.1ag-2007, 
--      December 2007
--  [MEF7.1] refers to MEF 7.1 'Phase 2 EMS-NMS Information Model', 
--      October 2009
--  [MEF17] refers to MEF 17 'Service OAM Requirements & Framework - Phase 1',
--      April 2007
--  [MEF10.2] refers to MEF 10.2 'Ethernet Services Attributes Phase 2', Oct 2009
--  [MEF SOAM-PM] refers to 'Service OAM Performance Monitoring - Phase 1
--      Implementation Agreement', January 2010
--  [MEF SOAM-FM] refers to 'Service OAM Fault Management Implementation
--      Agreement', January 2011
--  [Q.840.1] refers to 'ITU-T Requirements and analysis for NMS-EMS
--      management interface of Ethernet over Transport and Metro Ethernet
--      Network (EoT/MEN)', March 2007
-- -[Y.1731] refers to ITU-T Y.1731 'OAM functions and mechanisms for Ethernet 
--  -   based networks', February 2008
-- *****************************************************************************

-- *****************************************************************************
-- Object definitions in the SOAM FM MIB Module
-- *****************************************************************************
mefSoamFmNotifications  OBJECT IDENTIFIER ::= { mefSoamFmMib 0 }
mefSoamFmMibObjects     OBJECT IDENTIFIER ::= { mefSoamFmMib 1 }
mefSoamFmMibConformance OBJECT IDENTIFIER ::= { mefSoamFmMib 2 }

-- *****************************************************************************
-- Groups in the SOAM FM MIB Module
-- ******************************************************************
mefSoamNet               OBJECT IDENTIFIER ::= { mefSoamFmMibObjects 1 }
mefSoamMeg               OBJECT IDENTIFIER ::= { mefSoamFmMibObjects 2 }
mefSoamMep               OBJECT IDENTIFIER ::= { mefSoamFmMibObjects 3 }
mefSoamCc                OBJECT IDENTIFIER ::= { mefSoamFmMibObjects 4 }
mefSoamAis               OBJECT IDENTIFIER ::= { mefSoamFmMibObjects 5 }
mefSoamLb                OBJECT IDENTIFIER ::= { mefSoamFmMibObjects 6 }
mefSoamLt                OBJECT IDENTIFIER ::= { mefSoamFmMibObjects 7 }
mefSoamLck               OBJECT IDENTIFIER ::= { mefSoamFmMibObjects 8 }
mefSoamTest              OBJECT IDENTIFIER ::= { mefSoamFmMibObjects 9 }
mefSoamFmNotificationCfg OBJECT IDENTIFIER ::= { mefSoamFmMibObjects 10 }

-- *****************************************************************************
-- The Ethernet Maintenance Entity Group (MEG)/Maintenance Association (MA) 
-- Objects. These groups contain all the objects needed to augment the
-- dot1agCfmMaNetTable and ieee8021CfmMaCompTable.
-- *****************************************************************************

-- *****************************************************************************
-- Net Table
-- *****************************************************************************

mefSoamNetCfgTable OBJECT-TYPE
    SYNTAX      SEQUENCE OF MefSoamNetCfgEntry
    MAX-ACCESS  not-accessible
    STATUS      current
    DESCRIPTION
       "This table is an extension of the dot1agCfmMaNetTable and rows
        are automatically added or deleted from this table based upon row
        creation and destruction of the dot1agCfmMaNetTable.

        This table represents the Maintenance Entity Group (Y.1731) 
        configuration that is unique from the Maintenance Association. 
        Each row in the table represents a MEG specific configuration.

        The writable objects in this table need to be persistent
        upon reboot or restart of a device.
       "
    ::= { mefSoamNet 1 }

mefSoamNetCfgEntry OBJECT-TYPE
    SYNTAX      MefSoamNetCfgEntry
    MAX-ACCESS  not-accessible
    STATUS      current
    DESCRIPTION
            "The conceptual row of mefSoamNetCfgTable."
    AUGMENTS {
             dot1agCfmMaNetEntry
             }
    ::= { mefSoamNetCfgTable 1 }

MefSoamNetCfgEntry ::= SEQUENCE {
      mefSoamNetCfgY1731Compliant                  TruthValue,
      mefSoamNetCfgMegIdFormat                     MefSoamTcMegIdType,
      mefSoamNetCfgMegLevel                        Dot1agCfmMDLevel
    }

mefSoamNetCfgY1731Compliant OBJECT-TYPE
    SYNTAX      TruthValue
    MAX-ACCESS  read-create
    STATUS      current
    DESCRIPTION
        "A boolean flag to indicate whether the MEG ID/MAID for this MEG
         operates in conformance with 802.1ag (if FALSE) or Y.1731 (if TRUE).
         When set to FALSE:
           - The format of the MAID (Maintenance Association ID) is controlled 
             by the dot1agCfmMdFormat, dot1agCfmMdName, dot1agCfmMaNetFormat 
             and dot1agCfmMaNetName objects.
           - The mefSoamNetMegIdFormat and mefSoamNetMegLevel objects are 
             ignored.
           - The level is controlled by the dot1agCfmMdMdLevel object.
         When set to TRUE:
           - The MEG shall be in a domain where dot1agCfmMdFormat has 
             the value none(1).
           - The format of the MEG ID is as defined by 
             mefSoamNetMegIdFormat.  
           - The dot1agCfmMaNetFormat object is ignored.  
           - The dot1agCfmMaNetName object contains the MEG ID value.
           - The dot1agCfmMdMdLevel object is ignored, and the level is 
             controlled by the mefSoamNetMegLevel object.
        "
    ::= { mefSoamNetCfgEntry 1 }

mefSoamNetCfgMegIdFormat OBJECT-TYPE
    SYNTAX MefSoamTcMegIdType
    MAX-ACCESS  read-create
    STATUS      current
    DESCRIPTION
        "If mefSoamNetY1731Compliant is set to TRUE, this object indicates
         the MEG ID format of the value set in dot1agCfmMaNetName. Otherwise,
         this object is ignored.
        "
    DEFVAL { charString }
    ::= { mefSoamNetCfgEntry 2 }

mefSoamNetCfgMegLevel OBJECT-TYPE
    SYNTAX        Dot1agCfmMDLevel
    MAX-ACCESS  read-create
    STATUS      current
    DESCRIPTION
        "If mefSoamNetY1731Compliant is set to TRUE, this object indicates
         the MEG Level of the MEG.  Otherwise, this object is ignored.
        "
    ::= { mefSoamNetCfgEntry 3 }

-- *****************************************************************************
-- MEG Table
-- *****************************************************************************

mefSoamMegCfgTable OBJECT-TYPE
    SYNTAX      SEQUENCE OF MefSoamMegCfgEntry
    MAX-ACCESS  not-accessible
    STATUS      current
    DESCRIPTION
       "This table is an extension of the ieee8021CfmMaCompTable and rows
        are automatically added or deleted from this table based upon row
        creation and destruction of the ieee8021CfmMaCompTable.

        This table represents the Maintenance Entity Group (Y.1731) or 
        Maintenance Association (802.1ag). An MEG/MA is a set of MEPs, 
        each configured to the same service inside a common OAM domain. 

        This is the part of the complete MEG/MA table that is variable
        across the Bridges in a Maintenance Domain, or across the
        components of a single Bridge. Each row in the table represents an
        MEG/MA.

        For a Point-to-Point Ethernet Virtual Connection (EVC), a MEG contains
        a single Maintenance Entity (ME). For a Multipoint-to-Multipoint EVC or
        a Rooted Multipoint EVC associating 'n' User-to-Network Interfaces (UNIs),
        a MEG contains n*(n-1)/2 MEs.

        The writable objects in this table need to be persistent
        upon reboot or restart of a device.
       "
    ::= { mefSoamMeg 1 }

mefSoamMegCfgEntry OBJECT-TYPE
    SYNTAX      MefSoamMegCfgEntry
    MAX-ACCESS  not-accessible
    STATUS      current
    DESCRIPTION
            "The conceptual row of mefSoamMegCfgTable."
    AUGMENTS {
             ieee8021CfmMaCompEntry
             }
    ::= { mefSoamMegCfgTable 1 }

MefSoamMegCfgEntry ::= SEQUENCE {
      mefSoamMegCfgConnectivityStatusInterval      Unsigned32,
      mefSoamMegCfgPeerMepInfoAgingTime            Unsigned32,
      mefSoamMegCfgPortStatusTlvIncluded           TruthValue,
      mefSoamMegCfgInterfaceStatusTlvIncluded      TruthValue
    }

mefSoamMegCfgConnectivityStatusInterval OBJECT-TYPE
    SYNTAX      Unsigned32 (1..2100000)
    UNITS       "ms"
    MAX-ACCESS  read-create
    STATUS      current
    DESCRIPTION
       "This attribute specifies a configurable time interval to 
        detect a change in Connectivity Status. This is the timer 
        timeout value that is used by the Remote Maintenance Endpoint (MEP)
        state machine.

        The default value is 3.5 times the length of the Continuity Check
        Messaage (CCM) interval. This attribute overrides the standard CCM
        loss of connectivity time  interval which is 3.5 times the CCM interval.

        Units are milliseconds.
       "
    REFERENCE
       "[MEF 17] R2c, [CFM] 20.1"
    ::= { mefSoamMegCfgEntry 1 }

mefSoamMegCfgPeerMepInfoAgingTime OBJECT-TYPE
    SYNTAX      Unsigned32 (0..86400)
    UNITS       "seconds"
    MAX-ACCESS  read-create
    STATUS      current
    DESCRIPTION
       "This attribute defines a period of time after which an 
        instance in the dot1agCfmMepDbTable is removed if a valid CCM has not
        been received by the local MEP, i.e. Dot1agCfmRemoteMepState is set to
        rMEPFailed for the period of time indicated by 
        mefSoamMegPeerMepInfoAgingTime.

        A value of zero indicates no aging will occur and the entry remains in the
        table forever.
       "
    DEFVAL {0}
    ::= { mefSoamMegCfgEntry 2 }

mefSoamMegCfgPortStatusTlvIncluded OBJECT-TYPE
    SYNTAX      TruthValue
    MAX-ACCESS  read-create
    STATUS      current
    DESCRIPTION
       "Indicates whether a Port Status TLV is included in CCM frame
        transmission. 

        A value of 'true' indicates that the Port Status TLV is to be included. 

        A value of 'false' indicates that the Port Status TLV is not to be 
        included.
       "
    REFERENCE
       "[MEF7.1] 9.2.2"
    DEFVAL { true }
    ::= { mefSoamMegCfgEntry 3 }

mefSoamMegCfgInterfaceStatusTlvIncluded OBJECT-TYPE
    SYNTAX      TruthValue
    MAX-ACCESS  read-create
    STATUS      current
    DESCRIPTION
       "Indicates whether a Interface Status TLV is included in CCM frame
        transmission. 

        A value of 'true' indicates that the Interface Status TLV is to be 
        included. 

        A value of 'false' indicates that the Interface Status TLV is not to
        be included.
       "
    REFERENCE
       "[MEF7.1] 9.2.2"
    DEFVAL { true }
    ::= { mefSoamMegCfgEntry 4 }



-- *****************************************************************************
-- Ethernet MEG End Point Object. This group contains all the objects needed to
-- enhance the standard MEP objects in the dot1agCfmMepTable.
-- *****************************************************************************

-- *****************************************************************************
-- MEP Status Table
-- *****************************************************************************

mefSoamMepStatusTable OBJECT-TYPE
    SYNTAX      SEQUENCE OF MefSoamMepStatusEntry
    MAX-ACCESS  not-accessible
    STATUS      current
    DESCRIPTION
       "This table is an extension of the dot1agCfmMepTable and rows
        are automatically added or deleted from this table based upon row
        creation and destruction of the dot1agCfmMepTable.

        This table represents the status of a MEG End Point or Maintenance End
        Point (MEP), which is a provisioned OAM reference point capable of
        initiating and terminating proactive SOAM PDU frames. A MEP is also capable
        of initiating and reacting to diagnostic SOAM PDU frames.
        Terminology is MEG End Point (Y.1731) or MA End Point (802.1ag).
       "
    ::= { mefSoamMep 1 }

mefSoamMepStatusEntry OBJECT-TYPE
    SYNTAX      MefSoamMepStatusEntry
    MAX-ACCESS  not-accessible
    STATUS      current
    DESCRIPTION
        "The conceptual row of mefSoamMepTable."
    AUGMENTS {
             dot1agCfmMepEntry
             }
    ::= { mefSoamMepStatusTable 1 }

MefSoamMepStatusEntry ::= SEQUENCE {
      mefSoamMepStatusOperationalState           EntityOperState,
      mefSoamMepStatusConnectivityStatus         MefSoamTcConnectivityStatusType,
      mefSoamMepStatusSentPortStatus             Dot1agCfmPortStatus,
      mefSoamMepStatusSentInterfaceStatus        Dot1agCfmInterfaceStatus,
      mefSoamMepStatusLastDefectSentStatus       Dot1agCfmMepDefects,
      mefSoamMepStatusRdiTransmitStatus          TruthValue
    }

mefSoamMepStatusOperationalState OBJECT-TYPE
    SYNTAX      EntityOperState
    MAX-ACCESS  read-only
    STATUS      current
    DESCRIPTION
       "This attribute indicates the operational state (current
        capability) of the MEP. 

        If the value is 'enabled', the MEP is able to provide OAM capabilities 
        and has been set to active via the dot1agCfmMepActive object.
 
        If the value is 'disabled' the MEP is not able to provide OAM 
        capabilities, for example because it has been disabled via the 
        dot1agCfmMepActive object, has detected an operational failure 
        condition, or has failed an internal test. 

        If the value is 'testing' the MEP has been placed into a test mode, 
        either a troubleshooting mode or ETH-Test 'Out-of-service' mode.

        If the value is 'unknown' the MEP is unable to report the operational 
       state.
       "
    REFERENCE
       "[MEF7.1] 9.2.5"
    ::= { mefSoamMepStatusEntry 1 }

mefSoamMepStatusConnectivityStatus OBJECT-TYPE
    SYNTAX      MefSoamTcConnectivityStatusType
    MAX-ACCESS  read-only
    STATUS      current
    DESCRIPTION
       "This attribute indicates the connectivity status for a MEP
        in an EVC ME. 

        An 'active' MEP Connectivity Status refers to the ability to exchange
        SOAM PDU frames among all the UNIs of an EVC. 

        A 'partiallyActive' MEP Connectivity Status refers to the ability to
        exchange SOAM PDU frames among some but not all the UNIs of an EVC. 

        An 'inactive' MEP Connectivity Status refers to the inability to 
        exchange SOAM PDU frames among any of the UNIs of an EVC.
       "
    ::= { mefSoamMepStatusEntry 2 }

mefSoamMepStatusSentPortStatus OBJECT-TYPE
    SYNTAX      Dot1agCfmPortStatus
    MAX-ACCESS  read-only
    STATUS      current
    DESCRIPTION
       "An enumerated value of the Port status TLV sent in the
        last CCM from the local MEP or the default value
        psNoPortStateTLV indicating no CCM has been sent or
        no Port Status TLV has been sent.
       "
    REFERENCE
       "[CFM] 17.5"
    DEFVAL { psNoPortStateTLV }
    ::= { mefSoamMepStatusEntry 3 }

mefSoamMepStatusSentInterfaceStatus OBJECT-TYPE
    SYNTAX      Dot1agCfmInterfaceStatus
    MAX-ACCESS  read-only
    STATUS      current
    DESCRIPTION
       "An enumerated value of the Interface status TLV sent 
        in the last CCM from the local MEP or the default value
        isNoInterfaceStatus TLV indicating no CCM has been sent or
        no Interface Status TLV has been sent.
       "
    REFERENCE
       "[CFM] 17.5"
    DEFVAL { isNoInterfaceStatusTLV }
    ::= { mefSoamMepStatusEntry 4 }

mefSoamMepStatusLastDefectSentStatus OBJECT-TYPE
    SYNTAX      Dot1agCfmMepDefects
    MAX-ACCESS  read-only
    STATUS      current
    DESCRIPTION
       "This attribute indicates the state of the previous MEP defects, 
        dot1agCfmMepDefects, that was sent with the previous
        mefSoamMepDefect notification. It is always some *previous* value
        of dot1agCfmMepDefects. Once an mefSoamMepDefect is sent
        the dot1agCfmMepDefects that was sent in the notification
        updates the contents of this object.

        If no mefSoamMepDefect notification has been sent the value of
        this object is '0'.
       "
    DEFVAL { { } }
    ::= { mefSoamMepStatusEntry 5 }

mefSoamMepStatusRdiTransmitStatus OBJECT-TYPE
    SYNTAX      TruthValue
    MAX-ACCESS  read-only
    STATUS      current
    DESCRIPTION
       "Indicates whether the local MEP is generating a Remote Defect Indicator
        (RDI) bit in the CCM that it transmits. 

        A value of 'true' indicates that a RDI bit was set in the last CCM that
        the MEP transmitted. 

        A value of 'false' indicates that the last CCM transmitted by the MEP 
        did not set the RDI bit or that a CCM has never been transmitted by the
        MEP.
       "
    DEFVAL { true }
    ::= { mefSoamMepStatusEntry 6 }

-- *****************************************************************************
-- MEP Statistic Table
-- *****************************************************************************

mefSoamMepFmStatsTable OBJECT-TYPE
    SYNTAX  SEQUENCE OF MefSoamMepFmStatsEntry
    MAX-ACCESS  not-accessible
    STATUS  current
    DESCRIPTION
       "This table is an extension of the dot1agCfmMepTable and rows
        are automatically added or deleted from this table based upon row
        creation and destruction of the dot1agCfmMepTable.

        This object contains the set of service OAM fault management
        statistics to be collected for each Maintenance End Point.
       "
    ::= { mefSoamMep 2 }

mefSoamMepFmStatsEntry OBJECT-TYPE
    SYNTAX  MefSoamMepFmStatsEntry
    MAX-ACCESS  not-accessible
    STATUS  current
    DESCRIPTION
       "The conceptual row of mefSoamMepFmStatsTable."
    AUGMENTS {
             dot1agCfmMepEntry
             }
    ::= { mefSoamMepFmStatsTable 1 }

MefSoamMepFmStatsEntry ::= SEQUENCE {
    mefSoamMepFmStatsInOamFramesDiscarded        Counter32,
    mefSoamMepFmStatsInCcmTotal                  Counter32
}

mefSoamMepFmStatsInOamFramesDiscarded OBJECT-TYPE
    SYNTAX      Counter32
    MAX-ACCESS  read-only
    STATUS      current
    DESCRIPTION
       "This attribute indicates the count of incoming OAM frames discarded
        at the MEP. This count includes frames discarded because they have
        an unknown OpCode, and frames (other than CCMs) discarded because
        they have a level below the level of the MEP.  In other words, this 
        attribute counts frames discarded by the MEP Equal OpCode 
        Demultiplexer and the MEP Low OpCode Demultiplexer described in IEEE 
        802.1ag-2007 Sn 19.2.7, Table 19-1 and Figure 19-2.
        This count does not include frames that are malformed, or that 
        contain OpCode-specific errors (such as CCM defects or LBRs with bad 
        data).
       "
     ::= { mefSoamMepFmStatsEntry 1 }

mefSoamMepFmStatsInCcmTotal OBJECT-TYPE
    SYNTAX      Counter32
    MAX-ACCESS  read-only
    STATUS      current
    DESCRIPTION
       "This attribute indicates the count of the total number of valid (not
        malformed) CCMs received by the MEP.  In other words, it counts the
        frames received by the MEP Continuity Check Receiver described in IEEE
        802.1ag-2007 Sn 19.2.8 and Figure 19-2.  This includes CCMs at a lower
        level, CCMs with defects, CCMs from an unexpected peer MEP and
        out-of-sequence CCMs.  It does not include CCMs at a higher level than
        the MEP.
       "
     ::= { mefSoamMepFmStatsEntry 2 }

-- *****************************************************************************
-- Ethernet Continuity Check Configuration Object. This group contains all the
-- objects needed to enhance the standard MEP CC objects.
-- *****************************************************************************

-- *****************************************************************************
-- Continuity Check Configuration Table
-- *****************************************************************************

mefSoamCcCfgTable OBJECT-TYPE
    SYNTAX      SEQUENCE OF MefSoamCcCfgEntry
    MAX-ACCESS  not-accessible
    STATUS      current
    DESCRIPTION
       "This table is an extension of the dot1agCfmMepTable and rows
        are automatically added or deleted from this table based upon row
        creation and destruction of the dot1agCfmMepTable.

        This table includes configuration attributes and
        operations for the proactive Ethernet OAM Fault Management
        and Performance Monitoring Continuity Check function
        (ETH-CC) as defined in Y.1731 and 802.1ag.

        ETH-CC can be used for the following applications:
        
        - Used to detect loss of continuity between any pair of
           MEPs in a MEG.

        - Used to detect unintended connectivity conditions and
          other defect conditions.

        The OAM PDU used for ETH-CC and ETH-RDI information is CCM.

        This table also includes configuration attributes for the
        Ethernet OAM Fault Management Remote Defect Indication 
        function (ETH-RDI) as defined in Y.1731. ETH-RDI can be 
        used for the following applications:
        
        - Single-ended fault management: The receiving MEP 
          detects an RDI defect condition, which gets correlated 
          with other defect conditions in this MEP and may become a
          fault cause. The absence of received ETH-RDI information
          in a single MEP indicates the absence of defects in the 
          entire MEG.

        - Contribution to far-end performance monitoring: It 
          reflects that there was a defect condition in the far end
          which is used as an input to the performance monitoring 
          process.
       
        ETH-CC and ETH-RDI functions are only applicable to MEPs.
            
        The writable objects in this table need to be persistent
        upon reboot or restart of a device.
       "
    ::= { mefSoamCc 1 }

mefSoamCcCfgEntry OBJECT-TYPE
    SYNTAX      MefSoamCcCfgEntry
    MAX-ACCESS  not-accessible
    STATUS      current
    DESCRIPTION
       "The conceptual row of mefSoamCcCfgTable."
    AUGMENTS {
             dot1agCfmMepEntry
             }
    ::= { mefSoamCcCfgTable 1 }

MefSoamCcCfgEntry ::= SEQUENCE {
      mefSoamCcCfgDropEligible          TruthValue
    }

mefSoamCcCfgDropEligible OBJECT-TYPE
    SYNTAX      TruthValue
    MAX-ACCESS  read-create
    STATUS      current
    DESCRIPTION
       "This attribute specifies the eligibility of frames with
        ETH-CC and ETH-RDI information to be discarded when
        congestion conditions are encountered. 

        The value 'true' indicates frames are eligible to be discarded. 

        The value 'false' indicates frames are not eligible to be discarded.

        This attribute may be constrained to read-only in some
        implementations.
       "
    REFERENCE
       "[MEF7.1] 9.3.1.1"
    DEFVAL { false }
    ::= { mefSoamCcCfgEntry 1 }

-- *****************************************************************************
-- Ethernet Alarm Indication Signal (AIS) Configuration Object. This group 
-- contains all the objects needed to define the AIS functionality.
-- *****************************************************************************

-- *****************************************************************************
-- AIS Configuration Table
-- *****************************************************************************

mefSoamAisCfgTable OBJECT-TYPE
    SYNTAX      SEQUENCE OF MefSoamAisCfgEntry
    MAX-ACCESS  not-accessible
    STATUS      current
    DESCRIPTION
       "This table is an extension of the dot1agCfmMepTable and rows
        are automatically added or deleted from this table based upon row
        creation and destruction of the dot1agCfmMepTable.

        This table includes configuration attributes and
        operations for the proactive Ethernet OAM Fault Management
        Alarm Indication Signal function (ETH-AIS) as defined in
        Y.1731. ETH-AIS can be used for the following applications:

        - Used to suppress alarms following detection of defect 
          conditions (e.g., signal fail conditions when ETH-CC is
          enabled or AIS condition or LCK condition when ETH-CC is
          disabled).

        The OAM PDU used for ETH-AIS information is AIS. This function is 
        only applicable to MEPs. VLAN encapsulation on the generated AIS PDU
        is application dependent and dependent upon the level on which it is
        generated.

        The writable objects in this table need to be persistent
        upon reboot or restart of a device.
       "
    ::= { mefSoamAis 1 }

mefSoamAisCfgEntry OBJECT-TYPE
    SYNTAX      MefSoamAisCfgEntry
    MAX-ACCESS  not-accessible
    STATUS      current
    DESCRIPTION
            "The conceptual row of mefSoamAisCfgTable."
    AUGMENTS {
             dot1agCfmMepEntry
             }
    ::= { mefSoamAisCfgTable 1 }

MefSoamAisCfgEntry ::= SEQUENCE {
    mefSoamAisCfgEnabled       TruthValue,
    mefSoamAisCfgInterval      MefSoamTcIntervalTypeAisLck,
    mefSoamAisCfgPriority      IEEE8021PriorityValue,
    mefSoamAisCfgMdLevel       Dot1agCfmMDLevel,
    mefSoamAisCfgDropEligible  TruthValue
    }

mefSoamAisCfgEnabled OBJECT-TYPE
    SYNTAX      TruthValue
    MAX-ACCESS  read-create
    STATUS      current
    DESCRIPTION
       "This attribute specifies whether ETH-AIS transmission is 
        enabled. 

        The value 'true' indicates ETH-AIS transmission is enabled. 

        The value 'false' indicates ETH-AIS transmission is disabled.
       "
    REFERENCE
       "[MEF7.1] 9.3.4.1, [SOAM-FM] 8.4"
    DEFVAL { false }
    ::= { mefSoamAisCfgEntry 1 }

mefSoamAisCfgInterval OBJECT-TYPE
    SYNTAX      MefSoamTcIntervalTypeAisLck
    MAX-ACCESS  read-create
    STATUS      current
    DESCRIPTION
       "This attribute specifies the ETH-AIS transmission period.
        The default value is 1 frame per second.
       "
    REFERENCE
       "[MEF7.1] 9.3.4.1"
    DEFVAL { oneSecond }
    ::= { mefSoamAisCfgEntry 2 }

mefSoamAisCfgPriority OBJECT-TYPE
    SYNTAX      IEEE8021PriorityValue
    MAX-ACCESS  read-create
    STATUS      current
    DESCRIPTION
       "This attribute specifies the priority of frames with
        ETH-AIS information. 

        The default value MUST be the value which yields the lowest frame 
        loss for this EVC.
       "
    REFERENCE
       "[MEF7.1] 9.3.4.1"
    ::= { mefSoamAisCfgEntry 3 }

mefSoamAisCfgMdLevel OBJECT-TYPE
    SYNTAX      Dot1agCfmMDLevel
    MAX-ACCESS  read-create
    STATUS      current
    DESCRIPTION
       "The MEG/Maintenance Domain Level of the Client ETH-AIS PDU (transmitted
        level).
       "
    REFERENCE
       "[Y.1731] 7.4"
    DEFVAL { 0 }
    ::= { mefSoamAisCfgEntry 4 }

mefSoamAisCfgDropEligible OBJECT-TYPE
    SYNTAX      TruthValue
    MAX-ACCESS  read-create
    STATUS      current
    DESCRIPTION
       "This attribute specifies the eligibility of frames with
        ETH-AIS information to be discarded when congestion
        conditions are encountered. 

        The value 'true' indicates frames are eligible to be discarded. 

        The value 'false' indicates frames are not eligible to be discarded. 

        This attribute may be constrained to read-only in some implementations.
       "
    REFERENCE
       "[MEF7.1] 9.3.4.1"
    DEFVAL { false }
    ::= { mefSoamAisCfgEntry 5 }

-- *****************************************************************************
-- AIS Stats Table
-- *****************************************************************************

mefSoamAisStatsTable OBJECT-TYPE
    SYNTAX      SEQUENCE OF MefSoamAisStatsEntry
    MAX-ACCESS  not-accessible
    STATUS      current
    DESCRIPTION
       "This table is an extension of the dot1agCfmMepTable and rows
        are automatically added or deleted from this table based upon row
        creation and destruction of the dot1agCfmMepTable.

        This table includes status and counter values ETH-AIS function.
       "
    ::= { mefSoamAis 2 }

mefSoamAisStatsEntry OBJECT-TYPE
    SYNTAX      MefSoamAisStatsEntry
    MAX-ACCESS  not-accessible
    STATUS      current
    DESCRIPTION
            "The conceptual row of mefSoamAisStatsTable."
    AUGMENTS {
             dot1agCfmMepEntry
             }
    ::= { mefSoamAisStatsTable 1 }

MefSoamAisStatsEntry ::= SEQUENCE {
    mefSoamAisStatsOutStatus        TruthValue,
    mefSoamAisStatsOutCounter       Counter32,
    mefSoamAisStatsInStatus         TruthValue,
    mefSoamAisStatsInCounter        Counter32,
    mefSoamAisStatsInMacAddr        MacAddress
    }

mefSoamAisStatsOutStatus OBJECT-TYPE
    SYNTAX      TruthValue
    MAX-ACCESS  read-only
    STATUS      current
    DESCRIPTION
       "This attribute specifies the current AIS transmission status
        of the MEP. 

        The value 'true' indicates AIS frames are currently being transmitted 
        by the MEP. 

        The value 'false' indicates AIS frames are not currently being transmitted
        by the MEP.
       "
    REFERENCE
       "[Y.1731] 7.4"
    ::= { mefSoamAisStatsEntry 1 }

mefSoamAisStatsOutCounter OBJECT-TYPE
    SYNTAX      Counter32
    MAX-ACCESS  read-only
    STATUS      current
    DESCRIPTION
       "This attribute contains the count of the total number of
        AIS messages sent by the MEP to a peer or a client. The count is 
        incremented every time an AIS PDU is transmitted by the MEP.

        The initial value of the object when the row is created is zero.
       "
    ::= { mefSoamAisStatsEntry 2 } 

mefSoamAisStatsInStatus OBJECT-TYPE
    SYNTAX      TruthValue
    MAX-ACCESS  read-only
    STATUS      current
    DESCRIPTION
       "This attribute specifies the current AIS receive status
        of the MEP. 

        The value 'true' indicates an AIS PDU has been received and 3.5 times
        the interval defined in the PDU has not yet passed, otherwise it is
        'false'.
       "
    REFERENCE
       "[Y.1731] 7.4"
    ::= { mefSoamAisStatsEntry 3 }

mefSoamAisStatsInCounter OBJECT-TYPE
    SYNTAX      Counter32
    MAX-ACCESS  read-only
    STATUS      current
    DESCRIPTION
       "This attribute contains the count of the total number of
        AIS messages received by the MEP. The count is incremented every time
        an AIS PDU is received by the MEP.

        The initial value of the object when the row is created is zero.
       "
    ::= { mefSoamAisStatsEntry 4 } 

mefSoamAisStatsInMacAddr OBJECT-TYPE
    SYNTAX      MacAddress
    MAX-ACCESS  read-only
    STATUS      current
    DESCRIPTION
       "The source MAC Address Field of last AIS received by the MEP. If no AIS
        PDU has been received by the NE the MAC address is set to all zeros.
       "
    REFERENCE
       "[Y.1731] 7.7"
    ::= { mefSoamAisStatsEntry 5 }

-- *****************************************************************************
-- Ethernet Loopback Configuration Object. This group contains all the objects
-- needed to enhance the standard CFM loopback functionality.
-- *****************************************************************************

-- *****************************************************************************
-- Loopback Configuration Table
-- *****************************************************************************

mefSoamLbCfgTable OBJECT-TYPE
    SYNTAX      SEQUENCE OF MefSoamLbCfgEntry
    MAX-ACCESS  not-accessible
    STATUS      current
    DESCRIPTION
       "This table is an extension of the dot1agCfmMepTable and rows
        are automatically added or deleted from this table based upon row
        creation and destruction of the dot1agCfmMepTable.

        This table includes configuration attributes and
        operations for the on-demand Ethernet OAM Fault Management
        Loopback function (ETH-LB) as defined in Y.1731 and
        802.1ag. ETH-LM can be used for the following applications:
            - To verify bidirectional connectivity of a MEP with a MIP
              or a peer MEP.
            - To perform a bidirectional in-service or out-of-service 
              diagnostics test between a pair of peer MEPs. This includes
              verifying bandwidth throughput, detecting bit errors, etc.
        The OAM PDU used for ETH-LB request information is LBM. The
        OAM PDU used for ETH-LB reply is LBR. Unicast frames
        carrying the LBM PDU are called Unicast LBM frames. Unicast
        frames carrying the LBR PDU are called Unicast LBR frames.
        Multicast frames carrying the LBM PDU are called Multicast
        LBM frames. Multicast frames carrying the LBR PDU are
        called Multicast LBR frames.

        This functionality is similar to a 'ping'.

        The writable objects in this table need to be persistent
        upon reboot or restart of a device.
       "
    ::= { mefSoamLb 1 }

mefSoamLbCfgEntry OBJECT-TYPE
    SYNTAX      MefSoamLbCfgEntry
    MAX-ACCESS  not-accessible
    STATUS      current
    DESCRIPTION
       "The conceptual row of mefSoamLbCfgTable."
    AUGMENTS {
             dot1agCfmMepEntry
             }
    ::= { mefSoamLbCfgTable 1 }

MefSoamLbCfgEntry ::= SEQUENCE {
    mefSoamLbCfgMulticastEnabled  TruthValue,
    mefSoamLbCfgInterval          Unsigned32,
    mefSoamLbCfgFrameSize         Unsigned32,
    mefSoamLbCfgDataPattern       MefSoamTcDataPatternType,
    mefSoamLbCfgTestTlvIncluded   TruthValue,
    mefSoamLbCfgTestTlvPattern    MefSoamTcTestPatternType,
    mefSoamLbCfgTimeout           Unsigned32
    }

mefSoamLbCfgMulticastEnabled OBJECT-TYPE
    SYNTAX      TruthValue
    MAX-ACCESS  read-create
    STATUS      current
    DESCRIPTION
       "This attribute specifies whether a MEP uses unicast or 
        multicast to send the ETH-LB messages (LBM).The 802.1ag standard
        only allows unicast LBM. ITU-T Y.1731 allows LBM to be multicast.
        This attribute allows the MEP to send either multicast or unicast
        LBM on a per MEP basis.

        The value 'true' indicates multicast is enabled. 

        The value 'false' indicates unicast is enabled.
       "
    REFERENCE
       "[MEF7.1] 9.3.2.1" 
    DEFVAL { false }
    ::= { mefSoamLbCfgEntry 1 }

mefSoamLbCfgInterval OBJECT-TYPE
    SYNTAX      Unsigned32 (0..60000)
    UNITS       "ms"
    MAX-ACCESS  read-create
    STATUS      current
    DESCRIPTION
       "This attribute specifies the period between LBM
        transmissions in an LB Session. For an LB Session, the
        period for LBM transmission is configurable in the range
        0 and sixty seconds (60 s). Granularity of 100ms is required.

        The transmission of the next LBM is not dependent upon the reception
        the first LBR. The next LBM is sent out based upon the interval count. 

        An interval count of '0' indicates that the subsequent LBM is sent with 
        the minimum possible delay.
       "
    REFERENCE
       "[MEF7.1] 9.3.2.1" 
    DEFVAL { 1000 }
    ::= { mefSoamLbCfgEntry 2 }

mefSoamLbCfgFrameSize OBJECT-TYPE
    SYNTAX      Unsigned32 (64..9600)
    UNITS       "bytes"
    MAX-ACCESS  read-create
    STATUS      current
    DESCRIPTION
       "This attribute specifies the LBM frame size. For an LB Session, the
        size of the LBM frame is configurable to any Ethernet frame size 
        between 64 Bytes and the maximum transmission unit of the EVC. 

        The range of frame sizes from 64 through 2000 octets, in 4 octet 
        increments, MUST be supported, and the range of frame sizes from 2004
        through 9600 octets, in 4 octet increments, SHOULD be supported.  

        The adjustment to the frame size of the standard LBM PDU size is 
        accomplished  by the addition of a Data TLV or a Test TLV.

        Since the original IEEE8021-CFM-MIB defines the LBM frame size through
        the use of the Data TLV object (dot1agCfmMepTransmitLbmDataTlv) the
        mefSoamLbFrameSize object interacts with the 
        dot1agCfmMepTransmitLbmDataTlv object in the following ways:

        - If dot1agCfmMepTransmitLbmDataTlv is not zero length, the four new 
          objects, mefSoamLbFrameSize, mefSoamLbDataPattern, 
          mefSoamLbTestTlvIncluded and mefSoamLbTestTlvPattern are ignored.

        - Otherwise, if mefSoamLbFrameSize is non-zero then a Test TLV or Data
          TLV is included dependent upon the value of mefSoamLbTestTlvIncluded.
          The TLV included in the LBM frame is of sufficient length to result in an
          Ethernet frame of the size requested.

        - If a Data TLV is included (mefSoamLbTestTlvIncluded is 'false'), the
          contents are specified by mefSoamLbDataPattern.

        - If a Test TLV is included (mefSoamLbTestTlvIncluded is 'true'), the 
          contents are specified by mefSoamLbTestTlvPattern.
       " 
    REFERENCE
       "[MEF7.1] 9.3.2.1" 
    DEFVAL { 64 }
    ::= { mefSoamLbCfgEntry 3 }

mefSoamLbCfgDataPattern OBJECT-TYPE
    SYNTAX      MefSoamTcDataPatternType
    MAX-ACCESS  read-create
    STATUS      current
    DESCRIPTION
       "This attribute specifies the LBM data pattern included in a Data TLV
        when the size of the LBM frame is determined by the 
        mefSoamLbFrameSize object and mefSoamLbTestTlvIncluded is 'false'.
        
        If the frame size object does not define the LBM frame size or 
        mefSoamLbTestTlvIncluded is 'true' the value of this object is 
        ignored.
       " 
    DEFVAL { zeroPattern }
    ::= { mefSoamLbCfgEntry 4 }

mefSoamLbCfgTestTlvIncluded OBJECT-TYPE
    SYNTAX      TruthValue
    MAX-ACCESS  read-create
    STATUS      current
    DESCRIPTION
       "Indicates whether a Test TLV or Data TLV is included when the size
        of the LBM frame is determined by the mefSoamLbFrameSize object.
        
        A value of 'true' indicates that the Test TLV is to be included. 

        A value of 'false' indicates that the Data TLV is to be included.

        If the frame size object does not define the LBM frame size
        the value of this object is ignored.
       "
    REFERENCE
       "[Y.1731] 9.3"
    DEFVAL { false }
    ::= { mefSoamLbCfgEntry 5 }

mefSoamLbCfgTestTlvPattern OBJECT-TYPE
    SYNTAX      MefSoamTcTestPatternType
    MAX-ACCESS  read-create
    STATUS      current
    DESCRIPTION
       "This attribute specifies the type of test pattern to be
        sent in the LBM frame Test TLV when the size
        of LBM PDU is determined by the mefSoamLbFrameSize object and 
        mefSoamLbTestTlvIncluded is 'true'. 

        If the frame size object does not define the LBM frame size or 
        mefSoamLbTestTlvIncluded is 'false' the value of this object is 
        ignored.
       " 
    DEFVAL { null }
    ::= { mefSoamLbCfgEntry 6 }

mefSoamLbCfgTimeout OBJECT-TYPE
    SYNTAX      Unsigned32 (1..10000)
    UNITS       "ms"
    MAX-ACCESS  read-create
    STATUS      current
    DESCRIPTION
       "This attribute specifies the maximum amount of time to receive
        an LBR in response to a LBM. If a LBR is not received within
        the timeout value it is considered lost.
       " 
    DEFVAL {5000}
    ::= { mefSoamLbCfgEntry 7 }


-- *****************************************************************************
-- Loopback Stats Table
-- *****************************************************************************

mefSoamLbStatsTable OBJECT-TYPE
    SYNTAX      SEQUENCE OF MefSoamLbStatsEntry
    MAX-ACCESS  not-accessible
    STATUS      current
    DESCRIPTION
       "This table is an extension of the dot1agCfmMepTable and rows
        are automatically added or deleted from this table based upon row
        creation and destruction of the dot1agCfmMepTable.

        This table contains the counter and status attributes for
        the ETH-LB function.
       "
    ::= { mefSoamLb 2 }

mefSoamLbStatsEntry OBJECT-TYPE
    SYNTAX      MefSoamLbStatsEntry
    MAX-ACCESS  not-accessible
    STATUS      current
    DESCRIPTION
            "The conceptual row of mefSoamLbStatsTable."
    AUGMENTS {
             dot1agCfmMepEntry
             }
    ::= { mefSoamLbStatsTable 1 }

MefSoamLbStatsEntry ::= SEQUENCE {
      mefSoamLbStatsNumLbrInCrcErrors   Counter32
    }

mefSoamLbStatsNumLbrInCrcErrors OBJECT-TYPE
    SYNTAX      Counter32
    MAX-ACCESS  read-only
    STATUS      current
    DESCRIPTION
       "This attribute contains the count of the total number of
        LBR messages received with CRC errors This is only applicable when the 
        ETH-LB includes the test TLV with a test pattern of nullCrc32 or pbrsCrc32.

        The initial value of the object when the row is created is zero.
       "
    REFERENCE
       "[MEF7.1] 9.3.2.2" 
    ::= { mefSoamLbStatsEntry 1 } 

-- *****************************************************************************
-- Loopback Multicast Results Table
-- *****************************************************************************

mefSoamLbrMulticastTable OBJECT-TYPE
    SYNTAX      SEQUENCE OF MefSoamLbrMulticastEntry
    MAX-ACCESS  not-accessible
    STATUS      current
    DESCRIPTION
       "This table extends the MEP table and contains the responses from a
        Multicast Loopback message. It uses the same indexes as the 
        dot1agCfmMepTable.

        Rows in this table are automatically created, a new row for each
        response from a multicast loopback request. At the initiation of a 
        new multicast loopback operation all the previous rows in the table
        may be deleted automatically in order to conserve memory space.
       "
    ::= { mefSoamLb 3 }

mefSoamLbrMulticastEntry OBJECT-TYPE
    SYNTAX      MefSoamLbrMulticastEntry
    MAX-ACCESS  not-accessible
    STATUS      current
    DESCRIPTION
            "The conceptual row of mefSoamLbrMulticastTable."
    INDEX { dot1agCfmMdIndex,
            dot1agCfmMaIndex,
            dot1agCfmMepIdentifier,
            mefSoamLbrMulticastTransId,
            mefSoamLbrMulticastReceiveOrder
          }
    ::= { mefSoamLbrMulticastTable 1 }

MefSoamLbrMulticastEntry ::= SEQUENCE {
      mefSoamLbrMulticastTransId                Unsigned32,
      mefSoamLbrMulticastReceiveOrder           Unsigned32,
      mefSoamLbrMulticastReplyMac               MacAddress
    }

mefSoamLbrMulticastTransId OBJECT-TYPE
    SYNTAX      Unsigned32 (0..4294967295)
    MAX-ACCESS  not-accessible
    STATUS      current
    DESCRIPTION
       "Loopback transaction identifier returned by a previous loopback
        message command, indicating which loopback request is returned.
       "
    ::= { mefSoamLbrMulticastEntry 1 } 

mefSoamLbrMulticastReceiveOrder OBJECT-TYPE
    SYNTAX      Unsigned32 (0..4294967295)
    MAX-ACCESS  not-accessible
    STATUS      current
    DESCRIPTION
       "An index to distinguish among multiple LBRs with the same LBR
        Transaction Identifier field value. mefSoamLbrReceiveOrder are assigned
        sequentially from 1, in the order that the Loopback Initiator received
        the LBR.
       "
    ::= { mefSoamLbrMulticastEntry 2 } 

mefSoamLbrMulticastReplyMac OBJECT-TYPE
    SYNTAX      MacAddress
    MAX-ACCESS  read-only
    STATUS      current
    DESCRIPTION
       "Source MAC address returned in the LBR Ethernet frame.
       "
    REFERENCE
       "[CFM] 21.7, [Y.1731] 7.2"
    ::= { mefSoamLbrMulticastEntry 3 }

-- *****************************************************************************
-- Ethernet Linktrace Configuration Object. This group contains all the objects
-- needed to enhance the standard CFM linktrace functionality.
-- *****************************************************************************

-- *****************************************************************************
-- Linktrace Statistic Table
-- *****************************************************************************

mefSoamLtStatsTable OBJECT-TYPE
    SYNTAX      SEQUENCE OF MefSoamLtStatsEntry
    MAX-ACCESS  not-accessible
    STATUS      current
    DESCRIPTION
       "This table is an extension of the dot1agCfmMepTable and rows
        are automatically added or deleted from this table based upon row
        creation and destruction of the dot1agCfmMepTable.

        This table contains the counter and status attributes for
        the ETH-LT function.
       "
    ::= { mefSoamLt 1 }

mefSoamLtStatsEntry OBJECT-TYPE
    SYNTAX      MefSoamLtStatsEntry
    MAX-ACCESS  not-accessible
    STATUS      current
    DESCRIPTION
            "The conceptual row of mefSoamLtStatsTable."
    AUGMENTS {
             dot1agCfmMepEntry
             }
    ::= { mefSoamLtStatsTable 1 }

MefSoamLtStatsEntry ::= SEQUENCE {
      mefSoamLtLtmTransmitted           Counter32,
      mefSoamLtLtrReceived              Counter32,
      mefSoamLtLtmReceived              Counter32,
      mefSoamLtLtrTransmitted           Counter32
    }

mefSoamLtLtmTransmitted OBJECT-TYPE
    SYNTAX      Counter32
    MAX-ACCESS  read-only
    STATUS      current
    DESCRIPTION
       "This attribute contains the count of the total number of
        LTM messages transmitted by the MEP. 

        The initial value of the object when the row is created is zero.
       "
    ::= { mefSoamLtStatsEntry 1 } 

mefSoamLtLtrReceived OBJECT-TYPE
    SYNTAX      Counter32
    MAX-ACCESS  read-only
    STATUS      current
    DESCRIPTION
       "This attribute contains the count of the total number of
        LTR messages received by the MEP. 

        The initial value of the object when the row is created is zero.
       "
    ::= { mefSoamLtStatsEntry 2 } 

mefSoamLtLtmReceived OBJECT-TYPE
    SYNTAX      Counter32
    MAX-ACCESS  read-only
    STATUS      current
    DESCRIPTION
       "This attribute contains the count of the total number of
        LTM messages received by the MEP. 

        The initial value of the object when the row is created is zero.
       "
    ::= { mefSoamLtStatsEntry 3 } 

mefSoamLtLtrTransmitted OBJECT-TYPE
    SYNTAX      Counter32
    MAX-ACCESS  read-only
    STATUS      current
    DESCRIPTION
       "This attribute contains the count of the total number of
        LTR messages transmitted by the MEP. 

        The initial value of the object when the row is created is zero.
       "
    ::= { mefSoamLtStatsEntry 4 } 

-- *****************************************************************************
-- Ethernet Lock Configuration Object. This group contains all the objects
-- needed to define the Lck functionality.
-- *****************************************************************************

-- *****************************************************************************
-- Lck Configuration Table
-- *****************************************************************************

mefSoamLckCfgTable OBJECT-TYPE
    SYNTAX      SEQUENCE OF MefSoamLckCfgEntry
    MAX-ACCESS  not-accessible
    STATUS      current
    DESCRIPTION
       "This table is an extension of the dot1agCfmMepTable and rows
        are automatically added or deleted from this table based upon row
        creation and destruction of the dot1agCfmMepTable.

        This table includes configuration attributes and
        operations for the on-demand Ethernet OAM Fault Management
        Locked Signal function (ETH-LCK) as defined in Y.1731.
        ETH-LCK can be used for the following applications:

        - Used to communicate the administratively locking of a MEP
          and consequential interruption of data traffic forwarding
          toward the MEP expecting this traffic. This allows a MEP
          receiving ETH-LCK frames to distinguish between defect
          conditions and an administrative locking action.

        - Used by other OAM functions which require a MEP to be
          administratively locked, such as for out-of-service
          testing.

        The OAM PDU used for ETH-LCK information is LCK. VLAN encapsulation on
        the generated ETH-LCK PDU is application dependent and dependent upon
        the level on which it is generated.

        The writable objects in this table should be persistent
        upon reboot or restart of a device. It is not mandatory that they are
        persistent.
       "
    ::= { mefSoamLck 1 }

mefSoamLckCfgEntry OBJECT-TYPE
    SYNTAX      MefSoamLckCfgEntry
    MAX-ACCESS  not-accessible
    STATUS      current
    DESCRIPTION
            "The conceptual row of mefSoamLckCfgTable."
    AUGMENTS {
             dot1agCfmMepEntry
             }
    ::= { mefSoamLckCfgTable 1 }

MefSoamLckCfgEntry ::= SEQUENCE {
      mefSoamLckCfgAdminState   EntityAdminState,
      mefSoamLckCfgInterval     MefSoamTcIntervalTypeAisLck,
      mefSoamLckCfgPriority     IEEE8021PriorityValue,
      mefSoamLckCfgMdLevel      Dot1agCfmMDLevel
    }

mefSoamLckCfgAdminState OBJECT-TYPE
    SYNTAX      EntityAdminState
    MAX-ACCESS  read-create
    STATUS      current
    DESCRIPTION
       "This attribute specifies the locking state. 

        If mefSoamLckAdminState is set to 'locked', the MEP will be 
        administratively locked. 

        If mefSoamLckAdminState is set to 'unlocked', the MEP will be 
        administratively unlocked if previously locked. 

        Other values of mefSoamLckAdminState are undefined.
       "
    REFERENCE
       "[MEF7.1] 9.3.4.2"   
    DEFVAL { unlocked }
    ::= { mefSoamLckCfgEntry 1 }

mefSoamLckCfgInterval OBJECT-TYPE
    SYNTAX      MefSoamTcIntervalTypeAisLck
    MAX-ACCESS  read-create
    STATUS      current
    DESCRIPTION
       "This attribute specifies the ETH-LCK transmission period.
        The default value is 1 frame per second.
       "
    REFERENCE
       "[MEF7.1] 9.3.4.2"   
    DEFVAL { oneSecond }
    ::= { mefSoamLckCfgEntry 2 }

mefSoamLckCfgPriority OBJECT-TYPE
    SYNTAX      IEEE8021PriorityValue
    MAX-ACCESS  read-create
    STATUS      current
    DESCRIPTION
       "This attribute specifies the priority of frames with
        ETH-LCK information. 

        The default value MUST be the value which yields the lowest frame 
        loss for this EVC.
       "
    REFERENCE
       "[MEF7.1] 9.3.4.2"   
    ::= { mefSoamLckCfgEntry 3 }

mefSoamLckCfgMdLevel OBJECT-TYPE
    SYNTAX      Dot1agCfmMDLevel
    MAX-ACCESS  read-create
    STATUS      current
    DESCRIPTION
       "The MEG/Maintenance Domain Level of the Client LCK PDU (transmitted
        level).
       "
    REFERENCE
       "[Y.1731] 7.6"
    DEFVAL { 0 }
    ::= { mefSoamLckCfgEntry 4 }


-- *****************************************************************************
-- Lck Stats Table
-- *****************************************************************************

mefSoamLckStatsTable OBJECT-TYPE
    SYNTAX      SEQUENCE OF MefSoamLckStatsEntry
    MAX-ACCESS  not-accessible
    STATUS      current
    DESCRIPTION
       "This table is an extension of the dot1agCfmMepTable and rows
        are automatically added or deleted from this table based upon row
        creation and destruction of the dot1agCfmMepTable.

        This table contains the counter and status attributes for the
        ETH-LCK function. This object is used to capture
        statistics for both the sending and receiving MEPs.
       "
    ::= { mefSoamLck 2 }

mefSoamLckStatsEntry OBJECT-TYPE
    SYNTAX      MefSoamLckStatsEntry
    MAX-ACCESS  not-accessible
    STATUS      current
    DESCRIPTION
       "The conceptual row of mefSoamLckStatsTable."
    AUGMENTS {
             dot1agCfmMepEntry
             }
    ::= { mefSoamLckStatsTable 1 }

MefSoamLckStatsEntry ::= SEQUENCE {
      mefSoamLckStatsInStatus                    TruthValue,
      mefSoamLckStatsInCounter                   Counter32,
      mefSoamLckStatsOutStatus                   TruthValue,
      mefSoamLckStatsOutCounter                  Counter32
    }

mefSoamLckStatsInStatus OBJECT-TYPE
    SYNTAX      TruthValue
    MAX-ACCESS  read-only
    STATUS      current
    DESCRIPTION
       "This attribute specifies the current LCK receive status
        of the MEP. 

        The value 'true' indicates LCK frames are currently being received
        by the MEP. 

        The value 'false' indicates LCK frames are not currently being
        received by the MEP at the specified interval in the LCK PDU.

        If no LCK frames are received within an interval of 3.5 times the LCK
        transmission period indicated in the last LCK frame received, the MEP 
        clears the LCK condition by setting mefSoamLckInStatus to 'false'.
       "
    REFERENCE
       "[Y.1731] 7.6"
    ::= { mefSoamLckStatsEntry 1 }

mefSoamLckStatsInCounter OBJECT-TYPE
    SYNTAX      Counter32
    MAX-ACCESS  read-only
    STATUS      current
    DESCRIPTION
       "This attribute contains the count of the total number of LCK messages
        received. The count is incremented when a ETH-LCK message is received.
        This attribute is only applicable to the MEP receiving ETH-LCK messages.

        The initial value of the object when the row is created is zero.
       "
    REFERENCE
       "[Y.1731] 7.6"
    ::= { mefSoamLckStatsEntry 2 }

mefSoamLckStatsOutStatus OBJECT-TYPE
    SYNTAX      TruthValue
    MAX-ACCESS  read-only
    STATUS      current
    DESCRIPTION
       "This attribute specifies the current LCK transmission status
        of the MEP. 

        The value 'true' indicates LCK frames are currently being transmitted
        by the MEP. 

        The value 'false' indicates LCK frames are not currently being
        transmitted by the MEP.
       "
    REFERENCE
       "[Y.1731] 7.6"
    ::= { mefSoamLckStatsEntry 3 }

mefSoamLckStatsOutCounter OBJECT-TYPE
    SYNTAX      Counter32
    MAX-ACCESS  read-only
    STATUS      current
    DESCRIPTION
       "This attribute contains the count of the total number of
        LCK messages transmitted. This attribute is only applicable
        to the MEP sending ETH-LCK messages.

        The initial value of the object when the row is created is zero.
       "
    REFERENCE
       "[Y.1731] 7.6"
    ::= { mefSoamLckStatsEntry 4 }

-- *****************************************************************************
-- Ethernet Test Configuration Object. This group contains all the objects
-- needed to define the Test functionality.
-- *****************************************************************************

-- *****************************************************************************
-- Test Configuration Table
-- *****************************************************************************

mefSoamTestCfgTable OBJECT-TYPE
    SYNTAX      SEQUENCE OF MefSoamTestCfgEntry
    MAX-ACCESS  not-accessible
    STATUS      current
    DESCRIPTION
       "This table is an extension of the dot1agCfmMepTable and rows
        are automatically added or deleted from this table based upon row
        creation and destruction of the dot1agCfmMepTable 

        This table includes configuration attributes and
        operations for the on-demand OAM Fault Management Test
        function (ETH-Test) defined in Y.1731. The OAM PDU used
        for ETH-Test information is TST. This
        function is only applicable to MEPs.

        The writable objects in this table need to be persistent
        upon reboot or restart of a device.

        Steps to use entries in this table:

        1) Wait for mefSoamTestOutStatus value to be false by the following
           sequence:
           a. an SNMP GET for both SnmpSetSerialNo (SNMPv2-MIB, RFC 3418) and
              mefSoamTestOutStatus objects (in same SNMP PDU).
           b. Check if value for mefSoamTestOutStatus is false.
              - if not, wait a second, go to step a above.
              - if yes, save the value of SnmpSetSerialNo and go
                to step 2) below
        2) Change mefSoamTestOutStatus value from false to true to ensure
           no other management entity will use the service. In order to 
           avoid contention with other SNMP Managers, send an SNMP SET 
           for both SnmpSetSerialNo and mefSoamTestOutStatus objects (in same 
           SNMP PDU, and make sure SnmpSetSerialNo is the first varBind).
           For the SnmpSetSerialNo varBind, use the value that you obtained
           in step 1)a.. This ensures that two cooperating SNMP Managers will 
           not step on each other's toes. 
        3) Setup the different data to be sent and time to start, except do not
           set mefSoamTestOutEnabled.
        4) Record the current values of mefSoamTestNumIn, 
           mefSoamTestNumInOutOfOrder, mefSoamTestNumInCrcErrors, 
           mefSoamTestNumInBerErrors, mefSoamTestNumOut.
        5) Set mefSoamTestOutEnabled to a 'true' value to initiate 
           transmission of ETH-Test messages.
        6) Monitor the value of mefSoamTestOutEnabled. When it is reset to
           false, the last TST frame has been transmitted.
        7) Compare mefSoamTestNumIn, mefSoamTestNumInOutOfOrder, 
           mefSoamTestNumInCrcErrors, mefSoamTestNumInBerErrors, 
           mefSoamTestNumOut to their old values from step 4, above, to get 
           the results of the test.
        8) Change the mefSoamTestOutStatus value back to false to allow 
           other management entities to use the table.
       "
    ::= { mefSoamTest 1 }

mefSoamTestCfgEntry OBJECT-TYPE
    SYNTAX      MefSoamTestCfgEntry
    MAX-ACCESS  not-accessible
    STATUS      current
    DESCRIPTION
            "The conceptual row of mefSoamTestCfgTable."
    AUGMENTS {
             dot1agCfmMepEntry
             }
    ::= { mefSoamTestCfgTable 1 }

MefSoamTestCfgEntry ::= SEQUENCE {
      mefSoamTestCfgOutEnabled                 TruthValue,
      mefSoamTestCfgInEnabled                  TruthValue,
      mefSoamTestCfgInService                  TruthValue,
      mefSoamTestCfgDestMacAddress             MacAddress,
      mefSoamTestCfgDestMepId                  Dot1agCfmMepIdOrZero,
      mefSoamTestCfgDestIsMepId                TruthValue,
      mefSoamTestCfgInterval                   Unsigned32,
      mefSoamTestCfgPriority                   IEEE8021PriorityValue,
      mefSoamTestCfgDropEligible               TruthValue,
      mefSoamTestCfgFrameSize                  Unsigned32,
      mefSoamTestCfgPattern                    MefSoamTcTestPatternType,
      mefSoamTestCfgStartTimeType              MefSoamTcOperationTimeType,
      mefSoamTestCfgScheduledStartDateAndTime  DateAndTime,
      mefSoamTestCfgScheduledStopDateAndTime   DateAndTime,
      mefSoamTestCfgRelativeStartTime          TimeInterval,
      mefSoamTestCfgDurationTime               TimeInterval,
      mefSoamTestCfgOutStatus                  TruthValue
    }

mefSoamTestCfgOutEnabled OBJECT-TYPE
    SYNTAX      TruthValue
    MAX-ACCESS  read-create
    STATUS      current
    DESCRIPTION
       "This attribute specifies the enabling of the ETH-Test transmit function.
        
        A value of 'true' indicates that the ETH-Test transmit function is 
        enabled. 

        A value of 'false' indicates that ETH-Test function is disabled. The MEP
        ETH-Test Initiator State Machine sets this value to false to indicate
        that the ETH-Test transmission is completed.

        An SNMP Manager setting this variable to 'false' terminates an ETH-Test
        transmission function and sets mefSoamTestOutStatus to 'false'. The 
        desired method is to allow the State Machine to clear the enable, but
        the SNMP Manager may terminate the operation by clearing the object.
       "
    REFERENCE
       "[Y.1731] 7.7"   
    DEFVAL { false }
    ::= { mefSoamTestCfgEntry 1 }

mefSoamTestCfgInEnabled OBJECT-TYPE
    SYNTAX      TruthValue
    MAX-ACCESS  read-create
    STATUS      current
    DESCRIPTION
       "This attribute specifies the enabling of the ETH-Test receive function.
        
        A value of 'true' indicates that the ETH-Test receive function is 
        enabled. If the receiving MEP is configured for ETH-Test function, the 
        test signal detector associated with the MEP detects bit errors from 
        the pseudo-random bit sequence of the received TST frames and reports
        such errors via the mefSoamTestNumIn objects. 

        A value of 'false' indicates that ETH-Test receive function
        is disabled and ETH-Test frames received by the MEP are ignored.
       "
    REFERENCE
       "[Y.1731] 7.7.2"   
    DEFVAL { false }
    ::= { mefSoamTestCfgEntry 2 }

mefSoamTestCfgInService OBJECT-TYPE
    SYNTAX      TruthValue
    MAX-ACCESS  read-create
    STATUS      current
    DESCRIPTION
       "This attribute specifies the type of ETH-Test to perform, whether
        it is service interrupting or not. 

        A 'true' value indicates that the ETH-Test is 'in-service' and 
        normal client service traffic is not interrupted. 

        A 'false' value indicates that the ETH-Test is 'out-of-service' 
        and normal client service traffic is disrupted.

        When the type of ETH-Test is 'out-of-service' LCK frames are
        generated at the immediate client MEG level when enabled. For the
        ETH-Test generator the LCK frames are generated towards the ETH-Test
        receiver. For the ETH-Test receiver the LCK frames are generated at the 
        client MEG level in the direction in which the TST frames are received.
       "
    REFERENCE
       "[Y.1731] 7.7"   
    DEFVAL { true }
    ::= { mefSoamTestCfgEntry 3 }

mefSoamTestCfgDestMacAddress OBJECT-TYPE
    SYNTAX      MacAddress
    MAX-ACCESS  read-create
    STATUS      current
    DESCRIPTION
       "The Target MAC Address Field to be transmitted: A unicast
        destination MAC address.

        This address will be used if the value of the object
        mefSoamTestDestIsMepId is 'false'. 

        This object is only valid for the entity transmitting the 
        ETH-Test frames and is ignored by the entity receiving 
        ETH-Test frames.
       "
    REFERENCE
       "[Y.1731] 7.7"
    ::= { mefSoamTestCfgEntry 4 }

mefSoamTestCfgDestMepId OBJECT-TYPE
    SYNTAX      Dot1agCfmMepIdOrZero
    MAX-ACCESS  read-create
    STATUS      current
    DESCRIPTION
       "The Maintenance Association End Point Identifier of
        another MEP in the same Maintenance Association to which
        the TST frame is to be sent.

        This address will be used if the value of the column
        mefSoamTestDestIsMepId is 'true'. 

        A value of zero means that the destination MEP ID has not been
        configured.

       This object is only valid for the entity transmitting the ETH-Test 
       frames and is ignored by the entity receiving ETH-Test frames.
      "
    REFERENCE
       "[Y.1731] 7.7"
    DEFVAL { 0 }
    ::= { mefSoamTestCfgEntry 5 }

mefSoamTestCfgDestIsMepId OBJECT-TYPE
    SYNTAX      TruthValue
    MAX-ACCESS  read-create
    STATUS      current
    DESCRIPTION
       "A value of 'true' indicates that MEPID of the target MEP is used for
        TST frame transmission.

        A value of 'false' indicates that unicast destination MAC address of the
        target MEP is used for TST frame transmission.

       This object is only valid for the entity transmitting the ETH-Test 
       frames and is ignored by the entity receiving ETH-Test frames.
      "
    REFERENCE
       "[Y.1731] 7.7"
    DEFVAL { true }
    ::= { mefSoamTestCfgEntry 6 }

mefSoamTestCfgInterval OBJECT-TYPE
    SYNTAX      Unsigned32 (0..60000000)
    UNITS       "microseconds"
    MAX-ACCESS  read-create
    STATUS      current
    DESCRIPTION
       "This attribute specifies the ETH-Test transmission period
        between consecutive transmitted frames in microseconds. 

        A value of '0' indicates that the Test TLVs are sent as quickly as
        possible across the interface.

        This object is only valid for the entity transmitting the ETH-Test 
        frames and is ignored by the entity receiving ETH-Test frames.
       "
    REFERENCE
       "[MEF7.1] 9.3.4.3"
    DEFVAL { 1000000 }
    ::= { mefSoamTestCfgEntry 7 }

mefSoamTestCfgPriority OBJECT-TYPE
    SYNTAX      IEEE8021PriorityValue
    MAX-ACCESS  read-create
    STATUS      current
    DESCRIPTION
       "This attribute specifies the priority of the transmitted ETH-Test
        frames.
       
        This object is only valid for the entity transmitting the ETH-Test 
        frames and is ignored by the entity receiving ETH-Test frames.

        The default value MUST be the value which yields the lowest frame 
        loss for this EVC.
       "
    REFERENCE
       "[MEF7.1] 9.3.4.3"
    DEFVAL { 0 }
   ::= { mefSoamTestCfgEntry 8 }

mefSoamTestCfgDropEligible OBJECT-TYPE
    SYNTAX      TruthValue
    MAX-ACCESS  read-create
    STATUS      current
    DESCRIPTION
       "This attribute specifies the eligibility of frames with
        ETH-Test information to be discarded when congestion
        conditions are encountered. 

        The value 'true' indicates frames are eligible to be discarded. The
        value 'false' indicates frames are not eligible to be discarded. 

        This attribute may be constrained to read-only in some
        implementations.

        This object is only valid for the entity transmitting the ETH-Test 
        Frames and is ignored by the entity receiving ETH-Test frames.
       "
    REFERENCE
       "[MEF7.1] 9.3.4.3"
    DEFVAL { false }
    ::= { mefSoamTestCfgEntry 9 }

mefSoamTestCfgFrameSize OBJECT-TYPE
    SYNTAX      Unsigned32 (64..9600)
    UNITS       "bytes"
    MAX-ACCESS  read-create
    STATUS      current
    DESCRIPTION
       "This attribute specifies the ETH-Test Ethernet frame size between
        64 bytes and the maximum transmission unit of the EVC. 

        The range of frame sizes from 64 through 2000 octets, in 4 octet 
        increments, MUST be supported, and the range of frame sizes from 2004
        through 9600 octets, in 4 octet increments, SHOULD be supported.  

        The adjustment to the frame size of the standard TST PDU size is 
        accomplished by the addition of a Test TLV.

        This object is only valid for the entity transmitting the ETH-Test 
        frames and is ignored by the entity receiving ETH-Test frames.
       "
    REFERENCE
       "[MEF7.1] 9.3.4.3"
    DEFVAL { 64 }
    ::= { mefSoamTestCfgEntry 10 }

mefSoamTestCfgPattern OBJECT-TYPE
    SYNTAX      MefSoamTcTestPatternType
    MAX-ACCESS  read-create
    STATUS      current
    DESCRIPTION
       "This attribute specifies the type of test pattern to be
        sent or received in an OAM PDU Test TLV.
       " 
    REFERENCE
       "[MEF7.1] 9.3.4.3"
    DEFVAL { null }
    ::= { mefSoamTestCfgEntry 11 }

mefSoamTestCfgStartTimeType OBJECT-TYPE
    SYNTAX      MefSoamTcOperationTimeType
    MAX-ACCESS  read-create
    STATUS      current
    DESCRIPTION
       "This attribute specifies the type of scheduled start date/time to
        perform the on-demand ETH-Test operations. The start time can
        be disabled (none), immediate, relative, or fixed.

        The value of 'none' immediately stops the ETH-Test in process or 
        indicates that the ETH-Test will never begin.

        The value of 'immediate' starts the ETH-Test when the 
        mefSoamTestDurationTime object is written with a value and 
        mefSoamTestOutEnabled is true.

        The value of 'fixed' starts the ETH-Test when the 
        mefSoamTestScheduledStopDateAndTime is written and the start time
        (mefSoamTestScheduledStartDateAndTime) is less than or equal
        to the current system date and time and 
        mefSoamTestOutEnabled is true. 

        The value of 'relative' starts the ETH-Test when the current system date
        and time minus the mefSoamTestRelativeStartTime is greater than or equal
        to the system date and time when the 
        mefSoamTestRelativeStartTime object was written and 
        mefSoamTestOutEnabled is true. If the written value of the 
        mefSoamTestRelativeStartTime object is '0' the ETH-Test starts 
        immediately and the ETH-Test operates as if it was set to the immediate
        mode.
       "
    REFERENCE
       "[SOAM-PM] R2"
    DEFVAL { none }
    ::= { mefSoamTestCfgEntry 12 }

mefSoamTestCfgScheduledStartDateAndTime OBJECT-TYPE
    SYNTAX      DateAndTime
    MAX-ACCESS  read-create
    STATUS      current
    DESCRIPTION
       "This attribute specifies the scheduled start date/time to
        perform the on-demand ETH-Test operations. The default
        value for this attribute is the current system date and
        time, represented by a value of January 1, year 0000, indicating an
        immediate start time.

        This attribute is only valid for a Start Time of 'fixed' and is
        ignored otherwise.
       "
    REFERENCE
       "[MEF7.1] 9.3.4.3"
    DEFVAL { '0000010100000000'H }
   ::= { mefSoamTestCfgEntry 13 }

mefSoamTestCfgScheduledStopDateAndTime OBJECT-TYPE
    SYNTAX      DateAndTime
    MAX-ACCESS  read-create
    STATUS      current
    DESCRIPTION
       "This attribute specifies the scheduled stop date/time to
        perform on-demand ETH-Test operations. The stop date/time
        value must be greater than or equal to the scheduled
        start date/time value.

        The ending time can be specified January 1, year 0000 which represents
        that the ETH-Test does not end until manually terminated.

        This attribute is only valid for a Start Time of 'fixed' and is
        ignored otherwise.
       "
    REFERENCE
       "[MEF7.1] 9.3.4.3"
    DEFVAL { '0000010100000000'H }
    ::= { mefSoamTestCfgEntry 14 }
 
mefSoamTestCfgRelativeStartTime  OBJECT-TYPE
    SYNTAX      TimeInterval
    UNITS       "centi-seconds"
    MAX-ACCESS  read-create
    STATUS      current
    DESCRIPTION
       "This attribute specifies the relative start time, from the
        current system time, to perform on-demand ETH-Test. The
        default value for this attribute is zero, which represents an 
        immediate start time. The units are in 0.01 seconds.

        This attribute is only valid for a Start Time of 'relative' 
        and is ignored otherwise.
       "
    REFERENCE
       "[MEF7.1] 9.3.4.3"
    DEFVAL { 0 }
    ::= { mefSoamTestCfgEntry 15 }

mefSoamTestCfgDurationTime OBJECT-TYPE
    SYNTAX      TimeInterval
    UNITS       "centi-seconds"
    MAX-ACCESS  read-create
    STATUS      current
    DESCRIPTION
       "This attribute specifies the duration of the ETH-Test
        operation. The duration time can be specified as forever
        (represented by a zero value) or as a time duration. The units
        are in 0.01 seconds.

        This attribute is only valid for Start Times of 'immediate' and 
        'relative' and is ignored otherwise.
       "
    REFERENCE
       "[MEF7.1] 9.3.4.3"
   DEFVAL { 0 }
    ::= { mefSoamTestCfgEntry 16 }

mefSoamTestCfgOutStatus OBJECT-TYPE
    SYNTAX      TruthValue
    MAX-ACCESS  read-create
    STATUS      current
    DESCRIPTION
       "A Boolean flag set to true by the MEP ETH-Test Initiator State Machine or a
        SNMP Manager to indicate that another ETH-Test transmission
        operation is active. 

        It is reset to false by the MEP Test Initiator State Machine when an
        ETH-Test operation is complete.
       "
    REFERENCE
       "[Y.1731] 7.7"   
    DEFVAL { false }
    ::= { mefSoamTestCfgEntry 17 }

-- *****************************************************************************
-- Test Stats Table
-- *****************************************************************************

mefSoamTestStatsTable OBJECT-TYPE
    SYNTAX      SEQUENCE OF MefSoamTestStatsEntry
    MAX-ACCESS  not-accessible
    STATUS      current
    DESCRIPTION
       "This table is an extension of the dot1agCfmMepTable and rows
        are automatically added or deleted from this table based upon row
        creation and destruction of the dot1agCfmMepTable.

        This table contains the counter attributes for the
        ETH-Test function. These objects are used to capture
        statistics for both the sending and receiving MEPs.
       "
    ::= { mefSoamTest 2 }

mefSoamTestStatsEntry OBJECT-TYPE
    SYNTAX      MefSoamTestStatsEntry
    MAX-ACCESS  not-accessible
    STATUS      current
    DESCRIPTION
       "The conceptual row of mefSoamTestStatsTable."
    AUGMENTS {
             dot1agCfmMepEntry
             }
    ::= { mefSoamTestStatsTable 1 }

MefSoamTestStatsEntry ::= SEQUENCE {
      mefSoamTestStatsNumIn               Counter64,
      mefSoamTestStatsNumInOutOfOrder     Counter64,
      mefSoamTestStatsNumInCrcErrors      Counter64,
      mefSoamTestStatsNumInBerErrors      Counter64,
      mefSoamTestStatsNumOut              Counter64
    }

mefSoamTestStatsNumIn OBJECT-TYPE
    SYNTAX      Counter64
    MAX-ACCESS  read-only
    STATUS      current
    DESCRIPTION
       "This attribute contains the count of the total number of
        TST frames received. The count is incremented when a
        message is received with or without errors. This attribute
        is only applicable to the MEP receiving ETH-Test messages.

        The initial value of the object when the row is created is zero.
       "
    REFERENCE
       "[MEF7.1] 9.3.4.4"
    ::= { mefSoamTestStatsEntry 1 }

mefSoamTestStatsNumInOutOfOrder OBJECT-TYPE
    SYNTAX      Counter64
    MAX-ACCESS  read-only
    STATUS      current
    DESCRIPTION
       "This attribute contains the count of the total number of
        valid, out-of-order TST frames received. The count is
        incremented when the sequence number in the TST frame
        received does not match the expected sequence number. This
        attribute is only applicable to the MEP receiving ETH-Test
        messages.

        The initial value of the object when the row is created is zero.
       "
    REFERENCE
       "[MEF7.1] 9.3.4.4"
    ::= { mefSoamTestStatsEntry 2 }

mefSoamTestStatsNumInCrcErrors OBJECT-TYPE
    SYNTAX      Counter64
    MAX-ACCESS  read-only
    STATUS      current
    DESCRIPTION
       "This attribute contains the count of the total number of
        TST frames received with CRC errors. This attribute is
        only applicable to the MEP receiving ETH-Test messages that includes 
        the test TLV with a test pattern of nullCrc32 or pbrsCrc32. 

        The CRC is dependent upon the Test TLV only and is independent of BER
        errors, which is used to indicate a pattern error.

        The initial value of the object when the row is created is zero.
       "
    REFERENCE
       "[MEF7.1] 9.3.4.4"
    ::= { mefSoamTestStatsEntry 3 }

mefSoamTestStatsNumInBerErrors OBJECT-TYPE
    SYNTAX      Counter64
    MAX-ACCESS  read-only
    STATUS      current
    DESCRIPTION
       "This attribute contains the count of the total number of
        TST frames received with BER or data errors.  The count is
        incremented when the bit pattern in the received TST
        frames does not match the expected bit pattern. This
        attribute is only applicable to the MEP receiving
        ETH-Test messages.

        The BER error count is independent of the CRC error count and is used
        to indicate a data pattern error, while the CRC error is used to 
        indicate a TLV CRC error.

        The initial value of the object when the row is created is zero.
       "
    REFERENCE
       "[MEF7.1] 9.3.4.4"
    ::= { mefSoamTestStatsEntry 4 }

mefSoamTestStatsNumOut OBJECT-TYPE
    SYNTAX      Counter64
    MAX-ACCESS  read-only
    STATUS      current
    DESCRIPTION
       "This attribute contains the count of the total number of
        TST frames transmitted. This attribute is only applicable
        to the MEP sending ETH-Test messages (i.e., The MEP
        under Test).

        The initial value of the object when the row is created is zero.
       "
    REFERENCE
       "[MEF7.1] 9.3.4.4"
    ::= { mefSoamTestStatsEntry 5 }

-- *****************************************************************************
-- Notification Configuration Objects
-- *****************************************************************************

mefSoamAlarmInterval OBJECT-TYPE
    SYNTAX      Unsigned32 (0..60)
    UNITS       "Seconds"
    MAX-ACCESS  read-write
    STATUS      current
    DESCRIPTION
       "A value indicating the shortest time interval in seconds between the
        generation of the same notification type per MEP to the list of 
        notification destinations. An agent shall generate the first notification
        of given type for a given MEP immediately. An agent shall not generate a
        second specific notification of the same type for the same MEP until the
        time interval has expired. A value of zero indicates that all 
        notifications are sent immediately upon detection of the condition.
       "
    DEFVAL {5}
    ::= { mefSoamFmNotificationCfg 1 }

mefSoamAlarmEnable OBJECT-TYPE

    SYNTAX      BITS {
                     bCfmFaultAlarm(0),
                     bMepDefectAlarm(1),
                     bConfigErrorAssertAlarm(2),
                     bConfigErrorClearAlarm(3),
                     bMepOperStatusAlarm(4), 
                     bLckAlarm(5),
                     bAisAlarm(6)
                }
    MAX-ACCESS  read-write
    STATUS      current
    DESCRIPTION
       "A vector of bits that indicates whether a specific notification is
        enabled. 

        A bit set to '1' enables the specific notification generation. 

        A bit set to '0' disables the specific notification.

        If a particular alarm is not supported the BIT value of the enable/disable
        should be set to '0'.

        bCfmFaultAlarm(0)          enables/disables dot1agCfmFaultAlarm
        bMepDefectAlarm(1)         enables/disables mefSoamMepDefectAlarm
        bConfigErrorAssertAlarm(2) enables/disables mefSoamConfigErrorAssertAlarm
        bConfigErrorClearAlarm(3)  enables/disables mefSoamConfigErrorClearAlarm
        bMepOperStatusAlarm(4)     enables/disables mefSoamMepOperStatusAlarm 
        bLckAlarm(5)               enables/disables mefSoamLckAlarm
        bAisAlarm(6)               enables/disables mefSoamAisAlarm
       "
    DEFVAL { { } }
    ::= { mefSoamFmNotificationCfg 2 }


-- ******************************************************************
-- NOTIFICATIONS (TRAPS)
-- ******************************************************************

mefSoamMepDefectAlarm NOTIFICATION-TYPE
    OBJECTS     { 
                dot1agCfmMepDefects, 
                mefSoamMepStatusLastDefectSentStatus,
                dot1agCfmMepDbRMepState
                }
    STATUS      current
    DESCRIPTION
       "An mefSoamMepDefectAlarm notification is sent when the value of
        dot1agCfmMepDefects changes. It indicates a persistent defect
        in the MEP. This notification is sent whenever the dot1agCfmMepDefects 
        of the MEP changes, regardless of the dot1agCfmMepHighestPrDefect object.

        The inclusion of the dot1agCfmMepDbRMepState object is optional. It
        shall not be included if the defect is not based upon a specific MEP
        instance, e.g.. bDefErrorCCM.

        The management entity that receives the notification can identify
        the system from the network source address of the notification,
        and can identify the individual local MEP reporting the defect by the
        OID indices in the dot1agCfmMepDefects object.

        When included, the dot1agCfmMepDbRMepState object indicates the remote
        MEP that caused the defect by the OID indices in the object.

        An agent should not generate more than one mefSoamMepDefectAlarm
        'notification-event' in a given time interval per MEP as specified by  
        mefSoamAlarmInterval.  A 'notification-event' is the transmission 
        of a single notification to a list of notification destinations.

        If additional defect changes occur within the mefSoamAlarmInterval
        period, then notification generation for these changes shall be 
        suppressed by the agent until the current alarm interval expires.  At 
        the end of an alarm interval period, one notification-event shall be 
        generated if any defect changes occurred since the start of the alarm 
        interval period. In such a case, another alarm interval period is 
        started right away.
       "
    ::= { mefSoamFmNotifications 1 }

mefSoamConfigErrorAssertAlarm NOTIFICATION-TYPE
    OBJECTS     { 
                ieee8021CfmConfigErrorListErrorType 
                }
    STATUS      current
    DESCRIPTION
       "An mefSoamConfigErrorAssertAlarm notification is sent when an entry 
        is added to the ieee8021CfmConfigErrorListTable. It indicates a 
        configuration error during the setup for SOAM FM entity and provides
        a list of Interfaces and VIDs that are incorrectly configured.

        This notification is sent whenever a configuration error occurs.

        The management entity that receives the notification can identify
        the system from the network source address of the notification,
        and can identify the individual configuration reporting the error
        by the indices in the OID ieee8021CfmConfigErrorListErrorType, 
        including the ieee8021CfmConfigErrorListSelectorType,
        ieee8021CfmConfigErrorListSelector, and the 
        ieee8021CfmConfigErrorListIfIndex.

        An agent should not generate more than one mefSoamConfigErrorAssertAlarm
        'notification-event' in a given time interval as specified by  
        mefSoamAlarmInterval.  A 'notification-event' is the transmission of a
        single notification to a list of notification destinations.


        If additional configuration errors occur within the mefSoamAlarmInterval
        period, then notification generation for these changes shall be 
        suppressed by the agent until the current alarm interval expires.  At 
        the end of an alarm interval period, one notification-event shall be 
        generated if any configuration errors occurred since the start of the 
        alarm interval period. In such a case, another alarm interval period is 
        started right away.
       "
    ::= { mefSoamFmNotifications 2 }

mefSoamConfigErrorClearAlarm NOTIFICATION-TYPE
    OBJECTS     { 
                ieee8021CfmConfigErrorListErrorType 
                }
    STATUS      current
    DESCRIPTION
       "An mefSoamConfigErrorClearAlarm notification is sent when an entry is 
        deleted from the ieee8021CfmConfigErrorListTable. It indicates a 
        configuration error has been removed during the setup for SOAM FM 
        entity and provides a list of Interfaces and VIDs that are correctly
        configured.

        This notification is sent whenever a configuration error has been 
        cleared.

        The management entity that receives the notification can identify
        the system from the network source address of the notification,
        and can identify the individual configuration reporting the error
        clear by the indices in the OID ieee8021CfmConfigErrorListErrorType, 
        including the ieee8021CfmConfigErrorListSelectorType,
        ieee8021CfmConfigErrorListSelector, and the 
        ieee8021CfmConfigErrorListIfIndex.

        An agent should not generate more than one mefSoamConfigErrorClearAlarm
        'notification-event' in a given time interval as specified by  
        mefSoamAlarmInterval.  A 'notification-event' is the transmission of a
        single notification to a list of notification destinations.

        If additional configuration error clears occur within the 
        mefSoamAlarmInterval period, then notification generation for these 
        changes shall be suppressed by the agent until the current alarm 
        interval expires. At the end of an alarm interval period, one 
        notification-event shall be generated if any configuration error clears 
        occurred since the start of the alarm interval period. In such a case, 
        another alarm interval period is started right away.
       "
    ::= { mefSoamFmNotifications 3 }

mefSoamMepOperStatusAlarm NOTIFICATION-TYPE
    OBJECTS     { 
                mefSoamMepStatusOperationalState,
                dot1agCfmMepActive
                }
    STATUS      current
    DESCRIPTION
       "An mefSoamMepOperStatusAlarm notification is sent when the value of
        mefSoamMepOperationalState changes. It indicates an operational 
        state change in the MEP. This notification is sent whenever the 
        operational status of the MEP changes.

        The management entity that receives the notification can identify
        the system from the network source address of the notification,
        and can identify the individual MEP reporting the defect by the
        indices in the OID mefSoamMepOperationalState, including the 
        dot1agCfmMdIndex, dot1agCfmMaIndex, and the dot1agCfmMepIdentifier.

        An agent should not generate more than one mefSoamMepOperStatusAlarm
        'notification-event' in a given time interval per MEP as specified by  
        mefSoamAlarmInterval.  A 'notification-event' is the transmission
        of a single notification to a list of notification destinations.

        If additional operational state changes occur within the 
        mefSoamAlarmInterval period, then notification generation for these 
        changes shall be suppressed by the agent until the current alarm 
        interval expires. At the end of an alarm interval period, one 
        notification-event shall be generated if any operational state changes
        occurred since the start of the alarm interval period. In such a case, 
        another alarm interval period is started right away.
       "
    ::= { mefSoamFmNotifications 4 }

mefSoamLckAlarm NOTIFICATION-TYPE
    OBJECTS     { 
                mefSoamLckStatsInStatus,
                mefSoamLckStatsOutStatus
                }
    STATUS      current
    DESCRIPTION
       "An mefSoamLckAlarm notification is sent when the LCK PDU is 
        received or when either mefSoamLckInStatus or mefSoamLckOutStatus
        changes. Reception of the LCK PDU causes the MEP to enter Lock State.
        This notification is sent whenever the operational lock status of the
        MEP changes.

        The management entity that receives the notification can identify
        the system from the network source address of the notification,
        and can identify the individual MEP reporting the defect by the
        indices in the OID mefSoamLckInStatus, including the 
        dot1agCfmMdIndex, dot1agCfmMaIndex, and the dot1agCfmMepIdentifier.

        An agent should not generate more than one mefSoamLckAlarm
        'notification-event' in a given time interval per MEP as specified by  
        mefSoamAlarmInterval.  A 'notification-event' is the transmission
        of a single notification to a list of notification destinations.

        If additional operational state changes occur within the 
        mefSoamAlarmInterval period, then notification generation for these 
        changes shall be suppressed by the agent until the current alarm 
        interval expires. At the end of an alarm interval period, one 
        notification-event shall be generated if any operational state changes
        occurred since the start of the alarm interval period. In such a case, 
        another alarm interval period is started right away.
       "
    ::= { mefSoamFmNotifications 5 }

mefSoamAisAlarm NOTIFICATION-TYPE
    OBJECTS     { 
                mefSoamAisStatsOutStatus,
                mefSoamAisStatsInStatus
                }
    STATUS      current
    DESCRIPTION
       "An mefSoamAisAlarm notification is sent when the state of either 
        mefSoamAisOutStatus or mefSoamAisInStatus changes. mefSoamAisOutStatus
        is set to 'true' when AIS frames are sent by the MEP and set to 
        'false' when the MEP stops sending AIS frames. mefSoamAisInStatus
        is set to 'true' when AIS PDUs are received and is set to 'false'
        when AIS PDUs stop being received.

        The management entity that receives the notification can identify
        the system from the network source address of the notification,
        and can identify the individual MEP reporting the defect by the
        indices in the OID mefSoamAisOutStatus, including the 
        dot1agCfmMdIndex, dot1agCfmMaIndex, and the dot1agCfmMepIdentifier.

        An agent should not generate more than one mefSoamAisAlarm
        'notification-event' in a given time interval per MEP as specified by  
        mefSoamAlarmInterval.  A 'notification-event' is the transmission
        of a single notification to a list of notification destinations.

        If additional operational state changes occur within the 
        mefSoamAlarmInterval period, then notification generation for these 
        changes shall be suppressed by the agent until the current alarm 
        interval expires. At the end of an alarm interval period, one 
        notification-event shall be generated if any operational state changes
        occurred since the start of the alarm interval period. In such a case, 
        another alarm interval period is started right away.
       "
    ::= { mefSoamFmNotifications 6 }


-- ******************************************************************
-- SOAM-FM MIB Module - Conformance Information
-- ******************************************************************

mefSoamFmMibCompliances OBJECT IDENTIFIER ::= { mefSoamFmMibConformance 1 }
mefSoamFmMibGroups      OBJECT IDENTIFIER ::= { mefSoamFmMibConformance 2 }

-- ******************************************************************
-- SOAM-FM Units of conformance
-- ******************************************************************

mefSoamMegGroup OBJECT-GROUP
    OBJECTS {
      mefSoamMegCfgConnectivityStatusInterval,
      mefSoamMegCfgPeerMepInfoAgingTime,
      mefSoamMegCfgPortStatusTlvIncluded,
      mefSoamMegCfgInterfaceStatusTlvIncluded,
      mefSoamNetCfgY1731Compliant,
      mefSoamNetCfgMegIdFormat,
      mefSoamNetCfgMegLevel
    }
    STATUS      current
    DESCRIPTION
       "Mandatory objects for the Service OAM FM MEG group."
    ::= { mefSoamFmMibGroups 1 }

mefSoamMepMandatoryGroup OBJECT-GROUP
    OBJECTS {
      mefSoamMepStatusOperationalState,
      mefSoamMepStatusConnectivityStatus,
      mefSoamMepStatusSentPortStatus,
      mefSoamMepStatusSentInterfaceStatus,
      mefSoamMepStatusLastDefectSentStatus,
      mefSoamMepStatusRdiTransmitStatus
    }
    STATUS      current
    DESCRIPTION
       "Mandatory objects for the Service OAM FM MEP group."
    ::= { mefSoamFmMibGroups 2 }

mefSoamMepOptionalGroup OBJECT-GROUP
    OBJECTS {
      mefSoamMepFmStatsInOamFramesDiscarded,
      mefSoamMepFmStatsInCcmTotal
    }
    STATUS      current
    DESCRIPTION
       "Optional objects for the Service OAM FM MEP group."
    ::= { mefSoamFmMibGroups 3 }

mefSoamCcGroup OBJECT-GROUP
    OBJECTS {
      mefSoamCcCfgDropEligible
    }
    STATUS      current
    DESCRIPTION
       "Optional objects for the Service OAM FM CCM group."
    ::= { mefSoamFmMibGroups 4 }

mefSoamAisGroup OBJECT-GROUP
    OBJECTS {
      mefSoamAisCfgEnabled,
      mefSoamAisCfgInterval,
      mefSoamAisCfgPriority,
      mefSoamAisCfgMdLevel,
      mefSoamAisCfgDropEligible,
      mefSoamAisStatsOutStatus,
      mefSoamAisStatsOutCounter,
      mefSoamAisStatsInStatus,
      mefSoamAisStatsInCounter,
      mefSoamAisStatsInMacAddr
    }
    STATUS      current
    DESCRIPTION
       "Optional objects for the Service OAM FM AIS group."
    ::= { mefSoamFmMibGroups 5 }

mefSoamLbMandatoryGroup OBJECT-GROUP
    OBJECTS {
      mefSoamLbCfgMulticastEnabled,
      mefSoamLbCfgInterval,
      mefSoamLbCfgFrameSize,
      mefSoamLbCfgDataPattern,
      mefSoamLbStatsNumLbrInCrcErrors
    }
    STATUS      current
    DESCRIPTION
       "Mandatory objects for the Service OAM FM LB group."
    ::= { mefSoamFmMibGroups 6 }

mefSoamLbOptionalGroup OBJECT-GROUP
    OBJECTS {
      mefSoamLbCfgTestTlvIncluded,
      mefSoamLbCfgTestTlvPattern,
      mefSoamLbrMulticastReplyMac,
      mefSoamLbCfgTimeout
    }
    STATUS      current
    DESCRIPTION
       "Optional objects for the Service OAM FM LB group."
    ::= { mefSoamFmMibGroups 7 }

mefSoamLtMandatoryGroup OBJECT-GROUP
    OBJECTS {
      mefSoamLtLtmTransmitted,
      mefSoamLtLtrReceived
    }
    STATUS      current
    DESCRIPTION
       "Mandatory objects for the Service OAM FM LT group."
    ::= { mefSoamFmMibGroups 8 }

mefSoamLtOptionalGroup OBJECT-GROUP
    OBJECTS {
      mefSoamLtLtmReceived,
      mefSoamLtLtrTransmitted
      }
    STATUS      current
    DESCRIPTION
       "Optional objects for the Service OAM FM LT group."
    ::= { mefSoamFmMibGroups 9 }

mefSoamLckGroup OBJECT-GROUP
    OBJECTS {
        mefSoamLckCfgAdminState,
        mefSoamLckCfgInterval,
        mefSoamLckCfgPriority,
        mefSoamLckCfgMdLevel,
        mefSoamLckStatsInStatus,
        mefSoamLckStatsInCounter,
        mefSoamLckStatsOutStatus,
        mefSoamLckStatsOutCounter
    }
    STATUS      current
    DESCRIPTION
       "Optional objects for the Service OAM FM LCK group."
    ::= { mefSoamFmMibGroups 10 }

mefSoamTestGroup OBJECT-GROUP
    OBJECTS {
      mefSoamTestCfgOutEnabled,
      mefSoamTestCfgInEnabled,
      mefSoamTestCfgInService,
      mefSoamTestCfgDestMacAddress,
      mefSoamTestCfgDestMepId,
      mefSoamTestCfgDestIsMepId,
      mefSoamTestCfgInterval,
      mefSoamTestCfgPriority,
      mefSoamTestCfgDropEligible,
      mefSoamTestCfgFrameSize,
      mefSoamTestCfgPattern,
      mefSoamTestCfgStartTimeType,
      mefSoamTestCfgScheduledStartDateAndTime,
      mefSoamTestCfgScheduledStopDateAndTime,
      mefSoamTestCfgRelativeStartTime,
      mefSoamTestCfgDurationTime,
      mefSoamTestStatsNumIn,
      mefSoamTestStatsNumInOutOfOrder,
      mefSoamTestStatsNumInCrcErrors,
      mefSoamTestStatsNumInBerErrors,
      mefSoamTestStatsNumOut,
      mefSoamTestCfgOutStatus
    }
    STATUS      current
    DESCRIPTION
       "Optional objects for the Service OAM FM Test group."
    ::= { mefSoamFmMibGroups 11 }

mefSoamFmNotificationsMandatoryGroup NOTIFICATION-GROUP
    NOTIFICATIONS {
      mefSoamMepDefectAlarm,
      mefSoamConfigErrorAssertAlarm,
      mefSoamConfigErrorClearAlarm,
      mefSoamMepOperStatusAlarm
    }
    STATUS      current
    DESCRIPTION
       "Mandatory notifications for the SOAM FM Notifications group."
    ::= { mefSoamFmMibGroups 12 }

mefSoamFmNotificationCfgGroup OBJECT-GROUP
    OBJECTS {
      mefSoamAlarmInterval,
      mefSoamAlarmEnable
    }
    STATUS      current
    DESCRIPTION
       "Optional objects for the SOAM FM Notification Cfg group."
    ::= { mefSoamFmMibGroups 13 }

mefSoamFmNotificationsOptionalGroup NOTIFICATION-GROUP
    NOTIFICATIONS {
      mefSoamLckAlarm,
      mefSoamAisAlarm
    }
    STATUS      current
    DESCRIPTION
       "Optional notifications for the Service OAM FM Notification group."
    ::= { mefSoamFmMibGroups 14 }


-- ******************************************************************
-- SOAM-FM MIB Module Compliance statements
-- ******************************************************************

mefSoamFmMibCompliance MODULE-COMPLIANCE
    STATUS       current
    DESCRIPTION "The compliance statement for the Ethernet Service OAM MIB."
    MODULE
        MANDATORY-GROUPS { 
            mefSoamMegGroup,
            mefSoamMepMandatoryGroup,
            mefSoamLbMandatoryGroup,
            mefSoamLtMandatoryGroup,
            mefSoamFmNotificationsMandatoryGroup
        }

    GROUP mefSoamMepOptionalGroup
    DESCRIPTION "The mefSoamMepOptionalGroup is an optional requirement."

    GROUP mefSoamCcGroup
    DESCRIPTION "The mefSoamCcGroup is an optional requirement."

    GROUP mefSoamAisGroup
    DESCRIPTION "The mefSoamAisGroup is an optional requirement, but when 
                 implemented the whole group is necessary."

    GROUP mefSoamLbOptionalGroup
    DESCRIPTION "The mefSoamLbOptionalGroup is an optional requirement, but when 
                 implemented the whole group is necessary."

    GROUP mefSoamLtOptionalGroup
    DESCRIPTION "The mefSoamLtOptionalGroup is an optional requirement, but when 
                 implemented the whole group is necessary."

    GROUP mefSoamLckGroup
    DESCRIPTION "The mefSoamLckGroup is an optional requirement, but when 
                 implemented the whole group is necessary."

    GROUP mefSoamTestGroup
    DESCRIPTION "The mefSoamTestGroup is an optional requirement, but when 
                 implemented the whole group is necessary."

    GROUP mefSoamFmNotificationCfgGroup
    DESCRIPTION "The mefSoamFmNotificationsCfgGroup is an optional 
                 requirement, but when implemented the whole group is 
                 necessary."

    GROUP mefSoamFmNotificationsOptionalGroup
    DESCRIPTION "The mefSoamFmNotificationsOptionalGroup is an optional 
                 requirement, but when implemented the whole group is 
                 necessary."

    ::= { mefSoamFmMibCompliances 1 }

END
