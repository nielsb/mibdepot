BanwidthControl-MIB DEFINITIONS ::= BEGIN

        IMPORTS
                enterprises,
                OBJECT-TYPE,
                Counter
                        FROM RFC1155-SMI
                internetServer
                        FROM InternetServer-MIB;

--      microsoft        OBJECT IDENTIFIER ::= { enterprises 311 }
--      software         OBJECT IDENTIFIER ::= { microsoft 1 }
--      internetServer   OBJECT IDENTIFIER ::= { software 7 }
        bandwidthControl OBJECT IDENTIFIER ::= { internetServer 15 }
        bwcStatistics    OBJECT IDENTIFIER ::= { bandwidthControl 1 }


        BwcDisplayData ::= OCTET STRING (SIZE (512))


-- Bandwidth Control Statistics
	BwcPerf OBJECT-TYPE
		SYNTAX	BwcDisplayData
		ACCESS	read-only
		STATUS	mandatory
		DESCRIPTION 
			"Displays:  Name, Assign Int value, Actual Int value, Assing Ext value, Actual Ext value."
		::= { bwcStatistics 1 }
END
