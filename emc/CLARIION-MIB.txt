CLARIION-MIB DEFINITIONS ::= BEGIN 
IMPORTS
   OBJECT-TYPE, DisplayString
   FROM RFC1213-MIB;

   internet                                  OBJECT IDENTIFIER ::= { iso(1) org(3) dod(6) 1 }
   enterprises                               OBJECT IDENTIFIER ::= { internet private(4) 1 }
   clariion                                  OBJECT IDENTIFIER ::= { enterprises 1981 }
   clarInfo                                  OBJECT IDENTIFIER ::= { clariion 1}
   EventMonitor                              OBJECT IDENTIFIER ::= { clarInfo 4}

   deviceType OBJECT-TYPE
            SYNTAX  DisplayString
            ACCESS  read-only
            STATUS  mandatory
            DESCRIPTION
            "A textual description of this device.
            Description for all current devices is 'CLARiiON Storage System'."
            ::= { clarInfo 1 }


    hostName OBJECT-TYPE
            SYNTAX  DisplayString
            ACCESS  read-only
            STATUS  mandatory
            DESCRIPTION
                        "Clariion Host Name."
            ::= { EventMonitor 3 }

    deviceID OBJECT-TYPE
            SYNTAX  DisplayString
            ACCESS  read-only
            STATUS  mandatory
            DESCRIPTION
                        "Clariion Device ID."
            ::= { EventMonitor 4 }

    eventID OBJECT-TYPE
            SYNTAX  DisplayString
            ACCESS  read-only
            STATUS  mandatory
            DESCRIPTION
                        "Event ID."
            ::= { EventMonitor 5 }

    eventText OBJECT-TYPE
            SYNTAX  DisplayString
            ACCESS  read-only
            STATUS  mandatory
            DESCRIPTION
                        "Event description."
            ::= { EventMonitor 6 }

    storageSystem OBJECT-TYPE
            SYNTAX  DisplayString
            ACCESS  read-only
            STATUS  mandatory
            DESCRIPTION
                        "Storage System Name."
            ::= { EventMonitor 7 }

   EventMonitorTrap TRAP-TYPE
              ENTERPRISE  clariion 
              VARIABLES   { hostName, deviceID, 
                            eventID, eventText,
                            storageSystem }
              DESCRIPTION
                          "An EventMonitorTrap is generated in
                          response to a user-specified event.
                          Details can be found in Variables data."
              ::= 2

   EventMonitorTrapInfo TRAP-TYPE
              ENTERPRISE   clariion
              VARIABLES   { hostName, deviceID, 
                            eventID, eventText,
                            storageSystem }
              DESCRIPTION
                          "An Informational EventMonitorTrap is generated in
                          response to a user-specified event.
                          Details can be found in Variables data."
              ::= 3

   EventMonitorTrapWarn TRAP-TYPE
              ENTERPRISE   clariion
              VARIABLES   { hostName, deviceID, 
                            eventID, eventText,
                            storageSystem }
              DESCRIPTION
                          "A Warning EventMonitorTrap is generated in
                          response to a user-specified event.
                          Details can be found in Variables data."
              ::= 4

   EventMonitorTrapError TRAP-TYPE
              ENTERPRISE   clariion
              VARIABLES   { hostName, deviceID, 
                            eventID, eventText,
                            storageSystem }
              DESCRIPTION
                          "An Error EventMonitorTrap is generated in
                          response to a user-specified event.
                          Details can be found in Variables data."
              ::= 5

   EventMonitorTrapFault TRAP-TYPE
              ENTERPRISE   clariion
              VARIABLES   { hostName, deviceID, 
                            eventID, eventText,
                            storageSystem }
              DESCRIPTION
                          "A Fault EventMonitorTrap is generated in
                          response to a user-specified event.
                          Details can be found in Variables data."
              ::= 6

END
