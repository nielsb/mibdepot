DOCS-PNM-MIB DEFINITIONS ::= BEGIN

IMPORTS
    MODULE-IDENTITY,
    OBJECT-TYPE,
    Integer32,
    Unsigned32,
    Counter32
             FROM SNMPv2-SMI         -- RFC 2578
    TEXTUAL-CONVENTION,
    TruthValue,
    MacAddress,
    RowStatus,
    DateAndTime,
    TimeStamp
             FROM SNMPv2-TC          -- RFC 2579
    OBJECT-GROUP,
    MODULE-COMPLIANCE
             FROM SNMPv2-CONF        -- RFC 2580
    SnmpAdminString
             FROM SNMP-FRAMEWORK-MIB -- RFC 3411
    ifIndex,
    InterfaceIndex,
    InterfaceIndexOrZero
             FROM IF-MIB             -- RFC 2863
    Uri
             FROM URI-TC-MIB         -- RFC 1517
    InetAddressType,
    InetAddress
             FROM INET-ADDRESS-MIB   -- RFC 4001
    TenthdB
             FROM DOCS-IF-MIB        -- RFC 4546
    DsOfdmModulationType,
    HundredthdB
             FROM DOCS-IF31-MIB
    docsIf3CmSpectrumAnalysisCtrlCmd
             FROM DOCS-IF3-MIB
    clabProjDocsis
             FROM CLAB-DEF-MIB;


docsPnmMIB MODULE-IDENTITY
    LAST-UPDATED    "202306010000Z" -- June 1, 2023
    ORGANIZATION    "Cable Television Laboratories, Inc."
    CONTACT-INFO
       "Postal: Cable Television Laboratories, Inc.
        858 Coal Creek Circle
        Louisville, Colorado 80027-9750
        U.S.A.
        Phone: +1 303-661-9100
        Fax:   +1 303-661-9199
        E-mail: mibs@cablelabs.com"
    DESCRIPTION
       "This MIB module contains management objects for the
        management of DOCSIS 3.1 Proactive Network Maintenance.
        Copyright 2015-2023 Cable Television Laboratories, Inc.
        All rights reserved."

    REVISION    "202306010000Z" -- June 1, 2023
    DESCRIPTION
        "Revised Version includes ECN DOCS-PNM-MIB-N-23.2308-1."
    REVISION    "202302020000Z" -- February 2, 2023
    DESCRIPTION
        "Revised Version includes ECN DOCS-PNM-MIB-N-23.2298-1."
    REVISION    "202209290000Z" -- September 29, 2022
    DESCRIPTION
        "Revised Version includes ECN DOCS-PNM-MIB-N-22.2283-1."
    REVISION    "202203310000Z" -- March 31, 2022
    DESCRIPTION
        "Revised Version includes ECN DOCS-PNM-MIB-N-22.2244-1."
    REVISION    "202112160000Z" -- December 16, 2021
    DESCRIPTION
        "Revised Version includes ECN DOCS-PNM-MIB-N-21.2214-1."
    REVISION    "202106170000Z" -- June 17, 2021
    DESCRIPTION
        "Revised Version includes ECN DOCS-PNM-MIB-N-21.2170-2."
    REVISION    "202102040000Z" -- February 4, 2021
    DESCRIPTION
        "Revised Version includes ECN DOCS-PNM-MIB-N-21.2147-1."
    REVISION    "202011050000Z" -- November 5, 2020
    DESCRIPTION
        "Revised Version includes ECN DOCS-PNM-MIB-N-20.2125-2."
    REVISION    "201912120000Z" -- December 12, 2019
    DESCRIPTION
        "Revised Version includes ECN
         DOCS-PNM-MIB-N-19.2063-1."
    REVISION    "201909050000Z" -- September 5, 2019
    DESCRIPTION
        "Revised Version includes ECN
         DOCS-PNM-MIB-N-19.2046-1."
    REVISION    "201905160000Z" -- May 16, 2019
    DESCRIPTION
        "Revised Version includes ECN
         DOCS-PNM-MIB-N-19.2019-1."
    REVISION    "201902070000Z" -- February 7, 2019
    DESCRIPTION
        "Revised Version includes ECN
         DOCS-PNM-MIB-N-18.1990-3."
    REVISION "201811150000Z" -- November 15, 2018
    DESCRIPTION
        "Revised version includes ECN
         ECN DOCS-PNM-MIB-N-18.1970-3."
    REVISION "201808300000Z" -- August 30, 2018
    DESCRIPTION
        "Revised version includes ECN
         DOCS-PNM-MIB-N-18.1946-1."
    REVISION "201803220000Z" -- March 22, 2018
    DESCRIPTION
        "Revised version includes ECN
         DOCS-PNM-MIB-N-17.1856-3."
    REVISION "201708100000Z" -- August 10, 2017
    DESCRIPTION
        "Revised version includes ECN
         DOCS-PNM-MIB-N-17.1756-2"
    REVISION "201704130000Z" -- April 13, 2017
    DESCRIPTION
        "Revised Version includes ECN
         DOCS-PNM-MIB-N-17.1694-5"
    REVISION "201612150000Z" -- December 15, 2016
    DESCRIPTION
        "Revised Version includes ECN
         DOCS-PNM-MIB-N-16.1623-4"
    REVISION "201609010000Z" -- September 1, 2016
    DESCRIPTION
        "Revised Version includes ECN
         DOCS-PNM-MIB-N-16.1588-1"
    REVISION "201605050000Z" -- May 5, 2016
    DESCRIPTION
        "Revised Version includes ECN
         CCAP-OSSIv3.1-N-16.1489-3"
    REVISION "201511040000Z" -- November 4, 2015
    DESCRIPTION
       "Updated per CM-OSSIv3.1-N-1386-1, which rolls up changes from the following ECNs;
        CCAP-OSSIv3.1-N-15.1343-2: Update default file names for PNM test generated
        files to replace use of CCAP MAC Address(not unique), with any unique CCAP
        identifier. Also added requirement to insert a row in PNM tables for each
        ifIndex.
        CM-OSSIv3.1-N-15.1351-2: Add Capture Time, CM MAC Address to all file headers
        CM-OSSIv3.1-N-15.1365-1: Clarify fixed point usage for complexData Type."
    REVISION "201505200000Z" -- May 20, 2015
    DESCRIPTION
       "Updates per ECN CM-OSSIv3.1-N-15.1310-2 to synchronize with
        CM-SP-CM-OSSIv3.1-I04 and
        CM-SP-CCAP-OSSIv3.1-I04"
    REVISION "201504210000Z" -- April 21, 2015
    DESCRIPTION
       "Initial version, per ECN CM-OSSIv3.1-N-14.1221-6."
    ::= {  clabProjDocsis 27 }

-- ---------------------------------------------------------------------
-- Textual Conventions
-- ---------------------------------------------------------------------
MeasStatusType ::= TEXTUAL-CONVENTION
    STATUS      current
    DESCRIPTION
       "This data type is used to determine the state of a measurement.
       The enumerated values associated with MeasStatusType are:
        'other'
           Indicates any state not described below.
       'inactive'
           Indicates that a test is not started or in progress.
       'busy'
           Indicates that a test has been started and is in progress.
       'sampleReady'
           Indicates that a test has completed and that the measurement
           data is ready.
       'error'
           Indicates that there was an error starting or during the test and
           any test data, if available, may not be valid.
       'resourceUnavailable'
           Indicates that the test could not be started due to lack of test
           platform resources.
       'sampleTruncated'
           Indicates that the size of the requested data exceeded file size
           supported.
       'interfaceModification'
           Indicates that the interface numbering is changed due to DBC message
           or when Primary backup is changed.
        "
    REFERENCE
        "DOCSIS 3.1 Cable Modem Operations Support System Interface
        Specification CM-SP-CM-OSSIv3.1, PNM section."
    SYNTAX      INTEGER {other(1),
                         inactive(2),
                         busy(3),
                         sampleReady(4),
                         error(5),
                         resourceUnavailable(6),
                         sampleTruncated(7),
                         interfaceModification(8)
                        }

ThousandthdB ::= TEXTUAL-CONVENTION
     DISPLAY-HINT "d-3"
     STATUS       current
     DESCRIPTION
         "This data type represents power levels that are normally
          expressed in dB.  Units are in thousands of a dB;
          for example, 5.175 dB will be represented as 5175."
     SYNTAX       Integer32

UsOfdmaWindowingSizeType ::= TEXTUAL-CONVENTION
    DISPLAY-HINT "d"
    STATUS      current
    DESCRIPTION
       "This data type is defined to specify the eight possible values for the
       upstream windowing roll-off period samples. The Roll-Off Period Samples
       (NRP) are given in number of samples using the sample rate of 102.4
       Msamples/s. Reference: PHYv3.1] Table 7-5 - Roll-Off Period (RP) Values "
    REFERENCE
        "DOCSIS 3.1 Cable Modem Operations Support System Interface
        Specification CM-SP-CM-OSSIv3.1, PNM section."
    SYNTAX      Unsigned32 (0 | 32 | 64 | 96 | 128 | 160 | 192 | 224)




-- Administrative assignments
docsPnmNotifications   OBJECT IDENTIFIER ::= { docsPnmMIB 0 }
docsPnmMibObjects      OBJECT IDENTIFIER ::= { docsPnmMIB 1 }
docsPnmMibConformance  OBJECT IDENTIFIER ::= { docsPnmMIB 2 }

docsPnmMibCompliances  OBJECT IDENTIFIER ::= { docsPnmMibConformance 1 }
docsPnmMibGroups       OBJECT IDENTIFIER ::= { docsPnmMibConformance 2 }

-- No Notifications are defined for this MIB

docsPnmBulkData         OBJECT IDENTIFIER ::= { docsPnmMibObjects 1 }
docsPnmCmObjects        OBJECT IDENTIFIER ::= { docsPnmMibObjects 2 }
docsPnmCmtsObjects      OBJECT IDENTIFIER ::= { docsPnmMibObjects 3 }
docsLatencyObjects      OBJECT IDENTIFIER ::= { docsPnmMibObjects 4 }

docsPnmBulkCtl          OBJECT IDENTIFIER ::= { docsPnmBulkData 1 }
docsPnmCmtsOptObjects   OBJECT IDENTIFIER ::= { docsPnmCmtsObjects 9 }
docsPnmCmtsUtscObjects  OBJECT IDENTIFIER ::= { docsPnmCmtsObjects 10 }


-- ---------------------------------------------------------------------
-- PNM Bulk Data Objects
-- ---------------------------------------------------------------------
-- ---------------------------------------------------------------------
-- The CM Bulk Data Control objects
-- ---------------------------------------------------------------------

docsPnmBulkDestIpAddrType  OBJECT-TYPE
   SYNTAX      InetAddressType
   MAX-ACCESS  read-write
   STATUS      current
   DESCRIPTION
      "This object represents the IP address type of the 'docsPnmBulkDestIpAddr'
      object. This value is of type InetAddressType which is defined by RFC4001.

      Allowed values for this object are: 'unknown', 'ipv4', 'ipv6'.

      A successful connection depends on the value of this attribute being set
      to an IP Family supported by the device. For example, if this value is set
      to IPv6 and the device is operating in an IPv4-only mode, a successful
      upload will not be possible. In this case the 'docsPnmBulkFileUploadStatus'
      object would reflect the error. The CM must NOT allow the value of
      docsPnmBulkDestIpAddrType to change if the value of PnmCmCtlStatus is any
      value other than 'ready'. "
   DEFVAL { unknown }
   ::= { docsPnmBulkCtl 1 }

docsPnmBulkDestIpAddr  OBJECT-TYPE
   SYNTAX      InetAddress
   MAX-ACCESS  read-write
   STATUS      current
   DESCRIPTION
      "This object represents the IP address of the server to which the
      bulk data file is to be sent. This attribute is further defined by
      the 'docsPnmBulkDestIpAddrType' object. The CM must NOT allow the
      value of docsPnmBulkDestIpAddr to change if the value of PnmCmCtlStatus
      is any value other than 'ready'.  "
   REFERENCE
      "DOCSIS 3.1 Cable Modem Operations Support System Interface
      Specification CM-SP-CM-OSSIv3.1, Bulk Data section. "
   DEFVAL { "" }
   ::= { docsPnmBulkCtl 2 }

docsPnmBulkDestPath  OBJECT-TYPE
   SYNTAX      SnmpAdminString
   MAX-ACCESS  read-write
   STATUS      current
   DESCRIPTION
      "This object represents the path, excluding the filename, at the server
      to which the captured data file is to be sent. The CM must NOT allow the
      value of docsPnmBulkDestPath to change if the value of PnmCmCtlStatus
      is any value other than 'ready'. By default, the value of this object is
      an empty string. If used, this value must include all expected delimiters.
      The following examples, are valid values:
                   /Directory1/directory2/
                   /pnm/
      "
   REFERENCE
      "DOCSIS 3.1 Cable Modem Operations Support System Interface
       Specification CM-SP-CM-OSSIv3.1, Bulk Data section. "
   DEFVAL { "" }
   ::= { docsPnmBulkCtl 3 }

docsPnmBulkUploadControl  OBJECT-TYPE
   SYNTAX      INTEGER {other(1),
                        noAutoUpload(2),
                        autoUpload(3)
                       }
   MAX-ACCESS  read-write
   STATUS      current
   DESCRIPTION
      " This attribute controls the action taken by the device when a new bulk
      data file is generated. The possible values are defined below.

          noAutoUpload - Bulk Data files are not automatically uploaded by the
          device. All bulk data files are available to be uploaded, on demand,
          by manipulating the FileControl attribute in the BulkDataFile object
          for that file's row instance.

          autoUpload - When this option is selected, the device must
          automatically uploaded bulk data files as they become available. A
          file becomes available when a file-generation application completes
          the file and creates a row in the BulkDataFileTable. If this value is
          set, the bulk data file is automatically uploaded to the parameters
          defined by the DestIpAddr, DestIpAddrType, and DestPath. If the upload
          fails or additional uploads are desired, the file can be re-uploaded
          by manipulating the FileControl attribute in the BulkDataFile object
          for that file's row instance. "
   DEFVAL { autoUpload }
   ::= { docsPnmBulkCtl 4 }
-- ---------------------------------------------------------------------
-- The CCAP Bulk Data Control Table
-- ---------------------------------------------------------------------

docsPnmCcapBulkDataControlTable OBJECT-TYPE
     SYNTAX      SEQUENCE OF DocsPnmCcapBulkDataControlEntry
     MAX-ACCESS  not-accessible
     STATUS      deprecated
     DESCRIPTION
        "This table provides the configuration attributes needed
         for the device to upload Bulk Data files to a Server. "
     REFERENCE
         "Information Model Mapping: CM-SP-CCAP-OSSI 
          BulkDataServerCtrl"
     ::= { docsPnmBulkCtl 5}

docsPnmCcapBulkDataControlEntry OBJECT-TYPE
     SYNTAX      DocsPnmCcapBulkDataControlEntry
     MAX-ACCESS  not-accessible
     STATUS      deprecated
     DESCRIPTION
         "The conceptual row of the 'docsPnmCcapBulkDataControlTable'. "
     INDEX { docsPnmCcapBulkDataControlServerIndex }
     ::= { docsPnmCcapBulkDataControlTable 1 }

DocsPnmCcapBulkDataControlEntry ::=
    SEQUENCE {
        docsPnmCcapBulkDataControlServerIndex         Unsigned32,
        docsPnmCcapBulkDataControlDestIpAddrType      InetAddressType,
        docsPnmCcapBulkDataControlDestIpAddr          InetAddress,
        docsPnmCcapBulkDataControlDestPath            SnmpAdminString,
        docsPnmCcapBulkDataControlUploadControl       INTEGER,
        docsPnmCcapBulkDataControlPnmTestSelector     BITS
     }

docsPnmCcapBulkDataControlServerIndex OBJECT-TYPE
     SYNTAX      Unsigned32 (1..10)
     MAX-ACCESS  not-accessible
     STATUS      deprecated
     DESCRIPTION
        "This attribute is the index for the table. "
     REFERENCE
          "Information Model Mapping: CM-SP-CCAP-OSSI
           BulkDataServerCtrl::ServerIndex"
     ::= { docsPnmCcapBulkDataControlEntry 1 }

docsPnmCcapBulkDataControlDestIpAddrType  OBJECT-TYPE
   SYNTAX      InetAddressType
   MAX-ACCESS  read-write
   STATUS      deprecated
   DESCRIPTION
      "This attribute represents the IP address type of the
       'docsPnmCcapBulkDataControlDestIpAddr'attribute.
       This value is of type InetAddressType which is defined by RFC4001.
       Allowed values for this object are: 'unknown', 'ipv4', 'ipv6'.

      A successful connection depends on the value of this attribute being set
      to an IP Family supported by the device. For example, if this value is set
      to IPv6 and the device is operating in an IPv4-only mode, a successful
      upload will not be possible. In this case the 'docsPnmBulkFileUploadStatus'
      object would reflect the error. "
   REFERENCE
     "Information Model Mapping: CM-SP-CCAP-OSSI 
      BulkDataServerCtrl::DestIpAddrType"
   DEFVAL { unknown }
   ::= { docsPnmCcapBulkDataControlEntry 2 }

docsPnmCcapBulkDataControlDestIpAddr  OBJECT-TYPE
   SYNTAX      InetAddress
   MAX-ACCESS  read-write
   STATUS      deprecated
   DESCRIPTION
      "This attribute represents the IP address of the PNM server
       to which the bulk data file is to be sent. This attribute is
       further defined by the docsPnmCcapBulkDataControlDestIpAddrType
       attribute."
   REFERENCE
      "Information Model Mapping: CM-SP-CCAP-OSSI 
       BulkDataServerCtrl::DestIpAddr"
   DEFVAL { "" }
   ::= { docsPnmCcapBulkDataControlEntry 3 }

docsPnmCcapBulkDataControlDestPath  OBJECT-TYPE
   SYNTAX      SnmpAdminString
   MAX-ACCESS  read-write
   STATUS      deprecated
   DESCRIPTION
      "This attribute represents the path, excluding the filename, at the PNM server
      to which the captured data file is to be sent. By default, the value of this
      attribute is an empty string. If used, this value must include all expected delimiters.
      The following examples, are valid values:
                   /Directory1/directory2/
                   /pnm/
      "
   REFERENCE
      "Information Model Mapping: CM-SP-CCAP-OSSI 
       BulkDataServerCtrl::DestPath"
   DEFVAL { "" }
   ::= { docsPnmCcapBulkDataControlEntry 4 }

docsPnmCcapBulkDataControlUploadControl  OBJECT-TYPE
   SYNTAX      INTEGER {other(1),
                        noAutoUpload(2),
                        autoUpload(3)
                       }
   MAX-ACCESS  read-write
   STATUS      deprecated
   DESCRIPTION
      "This attribute controls the action taken by the device when a new bulk
       data file is generated. The possible values are defined below.

          noAutoUpload - Bulk Data files are not automatically uploaded by the
          device. All bulk data files are available to be uploaded, on demand,
          by manipulating the FileControl attribute in the BulkDataFile table
          for that file's row instance.

          autoUpload - When this option is selected, the device must
          automatically uploaded bulk data files as they become available. A
          file becomes available when a file-generation application completes
          the file and creates a row in the BulkDataFileTable. If this value is
          set, the bulk data file is automatically uploaded to the parameters
          defined by the DestIpAddr, DestIpAddrType, and DestPath. If the upload
          fails or additional uploads are desired, the file can be re-uploaded
          by manipulating the FileControl attribute in the BulkDataFile object
          for that file's row instance. "
   REFERENCE
       "Information Model Mapping: CM-SP-CCAP-OSSI 
        BulkDataServerCtrl::UploadControl"
   DEFVAL { autoUpload }
   ::= { docsPnmCcapBulkDataControlEntry 5 }

docsPnmCcapBulkDataControlPnmTestSelector OBJECT-TYPE
     SYNTAX      BITS {
                       other(0),
                       dsOfdmSymbolCapture (1),
                       dsOfdmNoisePowerRatio(2),
                       cmtsUsOfdmaActiveAndQuietProbe(3),
                       usImpulseNoise(4),
                       usOfdmaRxMerPerSubcarrier(5),
                       upstreamHistogram(6),
                       usOfdmaRxPower(7),
                       usTriggeredSpectrumCapture(8)   
                        }
     MAX-ACCESS  read-write
     STATUS      deprecated
     DESCRIPTION
        "This attribute permits to associate a group of PNM tests
         to the selected PNM server. The CCAP should reject configuration
         that associates more than one PNM server to the same PNM test."
     REFERENCE
       "Information Model Mapping: CM-SP-CCAP-OSSI 
        BulkDataServerCtrl::PnmTestSelector"
     ::= { docsPnmCcapBulkDataControlEntry 6 }

-- ---------------------------------------------------------------------
-- The CM BulkDataFile Table
-- ---------------------------------------------------------------------
docsPnmBulkFileTable OBJECT-TYPE
     SYNTAX      SEQUENCE OF DocsPnmBulkFileEntry
     MAX-ACCESS  not-accessible
     STATUS      current
     DESCRIPTION
        "This table provides the objects needed for the device to upload
        a bulk data file to the Server. This object is a table with a row for
        each file that is available in the device for upload. The parameters
        used for the upload are provided under the 'docsPnmBulkCtl' object. "
      REFERENCE
         "Information Model Mapping: CM-SP-CM-OSSI 
          BulkDataFileCtrl"
     ::= { docsPnmBulkData 2}

docsPnmBulkFileEntry OBJECT-TYPE
     SYNTAX      DocsPnmBulkFileEntry
     MAX-ACCESS  not-accessible
     STATUS      current
     DESCRIPTION
         "The conceptual row of the 'docsPnmBulkFileTable'. An instance
         is dynamically created and exists for each file that is available
         for upload.

         The device must create a row for each file that is available for
         upload. The device could have have limited resources to save captured
         data files. Therefore, if the number of files exceeds the minimum
         supported number of files requirements for the device, newly created
         rows can overwrite/replace existing rows as new data files become
         available. If a bulk data file is no longer available for upload, the
         device must remove that file's details from the BulkDataFile table.

         The conceptual rows do not persist across device resets."
     INDEX { docsPnmBulkFileIndex }
     ::= { docsPnmBulkFileTable 1 }

DocsPnmBulkFileEntry ::=
    SEQUENCE {
        docsPnmBulkFileIndex         Unsigned32,
        docsPnmBulkFileName          SnmpAdminString,
        docsPnmBulkFileControl       INTEGER,
        docsPnmBulkFileUploadStatus  INTEGER
     }

docsPnmBulkFileIndex OBJECT-TYPE
     SYNTAX      Unsigned32 (1..255)
     MAX-ACCESS  not-accessible
     STATUS      current
     DESCRIPTION
        "This object is the index for the table."
     REFERENCE
         "Information Model Mapping: CM-SP-CM-OSSI 
          CmBulkDataFile::FileIndex"
     ::= { docsPnmBulkFileEntry 1 }

docsPnmBulkFileName OBJECT-TYPE
     SYNTAX      SnmpAdminString
     MAX-ACCESS  read-only
     STATUS      current
     DESCRIPTION
        "This object contains the name of the bulk data file stored in the
        device, that is available to be uploaded to the server. Filenames
        are defined by the application that creates them. "
     REFERENCE
         "Information Model Mapping:   CM-SP-CM-OSSI    
          CmBulkDataFile::FileName"
     ::= { docsPnmBulkFileEntry 2 }

docsPnmBulkFileControl OBJECT-TYPE
     SYNTAX      INTEGER {other(1),
                          tftpUpload(2),
                          cancelUpload(3),
                          deleteFile(4)
                         }
     MAX-ACCESS  read-write
     STATUS      current
     DESCRIPTION
        "This object controls the action taken by the device regarding the
        file specified by the 'docsPnmBulkFileName' object. When a value is
        written to this object for a given row instance, the device is
        required to take that action on the specified bulk data file. The
        possible actions are:

             other(1) - This value is returned when the object is read.
             This value is not writeable.

             tftpUpload(2)
                The device must initiate a TFTP-Write to the server with
                the parameters specified in the 'docsPnmBulkDestIpAddr',
                'docsPnmBulkDestIpAddrType', and 'docsPnmBulkDestPath' objects.
                This action will change the value of the
                'docsPnmBulkFileUploadStatus' to 'uploadInProgress' while the
                transfer is ongoing. This object can only be set to 'tftpUpload'
                when the value of the 'docsPnmBulkFileUploadStatus' object is not
                set to a value of 'uploadInProgress' for this row OR for any row
                in the table. This limits the upload process to one upload at a
                time. This object will return 'inconsistentValue' for this case.

             cancelUpload(3)
                The device must cancel a pending upload or an upload currently in
                progress on this bulk data file. The value of
                'docsPnmBulkFileUploadStatus' will be changed to 'uploadCancelled'.

             deleteFile(4)
                The device must delete the file from its memory and from this table.
                This object can not be set to 'deleteFile' while an upload is in progress.
             "
     REFERENCE
         "Information Model Mapping:   CM-SP-CM-OSSI    
          CmBulkDataFile::FileControl"
     DEFVAL { other }
     ::= { docsPnmBulkFileEntry 3 }

docsPnmBulkFileUploadStatus  OBJECT-TYPE
   SYNTAX      INTEGER {other(1),
                        availableForUpload(2),
                        uploadInProgress(3),
                        uploadCompleted(4),
                        uploadPending(5),
                        uploadCancelled(6),
                        error(7)
                       }
   MAX-ACCESS  read-only
   STATUS      current
   DESCRIPTION
      "This attribute reflects the status of the bulk data file. The possible
       values are listed below.

        other(1) - Any condition not covered by the other defined values.

        availableForUpload(2) - The file is available to be uploaded.

        uploadInProgress(3) - The file is currently being uploaded.

        uploadCompleted(4) - The file was successfully uploaded.

        uploadPending(5) - The file has been selected for upload but a
            condition does not allow the upload to take place. The upload will
            start when the condition blocking uploads has been removed. For
            example, another upload that is currently in progress could cause
            this value to be returned.

        uploadCancelled(6) - An upload was cancelled before it completed.

        error(7) - An error occurred and the file was not successfully uploaded. "
   REFERENCE
         "Information Model Mapping:   CM-SP-CM-OSSI    
          CmBulkDataFile::FileUploadStatus"
   ::= { docsPnmBulkFileEntry 4 }
   
-- ---------------------------------------------------------------------
-- PNM CCAP Bulk File Transfer Objects
-- ---------------------------------------------------------------------

docsPnmBulkFileTransfer OBJECT IDENTIFIER ::= { docsPnmBulkData 3 }

-- ---------------------------------------------------------------------
-- PNM CCAP Bulk Data Transfer Configuration Table
-- ---------------------------------------------------------------------

docsPnmBulkDataTransferCfgTable OBJECT-TYPE
     SYNTAX      SEQUENCE OF DocsPnmBulkDataTransferCfgEntry
     MAX-ACCESS  not-accessible
     STATUS      current
     DESCRIPTION
        "This table defines the configuration of destinations for Telemetry data, 
         such as PNM test result measurements.
         The CCAP MUST support creation and deletion of multiple rows
         in this table.
         Support for HTTP and /HTTPS is optional for DOCSIS 4.0. 
         If HTTP or HTTPS is not supported, the CCAP MUST return 'inconsistent value' 
         when an SNMP Manager attempts to set the configuration for the attribute Protocol
         to 'http' or 'https'."
      REFERENCE
         "Information Model Mapping: CM-SP-CCAP-OSSI    
          DataTransferCfg"
     ::= { docsPnmBulkFileTransfer 1}

docsPnmBulkDataTransferCfgEntry OBJECT-TYPE
     SYNTAX      DocsPnmBulkDataTransferCfgEntry
     MAX-ACCESS  not-accessible
     STATUS      current
     DESCRIPTION
         "The conceptual row of the 'docsPnmBulkDataTransferCfgTable'. 
          An instance is created and exists for each destination where PNM test 
          result measurements are to be stored."
     INDEX { docsPnmBulkDataTransferCfgDestIndex }
     ::= { docsPnmBulkDataTransferCfgTable 1 }

DocsPnmBulkDataTransferCfgEntry ::=
    SEQUENCE {
        docsPnmBulkDataTransferCfgDestIndex          Unsigned32,
        docsPnmBulkDataTransferCfgDestHostname       SnmpAdminString,
        docsPnmBulkDataTransferCfgDestHostIpAddrType InetAddressType,
        docsPnmBulkDataTransferCfgDestHostIpAddress  InetAddress,
        docsPnmBulkDataTransferCfgDestPort           Unsigned32,
        docsPnmBulkDataTransferCfgDestBaseUri        Uri,
        docsPnmBulkDataTransferCfgProtocol           INTEGER,
        docsPnmBulkDataTransferCfgLocalStore         TruthValue,
        docsPnmBulkDataTransferCfgRowStatus          RowStatus
     }

docsPnmBulkDataTransferCfgDestIndex OBJECT-TYPE
     SYNTAX      Unsigned32 
     MAX-ACCESS  not-accessible
     STATUS      current
     DESCRIPTION
        "This key uniquely identifies a destination for 
         PNM test result measurements."
     REFERENCE
         "Information Model Mapping: CM-SP-CCAP-OSSI    
          DataTransferCfg::DestinationIndex"
     ::= { docsPnmBulkDataTransferCfgEntry 1 }

docsPnmBulkDataTransferCfgDestHostname OBJECT-TYPE
     SYNTAX      SnmpAdminString
     MAX-ACCESS  read-create
     STATUS      current
     DESCRIPTION
        "A fully-qualified domain name (FQDN) of the destination host.
         If the user configures Hostname, they need not configure IpAddrType
         and IpAddress. If all three are configured, the IpAddrType and IpAddress
         will be used and Hostname will be ignored."
     REFERENCE
         "Information Model Mapping: CM-SP-CCAP-OSSI    
          DataTransferCfg::DestinationHost"
     ::= { docsPnmBulkDataTransferCfgEntry 2 }
     
docsPnmBulkDataTransferCfgDestHostIpAddrType OBJECT-TYPE
     SYNTAX      InetAddressType
     MAX-ACCESS  read-create
     STATUS      current
     DESCRIPTION
        "This attribute indicates the type of the Internet
        address for the destination host.
        If the user configures IpAddrType and IpAddress, they 
        need not configure Hostname."
     REFERENCE
         "Information Model Mapping: CM-SP-CCAP-OSSI    
          DataTransferCfg::DestinationHost"
     ::= { docsPnmBulkDataTransferCfgEntry 3 }
     
docsPnmBulkDataTransferCfgDestHostIpAddress OBJECT-TYPE
     SYNTAX      InetAddress
     MAX-ACCESS  read-create
     STATUS      current
     DESCRIPTION
        "This attribute indicates the destination host IP address.
         If specified, it must be preceeded by the IpAddrType.
         If the user configures IpAddrType and IpAddress, they 
         need not configure Hostname."
     REFERENCE
         "Information Model Mapping: CM-SP-CCAP-OSSI    
          DataTransferCfg::DestinationHost"
     ::= { docsPnmBulkDataTransferCfgEntry 4 }
     
docsPnmBulkDataTransferCfgDestPort OBJECT-TYPE
     SYNTAX      Unsigned32 
     MAX-ACCESS  read-create
     STATUS      current
     DESCRIPTION
        "This attribute identifies a destination port number for PNM test 
         result measurements. 
         If the value of LocalStore is 'false', the attributes for DestHostname 
         or DestHostIpAddrType/DestHostIpAddress, DestinationUri and Protocol 
         must be configured."
     REFERENCE
         "Information Model Mapping: CM-SP-CCAP-OSSI    
          DataTransferCfg::DestinationPort"
     ::= { docsPnmBulkDataTransferCfgEntry 5 }
     
docsPnmBulkDataTransferCfgDestBaseUri  OBJECT-TYPE
     SYNTAX      Uri
     MAX-ACCESS  read-create
     STATUS      current
     DESCRIPTION
        "This attribute identifies a destination base Uniform Resource Identifier
         for PNM test result measurements. This attribute does not contain the 
         actual filename. 
         If the value of LocalStore is 'false', the attributes for DestHostname 
         or DestHostIpAddrType/DestHostIpAddress, DestinationUri and Protocol 
         must be configured."
     REFERENCE
         "Information Model Mapping: CM-SP-CCAP-OSSI    
          DataTransferCfg::DestinationBaseUri"
     ::= { docsPnmBulkDataTransferCfgEntry 6 }
     
docsPnmBulkDataTransferCfgProtocol OBJECT-TYPE
     SYNTAX      INTEGER {tftp(1),
                          http(2),
                          https(3),
                          gnmiStreamingTelemetry(4)
                         }
     MAX-ACCESS  read-write
     STATUS      current
     DESCRIPTION
        "This attribute identifies the data transfer protocol for the PNM 
         test result measurements. If the value of LocalStore is 'false', this object
         must be configured.

             tftp(1)
                Indicates the device will use TFTP to transfer the test result measurements.

             http(2)
                Indicates the device will use HTTP to transfer the test result measurements.
                
             https(3)
                Indicates the device will use HTTPS to transfer the test result measurements.
                This option is not supported in DOCSIS 3.1

             gnmiStreamingTelemetry(4)
                Indicates the device will use gNMI  to transfer the test result measurements. 
                This option is not supported in DOCSIS 3.1."
     REFERENCE
         "Information Model Mapping: CM-SP-CCAP-OSSI    
          DataTransferCfg::Protocol"
     DEFVAL { tftp }
     ::= { docsPnmBulkDataTransferCfgEntry 7 }

docsPnmBulkDataTransferCfgLocalStore  OBJECT-TYPE
     SYNTAX      TruthValue
     MAX-ACCESS  read-create
     STATUS      current
     DESCRIPTION
        "This attribute identifies whether the device stores PNM test 
         result measurements locally. If the valueIf the value of LocalStore is 'false', the attributes for DestHostname 
         or DestHostIpAddrType/DestHostIpAddress, DestinationUri and Protocol 
         must be configured. is set to 'true', the device 
         will store the test result measurements locally on the device. 
         If the value is set to 'false', the device will upload the results
         file to the DestinationHost using the Protocol configured for that host. 
         "
     REFERENCE
         "Information Model Mapping: CM-SP-CCAP-OSSI    
          DataTransferCfg::LocalStore"
     ::= { docsPnmBulkDataTransferCfgEntry 8 }

docsPnmBulkDataTransferCfgRowStatus    OBJECT-TYPE
     SYNTAX      RowStatus
     MAX-ACCESS  read-create
     STATUS      current
     DESCRIPTION
        "The conceptual row status for this table."
     ::= { docsPnmBulkDataTransferCfgEntry 9 }
     
-- ---------------------------------------------------------------------
-- The PNM CCAP Bulk File Status Table
-- ---------------------------------------------------------------------
docsPnmBulkFileStatusTable OBJECT-TYPE
     SYNTAX      SEQUENCE OF DocsPnmBulkFileStatusEntry
     MAX-ACCESS  not-accessible
     STATUS      current
     DESCRIPTION
        "This table reports the status attributes for each Telemetry data file 
         stored locally on the target device."
      REFERENCE
         "Information Model Mapping: CM-SP-CCAP-OSSI 
          FileStatus"
     ::= { docsPnmBulkFileTransfer 2 }

docsPnmBulkFileStatusEntry OBJECT-TYPE
     SYNTAX      DocsPnmBulkFileStatusEntry
     MAX-ACCESS  not-accessible
     STATUS      current
     DESCRIPTION
         "The conceptual row of the 'docsPnmBulkFileStatusTable'. An instance
         is dynamically created and exists for each file that is available
         for upload.

         The device must create a row for each file that is available for
         upload. The device could have have limited resources to save captured
         data files. Therefore, if the number of files exceeds the minimum
         supported number of files requirements for the device, newly created
         rows can overwrite/replace existing rows as new data files become
         available. If a telemetry data file is no longer available for upload, the
         device must remove that file's details from the BulkDataFile table.

         The conceptual rows do not persist across device resets."
     INDEX { docsPnmBulkFileStatusIndex }
     ::= { docsPnmBulkFileStatusTable 1 }

DocsPnmBulkFileStatusEntry ::=
    SEQUENCE {
        docsPnmBulkFileStatusIndex          Unsigned32,
        docsPnmBulkFileStatusLocalFilename  SnmpAdminString,
        docsPnmBulkFileStatusFileStatus     INTEGER,
        docsPnmBulkFileStatusDateCreated    DateAndTime
     }

docsPnmBulkFileStatusIndex OBJECT-TYPE
     SYNTAX      Unsigned32 (1..255)
     MAX-ACCESS  not-accessible
     STATUS      current
     DESCRIPTION
        "This key attribute is the index for the table."
     REFERENCE
         "Information Model Mapping: CM-SP-CCAP-OSSI 
          BulkDataFileStatus::Index"
     ::= { docsPnmBulkFileStatusEntry 1 }

docsPnmBulkFileStatusLocalFilename OBJECT-TYPE
     SYNTAX      SnmpAdminString
     MAX-ACCESS  read-only
     STATUS      current
     DESCRIPTION
        "This attribute contains the name of the bulk data file 
         stored in the device, that is available to be uploaded 
         to the server. Filenames are defined by the application 
         that creates them. "
     REFERENCE
         "Information Model Mapping: CM-SP-CCAP-OSSI    
          BulkDataFileStatus::LocalFilename"
     ::= { docsPnmBulkFileStatusEntry 2 }

docsPnmBulkFileStatusFileStatus OBJECT-TYPE
     SYNTAX      INTEGER {other(1),
                          availableForUpload(2),
                          uploadInProgress(3),
                          uploadCompleted(4),
                          uploadPending(5),
                          uploadCancelled(6),
                          error(7)
                         }
     MAX-ACCESS  read-only
     STATUS      current
     DESCRIPTION
        "This attribute reflects the status of the bulk data file. 
         The possible values are listed below.
         other(1) - Any condition not covered by the other defined values.
         availableForUpload(2) - The file is available to be uploaded.
         uploadInProgress(3) - The file is currently being uploaded.
         uploadCompleted(4) - The file was successfully uploaded.
         uploadPending(5) - The file has been selected for upload, but a condition 
           does not allow the upload to take place. The upload will start when the 
           condition blocking uploads has been removed. For example, another upload 
           that is currently in progress could cause this value to be returned.
         uploadCancelled(6) - An upload was cancelled before it completed.
         error(7) - An error occurred and the file was not successfully uploaded."
     REFERENCE
         "Information Model Mapping: CM-SP-CCAP-OSSI    
          BulkDataFileStatus::FileStatus"
     ::= { docsPnmBulkFileStatusEntry 3 }
     
docsPnmBulkFileStatusDateCreated OBJECT-TYPE
     SYNTAX      DateAndTime
     MAX-ACCESS  read-only
     STATUS      current
     DESCRIPTION
        "The date when the file was written."
     REFERENCE
         "Information Model Mapping: CM-SP-CCAP-OSSI    
          BulkDataFileStatus::DateCreated"
     ::= { docsPnmBulkFileStatusEntry 4 }

-- ---------------------------------------------------------------------
-- The PNM CCAP File Management Table
-- ---------------------------------------------------------------------
docsPnmBulkFileMgmtTable OBJECT-TYPE
     SYNTAX      SEQUENCE OF DocsPnmBulkFileMgmtEntry
     MAX-ACCESS  not-accessible
     STATUS      current
     DESCRIPTION
        "This table represents actions to be taken to manage files 
         on a target device."
     ::= { docsPnmBulkFileTransfer 3 }

docsPnmBulkFileMgmtEntry OBJECT-TYPE
     SYNTAX      DocsPnmBulkFileMgmtEntry
     MAX-ACCESS  not-accessible
     STATUS      current
     DESCRIPTION
         "The conceptual row of the 'docsPnmBulkFileMgmtTable'. 
          Entries are created in this table based on an index in
          the BulkFileStatusTable."
     INDEX { docsPnmBulkFileStatusIndex }
     ::= { docsPnmBulkFileMgmtTable 1 }

DocsPnmBulkFileMgmtEntry ::=
    SEQUENCE {
        docsPnmBulkFileMgmtControl          INTEGER,
        docsPnmBulkFileMgmtDestIndex        Unsigned32,
        docsPnmBulkFileMgmtDeleteFile       TruthValue
     }

docsPnmBulkFileMgmtControl OBJECT-TYPE
     SYNTAX      INTEGER  {
                         abortFileUpload(1),
                         deleteFile(2),
                         uploadFile(3)             
                }                 
     MAX-ACCESS  read-create
     STATUS      current
     DESCRIPTION
        "The operator management operation on the file.
         The actions are as follows:
         
         abortFileUpload(1) - This operations aborts, or cancels, a pending file 
         upload or an upload currently in progress. A successful operation will 
         result in the CCAP aborting a pending file upload or a file upload 
         currently in progress. The FileStatus for the file identified by the Index
         will be changed to 'uploadCancelled'.         
         
         deleteFile(2) - This operation deletes a file stored locally on the 
         target device. A successful operation will result in the CCAP deleting 
         a stored file from local memory.  The FileStatus instance of the file 
         identified by the Index will deleted. An unsuccessful operation will 
         occur if a file upload is currently in progress. 
         
         uploadFile(3) - This operation uploads a file stored locally on the 
         target device. The file specified by the index, with a status of 
         'availableForUpload', will be uploaded to the configured destination server
         specified by DestinationIndex in the DataTransferCfg table. If the 
         docsPnmBulkFileMgmtDeleteFile is set to 'true', the file will be retained in
         local storage. A successful operation will result in the CCAP initiating a 
         file upload using the configured file transfer method.  The FileStatus
         instance of the file identified by the Index will be updated to 'uploadInProgress'.
         If the CCAP is unable to immediately initiate the file transfer due to another 
         blocking condition, the FileStatus instance of the file identified by the Index 
         will be updated to 'uploadPending'. The upload will be initiated when the blocking 
         condition, for example, another upload in progress, has been removed."     
     ::= { docsPnmBulkFileMgmtEntry 1 }
     
docsPnmBulkFileMgmtDestIndex OBJECT-TYPE
     SYNTAX      Unsigned32 
     MAX-ACCESS  read-write
     STATUS      current
     DESCRIPTION
        "The destination index of the corresponding entry in the
         docsPnmBulkDataTransferCfgTable. This is only applicable 
         to an uploadFile request."
     ::= { docsPnmBulkFileMgmtEntry 2 }
     
docsPnmBulkFileMgmtDeleteFile  OBJECT-TYPE
     SYNTAX      TruthValue 
     MAX-ACCESS  read-write
     STATUS      current
     DESCRIPTION
        "This parameter is a Boolean flag indicating whether the target
         device is to retain the file in local storage. If set to 'true', 
        the target device will delete the locally stored file after 
        successful upload. If set to 'false', the target device will 
        retain the locally stored file after a successful upload."
     ::= { docsPnmBulkFileMgmtEntry 3 }


     
-- ---------------------------------------------------------------------
-- CM PNM Objects
-- ---------------------------------------------------------------------

-- ---------------------------------------------------------------------
-- The CM PNM Control Objects
-- ---------------------------------------------------------------------
docsPnmCmControlObjects       OBJECT IDENTIFIER ::= { docsPnmCmObjects 1 }

docsPnmCmCtlTest   OBJECT-TYPE
     SYNTAX      INTEGER {other(1),
                          dsSpectrumAnalyzer(2),
                          dsOfdmSymbolCapture(3),
                          dsOfdmChanEstCoef(4),
                          dsConstellationDisp(5),
                          dsOfdmRxMERPerSubCar(6),
                          dsOfdmCodewordErrorRate(7),
                          dsHistogram(8),
                          usPreEqualizerCoef(9)
                         }
     MAX-ACCESS  read-only
     STATUS      current
     DESCRIPTION
        "This attribute represents the current PNM test. The value could represent
        the current test in-progress or if no test is running, the last test
        that was attempted.

        Any test that is not specifically covered by the enumeration for this
        object, but manipulates the 'PnmCmCtlStatus' object, the CM must set this
        object to a value of 'other' and will update the 'PnmCmCtlTestDuration'
        object. The value of this object is not required to persist across
        device resets. After a reset and before any test is run, the object
        will return a value of 'other'. 
        
        Possible values for this object are listed below:
        other(1) Any PNM test not covered by other defined values
        dsSpectrumAnalyzer(2) Downstream Spectrum Analysis described in 
        Annex D.2.4 CM Spectrum Analysis Objects
        
        dsOfdmSymbolCapture(3) Downstream OFDM Symbol Capture described in
        Annex D.2.5 CmSymbolCapture
        
        dsOfdmChanEstCoef(4) Downstream OFDM Channel Estimate Coefficient described in 
        Annex D.2.6 CmDsOfdmChanEstimateCoef
        
        dsConstellationDisp(5) Downstream Constellation Display described in 
        Annex D.2.7 CmDsConstDispMeas
        
        dsOfdmRxMERPerSubCar(6) Downstream OFDM Receive Modulation Error Ratio per 
        Subcarrier described in Annex D.2.8 CmDsOfdmRxMer
                                
        dsOfdmCodewordErrorRate(7) Downstream OFDM Codeword Error Rate described in
        Annex D.2.10 CmDsOfdmFecSummary
                                   
        dsHistogram(8) Downstream Histogram described in Annex D.2.12 CmDsHist
        
        usPreEqualizerCoef(9) Upstream Pre-equalizer Coefficients described in 
        Annex D.2.13 CmUsPreEq"
     REFERENCE
         "Information Model Mapping: CM-SP-CM-OSSI    
          PnmCmControl::PnmCmCtlTest"
     ::= { docsPnmCmControlObjects 1 }

docsPnmCmCtlTestDuration   OBJECT-TYPE
     SYNTAX      Unsigned32
     UNITS       "seconds"
     MAX-ACCESS  read-only
     STATUS      current
     DESCRIPTION
        "This attribute represents the number of seconds that the test
        specified in 'PnmCmCtlTest' spent with a 'PnmCmCtlStatus' of
        'testInProgress'. This serves to provide a rough (seconds resolution)
        estimate of the time spent under test. If this object is read while
        the value of 'PnmCmCtlStutus' is 'testInProgress', then this object
        will return the number of seconds since the test started. This value
        is informative only and is not a guarantee of future performance. "
     REFERENCE
         "Information Model Mapping: CM-SP-CM-OSSI    
          PnmCmControl::PnmCmCtlTestDuration"
     ::= { docsPnmCmControlObjects 2 }

docsPnmCmCtlStatus   OBJECT-TYPE
     SYNTAX      INTEGER {other(1),
                          ready(2),
                          testInProgress(3),
                          tempReject(4)
                         }
     MAX-ACCESS  read-only
     STATUS      current
     DESCRIPTION
        "This attribute represents the overall status of the PNM test platform.
        Individual tests, within the PNM test suite, have their own specific
        objects to start and stop. For each test defined by the data-type
        enumeration for 'PnmCmCtlTest', the CM must first check the status of this
        object before starting. If this object is set to any value other than
        'ready', the CM must not start the test. If the CM was not able to start
        the test and the test has a 'MeasStatusType' object, the CM must set the
        'MeasStatusType' to a value of 'resourceUnavailable'.

        If the test is allowed to start, the CM must change the value of this
        object to 'testInProgress'. When the test is no longer in progress, the
        CM must change the value of this object to a value other than
        'testInProgress'.

        This mechanism serves to allow only one instance of only one test to
        run at a time. There may be some tests that are not included by
        this control object. That is, if any test is not defined by the
        data-type enumeration for 'PnmCmCtlTest', then it is not included
        (unless otherwise stated by the test definition) and is not required to
        check or to change this object. If a test is not included or covered by
        this set of objects, then it is allowed to run regardless of any
        other tests in progress.

        The possible values for this object are:
          'other' - Any condition not otherwise defined
          'ready' - The PNM platform is capable and ready to support a test.
                    A test can be initiated
          'testInProgress' - A PNM test is currently in progress
          'tempReject' - A temporary condition exists that prohibits a test
                         from starting, e.g., DBC
        "
     REFERENCE
         "Information Model Mapping: CM-SP-CM-OSSI    
          PnmCmControl::PnmCmCtlStatus"
     ::= { docsPnmCmControlObjects 3 }


-- ---------------------------------------------------------------------
-- The CmDsOfdmSymbolCapture Table
-- ---------------------------------------------------------------------
docsPnmCmDsOfdmSymCapTable OBJECT-TYPE
     SYNTAX      SEQUENCE OF DocsPnmCmDsOfdmSymCapEntry
     MAX-ACCESS  not-accessible
     STATUS      current
     DESCRIPTION
        "The purpose of downstream symbol capture is to provide partial
        functionality of a network analyzer to analyze the response of the
        cable plant from the CM's perspective.

        At the CM, the received I and Q time-domain samples of one full OFDM
        symbol before the FFT, not including the guard interval, are captured
        and made available for analysis. This capture will result in a number
        of data points equal to the FFT length in use, time aligned for receiver
        FFT processing. The number of captured samples can be reduced for
        narrower channels if the sampling rate, which is implementation dependent,
        is reduced. The capture includes a bit indicating if receiver windowing
        effects are present in the data. The time domain samples are expressed
        as 16 bit two's complement numbers using s3.12 format. The CM samples are
        scaled such that the average power of the samples is approximately 1, in
        order to avoid excessive clipping and quantization noise.

        Capturing the input and output of the cable plant is equivalent to a
        wideband sweep of the channel, which permits full characterization of
        the linear and nonlinear response of the downstream plant. The MAC
        provides signaling via the PLC Trigger Message to ensure that the same
        symbol is captured at the CMTS and CM.

        The Downstream Symbol Capture is controlled by setting the
        'docsPnmCmDsOfdmSymTrigEnable' object. The status of the capture is
        obtained by reading the value of the 'docsPnmCmDsOfdmSymMeasStatus'
        object.

        This table will have a row for each ifIndex for the modem. "
     REFERENCE
         "Information Model Mapping: CM-SP-CM-OSSI    
          CmSymbolCapture"
     ::= { docsPnmCmObjects 2}

docsPnmCmDsOfdmSymCapEntry OBJECT-TYPE
     SYNTAX      DocsPnmCmDsOfdmSymCapEntry
     MAX-ACCESS  not-accessible
     STATUS      current
     DESCRIPTION
         "The conceptual row of the docsPnmCmDsOfdmSymCapTable. An instance
         is dynamically created and exists for an associated ifIndex of the
         physical downstream channel upon which the test defined by this table
         can take place.

         The conceptual rows do not persist across device resets. "
     INDEX { ifIndex  }
     ::= { docsPnmCmDsOfdmSymCapTable 1 }

DocsPnmCmDsOfdmSymCapEntry ::=
    SEQUENCE {
        docsPnmCmDsOfdmSymTrigEnable            TruthValue,
        docsPnmCmDsOfdmSymTrigEnableTimeout     Unsigned32,
        docsPnmCmDsOfdmSymTrigGroupId           Unsigned32,
        docsPnmCmDsOfdmSymRxWindowing           TruthValue,
        docsPnmCmDsOfdmSymTransactionId         Unsigned32,
        docsPnmCmDsOfdmSymSampleRate            Unsigned32,
        docsPnmCmDsOfdmSymFftLength             Unsigned32,
        docsPnmCmDsOfdmSymMeasStatus            MeasStatusType,
        docsPnmCmDsOfdmSymCaptFileName          SnmpAdminString
     }

docsPnmCmDsOfdmSymTrigEnable OBJECT-TYPE
     SYNTAX      TruthValue
     MAX-ACCESS  read-write
     STATUS      current
     DESCRIPTION
        "If this attribute is set to a value of 'true' the CM must begin
        looking for the presence of the Trigger Message Block in the PLC with
        a Group ID matching the CM's 'docsPnmCmDsOfdmSymTrigGroupId'. The
        TrigEnable is a one-shot enable and the attribute is internally
        disabled when a PLC containing a Group ID matching the CM's
        'docsPnmCmDsOfdmSymTrigGroupId' in a Trigger Message Block is received.

        If this attribute is set to a value of 'false' the CM must stop
        looking for the presence of the Trigger Message Block in the PLC with
        a Group ID matching the CM's 'docsPnmCmDsOfdmSymTrigGroupId'. In this
        case the value of the 'docsPnmCmDsOfdmSymMeasStatus' attribute will be
        set to 'inactive'.

        When read, the CM must return a value of 'true' if the CM is actively
        looking for the presence of the Trigger Message Block in the PLC with
        a Group ID matching the CM's 'docsPnmCmDsOfdmSymTrigGroupId'. Otherwise
        the CM must return 'false'.

        Interaction with other table rows:

        - This object is subject to the rules specified by the
        'docsPnmCmCtlStatus' object. Therefore this object returns
        'inconsistentValue' if set to 'true' while the value of
        'docsPnmCmCtlStatus' is any value other than 'ready'.

        - This object returns 'inconsistentValue' if set to 'true' while the
        CM is in DOCSIS Light Sleep (DLS) mode or the CM is in battery-backup mode.

        - Default values for 'docsPnmCmDsOfdmSymCaptFileName',
        'docsPnmCmDsOfdmSymTrigEnableTimeout', and 'docsPnmCmDsOfdmSymTrigGroupId'
        objects are defined; thus, this object may be set to 'true' without
        explicitly setting these values. Care should be taken to insure these values
        are correct for the desired test case.

        - Setting this attribute to a value of 'true' will change the value of the
        'docsPnmCmDsOfdmSymMeasStatus' attribute to 'busy'. "
     REFERENCE
         "Information Model Mapping: CM-SP-CM-OSSI    
          CmSymbolCapture::TriggerEnable"
     DEFVAL { false }
     ::= { docsPnmCmDsOfdmSymCapEntry 1 }

docsPnmCmDsOfdmSymTrigEnableTimeout OBJECT-TYPE
     SYNTAX      Unsigned32 (0..3600)
     UNITS       "seconds"
     MAX-ACCESS  read-write
     STATUS      current
     DESCRIPTION
        "This attribute is used to disable the TrigEnable if no PLC
        containing a Group ID matching the CM's TrigGroupId in a Trigger
        Message Block is received within the timeout period. The CM must
        timeout the test after TriggerEnableTimeout seconds from the time
        when the TriggerEnable was set to 'true'. A value of 0 indicates
        that no timeout is enforced, in this case the CM must enable the
        test until it completes, note in this case, the trigger could be
        enabled indefinitely.

        This value can only be changed while a test is not in progress. An attempt
        to set this value while the value of 'docsPnmCmDsOfdmSymMeasStatus' is
        'busy' will return 'inconsistentValue'. "
     REFERENCE
         "Information Model Mapping: CM-SP-CM-OSSI    
          CmSymbolCapture::TriggerEnableTimeout"
     DEFVAL { 600 }
     ::= { docsPnmCmDsOfdmSymCapEntry 2 }

docsPnmCmDsOfdmSymTrigGroupId OBJECT-TYPE
     SYNTAX      Unsigned32 (0..65535)
     MAX-ACCESS  read-write
     STATUS      current
     DESCRIPTION
        "This attribute is used to associate a CM with a group of CMs expected
        to perform Symbol Capture measurements for the designated symbol.

        This value can only be changed while a test is not in progress. If the CM
        receives an attempt to set this value while the value of
        'docsPnmCmDsOfdmSymMeasStatus' is 'busy' it will return
        'inconsistentValue' for this attribute."
     REFERENCE
         "Information Model Mapping: CM-SP-CM-OSSI    
          CmSymbolCapture::TriggerGroupId"
     DEFVAL { 0 }
     ::= { docsPnmCmDsOfdmSymCapEntry 3 }

docsPnmCmDsOfdmSymRxWindowing OBJECT-TYPE
     SYNTAX      TruthValue
     MAX-ACCESS  read-only
     STATUS      current
     DESCRIPTION
        "This attribute is a flag indicating if vendor proprietary receiver
        windowing was enabled during the capture. "
     REFERENCE
         "Information Model Mapping: CM-SP-CM-OSSI    
          CmSymbolCapture::RxWindowing"
     ::= { docsPnmCmDsOfdmSymCapEntry 4}

docsPnmCmDsOfdmSymTransactionId OBJECT-TYPE
     SYNTAX      Unsigned32 (0..255)
     MAX-ACCESS  read-only
     STATUS      current
     DESCRIPTION
        "This attribute is the Transaction ID sent by the CMTS in the Trigger
        Message Block. The CMTS increments this field by one on each trigger
        message that is sent, rolling over at value 255. Prior to completion of
        a measurement this attribute has no meaning. "
     REFERENCE
         "Information Model Mapping: CM-SP-CM-OSSI    
          CmSymbolCapture::TransactionId"
     ::= { docsPnmCmDsOfdmSymCapEntry 5 }

docsPnmCmDsOfdmSymSampleRate OBJECT-TYPE
     SYNTAX      Unsigned32
     UNITS       "Hz"
     MAX-ACCESS  read-only
     STATUS      current
     DESCRIPTION
        "This attribute is the FFT sample rate in use by the CM for the
        channel. Typically the sample rate for the downstream channel will
        be 204.8MHz. "
     REFERENCE
         "Information Model Mapping: CM-SP-CM-OSSI    
          CmSymbolCapture::SampleRate"
     ::= { docsPnmCmDsOfdmSymCapEntry 6 }

docsPnmCmDsOfdmSymFftLength OBJECT-TYPE
     SYNTAX      Unsigned32 (512  | 1024 | 2048 |4096 | 8192)
     MAX-ACCESS  read-only
     STATUS      current
     DESCRIPTION
        "This attribute is the FFT length in use by the CM for the channel;
        typically this value is 4096 or 8192 for the Downstream Channel. "
     REFERENCE
         "Information Model Mapping: CM-SP-CM-OSSI    
          CmSymbolCapture::FftLength"
     ::= { docsPnmCmDsOfdmSymCapEntry 7 }

docsPnmCmDsOfdmSymMeasStatus OBJECT-TYPE
     SYNTAX      MeasStatusType
     MAX-ACCESS  read-only
     STATUS      current
     DESCRIPTION
        "This attribute is used to determine the status of the measurement.
        The PNM server will query this value to determine when the file
        is ready for transfer."
     REFERENCE
         "Information Model Mapping: CM-SP-CM-OSSI    
          CmSymbolCapture::MeasStatus"
     ::= { docsPnmCmDsOfdmSymCapEntry 8 }

docsPnmCmDsOfdmSymCaptFileName OBJECT-TYPE
     SYNTAX      SnmpAdminString
     MAX-ACCESS  read-write
     STATUS      current
     DESCRIPTION
        "This attribute is the name of the file, at the CM and containing captured
        symbol data, which is to be downloaded by the PNM server.

        This value can only be changed while a test is not in progress. An attempt
        to set this value while the value of 'docsPnmCmDsOfdmSymMeasStatus' is
        'busy' will return 'inconsistentValue'.

        If the value of this object is the DEFVAL (empty string), then a default
        filename value will be used. Otherwise the value set will be used as
        the filename. If a default filename is generated, then that
        value will be returned in this object and will represent the
        filename that was used for the test. All subsequent tests
        should set this object to a meaningful value or to an
        'empty string' value (to generate a new default filename)
        before starting a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMSymCap_<CM MAC address>_<epoch>

        For example:  PNMSymCap_0010181A2D11_1403405123

        The data file is comprised of a header plus the Symbol Capture Data.
        The header is comprised of ordered fixed-length fields. Unless
        otherwise specified, the header fields contain hex values that are
        right-justified within the field. If necessary, the field is left-padded
        with zero values.

        The file type is either '504E4D01' or '504E4E01' (with Versioning)"
     REFERENCE
         "Information Model Mapping: CM-SP-CM-OSSI    
          CmSymbolCapture::FileName"
     DEFVAL { "" }
     ::= { docsPnmCmDsOfdmSymCapEntry 9 }


-- ---------------------------------------------------------------------
-- The OFDM Downstream Channel Estimate Coefficients Table
-- ---------------------------------------------------------------------
docsPnmCmOfdmChanEstCoefTable OBJECT-TYPE
     SYNTAX      SEQUENCE OF DocsPnmCmOfdmChanEstCoefEntry
     MAX-ACCESS  not-accessible
     STATUS      current
     DESCRIPTION
        "The purpose of this table is for the CM to report its estimate of the
        downstream channel response. The reciprocals of the channel response
        coefficients are typically used by the CM as its frequency-domain
        downstream equalizer coefficients. The channel estimate consists of a
        single complex valued coefficient per subcarrier. The channel response
        coefficients are expressed as 16 bit two's complement numbers using s2.13
        format. The CM samples are scaled such that the average power of the
        samples is approximately 1, in order to avoid excessive clipping and
        quantization noise.
        Summary metrics (slope, ripple, and mean) are defined in order to
        avoid having to send all coefficients on every query. The summary metrics
        are calculated when the corresponding MIB is queried. A Coefficient
        filename and trigger are provided to obtain the channel coefficients.
        This table will have a row for each ifIndex for the modem. "
     REFERENCE
         "Information Model Mapping: CM-SP-CM-OSSI    
          CmDsOfdmChanEstimateCoef"
     ::= { docsPnmCmObjects 3}

docsPnmCmOfdmChanEstCoefEntry OBJECT-TYPE
     SYNTAX      DocsPnmCmOfdmChanEstCoefEntry
     MAX-ACCESS  not-accessible
     STATUS      current
     DESCRIPTION
         "The conceptual row of the docsPnmCmOfdmChanEstCoefTable. An instance
         is dynamically created and exists for an associated ifIndex of the
         physical downstream channel upon which the test defined by this table
         can take place.

         The conceptual rows do not persist across device resets."
     INDEX { ifIndex }
     ::= { docsPnmCmOfdmChanEstCoefTable 1 }

DocsPnmCmOfdmChanEstCoefEntry ::=
    SEQUENCE {
        docsPnmCmOfdmChEstCoefTrigEnable             TruthValue,
        docsPnmCmOfdmChEstCoefAmpRipplePkToPk        ThousandthdB,
        docsPnmCmOfdmChEstCoefAmpRippleRms           ThousandthdB,
        docsPnmCmOfdmChEstCoefAmpSlope               Integer32,
        docsPnmCmOfdmChEstCoefGrpDelayRipplePkToPk   Unsigned32,
        docsPnmCmOfdmChEstCoefGrpDelayRippleRms      Unsigned32,
        docsPnmCmOfdmChEstCoefMeasStatus             MeasStatusType,
        docsPnmCmOfdmChEstCoefFileName               SnmpAdminString,
        docsPnmCmOfdmChEstCoefAmpMean                ThousandthdB,
        docsPnmCmOfdmChEstCoefGrpDelaySlope          Integer32,
        docsPnmCmOfdmChEstCoefGrpDelayMean           Integer32
     }

docsPnmCmOfdmChEstCoefTrigEnable OBJECT-TYPE
     SYNTAX      TruthValue
     MAX-ACCESS  read-write
     STATUS      current
     DESCRIPTION
        "Setting this object to a value of 'true' instructs the CM to begin
        collection and storing the channel estimate coefficients into the
        file specified by the 'docsPnmCmOfdmChEstCoefFileName' object.

        Setting this object to a value of 'false' instructs the CM to stop
        storing channel estimate coefficients in the file.

        When read, this object returns 'true' if the CM is actively storing
        channel estimate coefficients in the file. Otherwise it returns
        'false'.

        Interaction with other table rows:

        - This object is subject to the rules specified by the
        'docsPnmCmCtlStatus' object. Therefore this object returns
        'inconsistentValue' if set to 'true' while the value of
        'docsPnmCmCtlStatus' is any value other than 'ready'.

        - This object returns 'inconsistentValue' if set to 'true' while the
        CM is in DOCSIS Light Sleep (DLS) mode or the CM is in battery-backup mode.

        - A default value for 'docsPnmCmOfdmChEstCoefFileName' is defined; thus,
        this object may be set to 'true' without explicitly setting this value.

        - Setting this object to a value of 'true' will change the value of
        'docsPnmCmOfdmChEstCoefMeasStatus' to 'busy'. "
     REFERENCE
         "Information Model Mapping: CM-SP-CM-OSSI    
          CmDsOfdmChanEstimateCoef::TriggerEnable"
     DEFVAL { false }
     ::= { docsPnmCmOfdmChanEstCoefEntry 1 }

docsPnmCmOfdmChEstCoefAmpRipplePkToPk OBJECT-TYPE
     SYNTAX      ThousandthdB
     UNITS       "dB"
     MAX-ACCESS  read-only
     STATUS      current
     DESCRIPTION
        "This attribute represents the value of the peak to peak ripple
        in the magnitude of the equalizer coefficients [PHYv3.1]. The
        slope component calculated for the AmplitudeSlope is subtracted
        from the frequency domain data and the peak to peak Ripple is
        calculated from the resultant data. This attribute represents
        the ripple across the entire OFDM channel.

        Note: An algorithm for calculating the ripple and slope for
        these measurements is provided in section 6.5 and D.3 of the
        the DOCSIS 3.1 CM OSSI Specification."
     REFERENCE
         "Information Model Mapping: CM-SP-CM-OSSI    
          CmDsOfdmChanEstimateCoef::AmplitudeRipplePkToPk"
     ::= { docsPnmCmOfdmChanEstCoefEntry 2 }

docsPnmCmOfdmChEstCoefAmpRippleRms OBJECT-TYPE
     SYNTAX      ThousandthdB
     UNITS       "dB"
     MAX-ACCESS  read-only
     STATUS      current
     DESCRIPTION
        "This attribute represents the value of the RMS ripple in the
         magnitude of the equalizer coefficients. The slope component
         calculated for the AmplitudeSlope is subtracted from the
         frequency domain data the RMS Ripple is calculated from the
         resultant data. This attribute represents the ripple
         across the entire OFDM channel.

         Note: An algorithm for calculating the ripple and slope for
         these measurements is provided in section D.3 of the
         the DOCSIS 3.1 CM OSSI Specification."
     REFERENCE
         "Information Model Mapping: CM-SP-CM-OSSI    
          CmDsOfdmChanEstimateCoef::AmplitudeRippleRms"
     ::= { docsPnmCmOfdmChanEstCoefEntry 3 }

docsPnmCmOfdmChEstCoefAmpSlope OBJECT-TYPE
     SYNTAX      Integer32
     UNITS       "ThousandthdB/MHz"
     MAX-ACCESS  read-only
     STATUS      current
     DESCRIPTION
        "This attribute represents the slope in 0.001 dB per MHz in the
         magnitude of the equalizer coefficients. The slope is
         calculated as the slope of a linear least squares fit of the
         frequency domain data. This attribute represents the slope
         across the entire OFDM channel.

         Note: An algorithm for calculating the ripple and slope for
         these measurements is provided in section D.3 of the
         the DOCSIS 3.1 CM OSSI Specification."
     REFERENCE
         "Information Model Mapping: CM-SP-CM-OSSI    
          CmDsOfdmChanEstimateCoef::AmplitudeSlope"
     ::= { docsPnmCmOfdmChanEstCoefEntry 4 }

docsPnmCmOfdmChEstCoefGrpDelayRipplePkToPk OBJECT-TYPE
     SYNTAX      Unsigned32
     UNITS       "ThousandthNsec"
     MAX-ACCESS  read-only
     STATUS      current
     DESCRIPTION
        "This attribute represents the peak-to-peak group delay ripple
         expressed in units of 0.001 nsec. This attribute represents the
         group delay variation across the entire OFDM channel. The slope
         component calculated for the GroupDelaySlope is subtracted from
         the frequency domain data and the peak-to-peak ripple is
         calculated from the resultant data."
     REFERENCE
         "Information Model Mapping: CM-SP-CM-OSSI    
          CmDsOfdmChanEstimateCoef::GroupDelayRipplePkToPk"
     ::= { docsPnmCmOfdmChanEstCoefEntry 5 }

docsPnmCmOfdmChEstCoefGrpDelayRippleRms OBJECT-TYPE
     SYNTAX      Unsigned32
     UNITS       "ThousandthNsec"
     MAX-ACCESS  read-only
     STATUS      current
     DESCRIPTION
        "This attribute represents the RMS value of the group delay
         ripple expressed in units of 0.001 nsec. This attribute
         represents the group delay variation across the entire OFDM
         channel. The slope component calculated for the
         GroupDelaySlope is subtracted from the frequency domain data
         and the RMS ripple is calculated from the resultant data.
         This attribute is not stored in the data file. "
     REFERENCE
         "Information Model Mapping: CM-SP-CM-OSSI    
          CmDsOfdmChanEstimateCoef::GroupDelayRippleRms"
     ::= { docsPnmCmOfdmChanEstCoefEntry 6  }

docsPnmCmOfdmChEstCoefMeasStatus OBJECT-TYPE
     SYNTAX      MeasStatusType
     MAX-ACCESS  read-only
     STATUS      current
     DESCRIPTION
        "This attribute is used to determine the status of the measurement.
        The PNM server will query this value to determine when the file
        is ready for transfer. "
     REFERENCE
         "Information Model Mapping: CM-SP-CM-OSSI    
          CmDsOfdmChanEstimateCoef::MeasStatus"
     ::= { docsPnmCmOfdmChanEstCoefEntry 7 }

docsPnmCmOfdmChEstCoefFileName OBJECT-TYPE
     SYNTAX      SnmpAdminString
     MAX-ACCESS  read-write
     STATUS      current
     DESCRIPTION
        "This attribute is the name of the file at the CM which is to be
        transferred to the PNM server. The data is stored as 16 bit integers
        for the I and Q data.

        This value can only be changed while a test is not in progress. An attempt
        to set this value while the value of 'docsPnmCmOfdmChEstCoefMeasStatus' is
        'busy' will return 'inconsistentValue'.

        If the value of this object is the DEFVAL (empty string), then a default
        filename value will be used. Otherwise the value set will be used as
        the filename. If a default filename is generated, then that
        value will be returned in this object and will represent the
        filename that was used for the test. All subsequent tests should
        set this object to a meaningful value or to an 'empty string'
        value (to generate a new default filename) before starting
        a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMChEstCoef_<CM MAC address>_<epoch>

        For example:  PNMChEstCoef_0010181A2D11_1403405123

        The data file is comprised of a header plus the Chan Estimate
        Coefficient Data.
        The header is comprised of ordered fixed-length fields. Unless
        otherwise specified, the header fields contain hex values that are
        right-justified within the field. If necessary the field is left-padded
        with zero values.

        The file type is either '504E4D02' or '504E4E02' (with Versioning)"
     REFERENCE
         "Information Model Mapping: CM-SP-CM-OSSI    
          CmDsOfdmChanEstimateCoef::FileName"
     DEFVAL { "" }
     ::= { docsPnmCmOfdmChanEstCoefEntry 8 }

docsPnmCmOfdmChEstCoefAmpMean OBJECT-TYPE
     SYNTAX      ThousandthdB
     UNITS       "dB"
     MAX-ACCESS  read-only
     STATUS      current
     DESCRIPTION
        "This attribute represents the mean, in 0.001 dB, of the
        magnitude of the equilizer coefficients."
     REFERENCE
         "Information Model Mapping: CM-SP-CM-OSSI    
          CmDsOfdmChanEstimateCoef::AmplitudeMean"
     ::= { docsPnmCmOfdmChanEstCoefEntry 9 }

docsPnmCmOfdmChEstCoefGrpDelaySlope OBJECT-TYPE
     SYNTAX      Integer32
     UNITS       "ThousandthNsec/MHz"
     MAX-ACCESS  read-only
     STATUS      current
     DESCRIPTION
        "This attribute represents the slope in 0.001 nsec per MHz in
         the group delay of the equalizer coefficients. This attribute
         represents the slope across the entire OFDM channel.

        Note: An algorithm for calculating the ripple and slope for these
        measurements is provided in section D.3 of the DOCSIS 3.1 CM
        OSSI Specification."
     REFERENCE
         "Information Model Mapping: CM-SP-CM-OSSI    
          CmDsOfdmChanEstimateCoef::GroupDelaySlope"
     ::= { docsPnmCmOfdmChanEstCoefEntry 10 }

docsPnmCmOfdmChEstCoefGrpDelayMean OBJECT-TYPE
     SYNTAX      Integer32
     UNITS       "ThousandthNsec"
     MAX-ACCESS  read-only
     STATUS      current
     DESCRIPTION
        "This attribute represents the mean of the group delay, in
         units of 0.001 nsec."
     REFERENCE
         "Information Model Mapping: CM-SP-CM-OSSI    
          CmDsOfdmChanEstimateCoef::GroupDelayMean"
     ::= { docsPnmCmOfdmChanEstCoefEntry 11 }

-- ---------------------------------------------------------------------
-- The Downstream Constellation Display Measurement Table
-- ---------------------------------------------------------------------
docsPnmCmDsConstDispMeasTable OBJECT-TYPE
     SYNTAX      SEQUENCE OF DocsPnmCmDsConstDispMeasEntry
     MAX-ACCESS  not-accessible
     STATUS      current
     DESCRIPTION
        "The downstream constellation display provides received QAM
        constellation points for display. Equalized soft decisions (I and Q)
        at the slicer input are collected over time, possibly subsampling to
        reduce complexity, and made available for analysis. This measurement is
        intended for data subcarriers only. Up to 8192 samples are provided for
        each query; additional queries can be made to further fill in the plot.
        The complex Constellation Display values are expressed as 16 bit two's
        complement numbers using s2.13 format. The CM samples are scaled such
        that the average power of the QAM constellation is approximately 1, in
        order to avoid excessive clipping and quantization noise.

        The object controls the CM capturing and reporting of received
        soft-decision samples, for a single selected constellation
        from the set of profiles it is receiving, within a single OFDM
        downstream channel.

        This table will have a row for each ifIndex for the modem."
      REFERENCE
         "Information Model Mapping: CM-SP-CM-OSSI    
          CmDsConstDispMeas"
     ::= { docsPnmCmObjects 4}

docsPnmCmDsConstDispMeasEntry OBJECT-TYPE
     SYNTAX      DocsPnmCmDsConstDispMeasEntry
     MAX-ACCESS  not-accessible
     STATUS      current
     DESCRIPTION
         "The conceptual row of the docsPnmCmDsConstDispMeasTable. An instance
         is dynamically created and exists for an associated ifIndex upon
         which the test defined by this table can take place.

         The conceptual rows do not persist across device resets."
     INDEX { ifIndex }
     ::= { docsPnmCmDsConstDispMeasTable 1 }

DocsPnmCmDsConstDispMeasEntry ::=
    SEQUENCE {
        docsPnmCmDsConstDispTrigEnable         TruthValue,
        docsPnmCmDsConstDispModOrderOffset     Unsigned32,
        docsPnmCmDsConstDispNumSampleSymb      Unsigned32,
        docsPnmCmDsConstDispSelModOrder        DsOfdmModulationType,
        docsPnmCmDsConstDispMeasStatus         MeasStatusType,
        docsPnmCmDsConstDispFileName           SnmpAdminString
     }

docsPnmCmDsConstDispTrigEnable OBJECT-TYPE
     SYNTAX      TruthValue
     MAX-ACCESS  read-write
     STATUS      current
     DESCRIPTION
        "Setting this object to a value of 'true' instructs the CM to begin
        collection and storing the constellation points into the
        file specified by the 'docsPnmCmDsConstDispFileName' object.

        Setting this object to a value of 'false' instructs the CM to stop
        storing constellation points in the file.

        When read, this object returns 'true' if the CM is actively storing
        constellation points in the file. Otherwise it returns
        'false'.

        Interaction with other table rows:

        - This object is subject to the rules specified by the
        'docsPnmCmCtlStatus' object. Therefore this object returns
        'inconsistentValue' if set to 'true' while the value of
        'docsPnmCmCtlStatus' is any value other than 'ready'.

        - This object returns 'inconsistentValue' if set to 'true' while the
        CM is in DOCSIS Light Sleep (DLS) mode or the CM is in battery-backup mode.

        - A default value for 'docsPnmCmDsConstDispFileName' is defined; thus,
        this object may be set to 'true' without explicitly setting this value.

        - Setting this object to a value of 'true' will change the value of the
        'docsPnmCmDsConstDispMeasStatus' to 'busy'."
     REFERENCE
         "Information Model Mapping: CM-SP-CM-OSSI    
          CmDsConstDispMeas::TriggerEnable"
     DEFVAL { false }
     ::= { docsPnmCmDsConstDispMeasEntry 1 }

docsPnmCmDsConstDispModOrderOffset OBJECT-TYPE
     SYNTAX      Unsigned32 (0..10)
     MAX-ACCESS  read-write
     STATUS      current
     DESCRIPTION
        "This attribute specifies an offset from the lowest order modulation
        for the data subcarriers in any of the profiles in the downstream
        channel. If the lowest order modulation order that the CM was receiving
        was 1024-QAM and the ModulationOrderOffset was zero, then the CM would
        capture the soft decision samples for all of the subcarriers which were
        using 1024-QAM modulation order. If the ModulationOrderOffset was 1,
        then the CM would capture the soft decision samples for all of the
        subcarriers using the next highest modulation order in use for the
        profiles in the downstream channel.

        This value can only be changed while a test is not in progress. An attempt
        to set this value while the value of 'docsPnmCmDsConstDispMeasStatus' is
        'busy' will return 'inconsistentValue'."
     REFERENCE
         "Information Model Mapping: CM-SP-CM-OSSI    
          CmDsConstDispMeas::ModulationOrderOffset"
         DEFVAL { 0 }
     ::= { docsPnmCmDsConstDispMeasEntry 2 }

docsPnmCmDsConstDispNumSampleSymb OBJECT-TYPE
     SYNTAX      Unsigned32 (0..65535)
     MAX-ACCESS  read-write
     STATUS      current
     DESCRIPTION
        "This attribute tells the CM how many soft decision samples of
         OFDM subcarriers with the specified modulation order are
         captured.

         This value can only be changed while a test is not in progress.
         An attempt to set this value while the value of
         'docsPnmCmDsConstDispMeasStatus' is 'busy' will return
         'inconsistentValue'."
     REFERENCE
         "Information Model Mapping: CM-SP-CM-OSSI    
          CmDsConstDispMeas::NumSampleSymbols"
     DEFVAL { 8192 }
     ::= { docsPnmCmDsConstDispMeasEntry 3 }

docsPnmCmDsConstDispSelModOrder OBJECT-TYPE
     SYNTAX      DsOfdmModulationType
     MAX-ACCESS  read-only
     STATUS      current
     DESCRIPTION
        "This object provides the actual Modulation Order that will be used for
        the Constellation display based on the selected ModulationOrderOffset."
     REFERENCE
         "Information Model Mapping: CM-SP-CM-OSSI    
          CmDsConstDispMeas::SelectedModulationOrder"
     ::= { docsPnmCmDsConstDispMeasEntry 4 }

docsPnmCmDsConstDispMeasStatus OBJECT-TYPE
     SYNTAX      MeasStatusType
     MAX-ACCESS  read-only
     STATUS      current
     DESCRIPTION
        "This attribute is used to determine the status of the measurement. The
        PNM server will query this value to determine when the file is ready
        for transfer."
     REFERENCE
         "Information Model Mapping: CM-SP-CM-OSSI    
          CmDsConstDispMeas::MeasStatus"
     ::= { docsPnmCmDsConstDispMeasEntry 5}

docsPnmCmDsConstDispFileName OBJECT-TYPE
     SYNTAX      SnmpAdminString
     MAX-ACCESS  read-write
     STATUS      current
     DESCRIPTION
        "This attribute is the name of the file at the CM which is to be
        transferred to the PNM server. The data is stored as 16 bit integers
        for the I and Q data.

        This value can only be changed while a test is not in progress. An attempt
        to set this value while the value of 'docsPnmCmDsConstDispMeasStatus' is
        'busy' will return 'inconsistentValue'.

        If the value of this object is the DEFVAL (empty string), then a default
        filename value will be used. Otherwise the value set will be used as
        the filename. If a default filename is generated, then that
        value will be returned in this object and will represent the
        filename that was used for the test. All subsequent tests should
        set this object to a meaningful value or to an 'empty string'
        value (to generate a new default filename) before starting a
        new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMDSConDisp_<CM MAC address>_<epoch>

        For example:  PNMDSConDisp_0010181A2D11_1403405123

        The data file is comprised of a header plus the Constellation Display
        Data.
        The header is comprised of ordered fixed-length fields. Unless
        otherwise specified, the header fields contain hex values that are
        right-justified within the field. If necessary the field is left-padded
        with zero values.

        The file type is either '504E4D03' or '504E4E03' (with Versioning)"
     REFERENCE
         "Information Model Mapping: CM-SP-CM-OSSI    
          CmDsConstDispMeas::FileName"
     DEFVAL { "" }
     ::= { docsPnmCmDsConstDispMeasEntry 6 }

-- -------------------------------------------------------------------------
-- The Downstream OFDM Receive Modulation Error Ratio (RxMER) Per Subcarrier
-- -------------------------------------------------------------------------
docsPnmCmDsOfdmRxMerTable OBJECT-TYPE
     SYNTAX      SEQUENCE OF DocsPnmCmDsOfdmRxMerEntry
     MAX-ACCESS  not-accessible
     STATUS      current
     DESCRIPTION
        "This table provides measurements of the receive modulation error ratio
        (RxMER) for each subcarrier. Each subcarrier RxMER value consists of one
        byte which represents the RxMER value with range 0 to 63.5 dB in 0.25 dB
        steps. If some subcarriers (such as exclusion bands) cannot be measured
        by the CM, the CM indicates that condition by reporting a value of 0xFF
        for the RxMER for those subcarriers. Any measured RxMER value below 0 dB
        is clipped to 0 dB (0x00), and any measured value above 63.5 dB is clipped
        to 63.5 dB (0xFE).

        Mathematical notation for the calculation of RxMER is provided in [PHYv3.1]:
        'Downstream Receive Modulation Error Ratio (RxMER) Per Subcarrier'.

        This table will have a row for each ifIndex for the modem. "
     REFERENCE
         "Information Model Mapping: CM-SP-CM-OSSI    
          CmDsOfdmRxMer"
     ::= { docsPnmCmObjects 5}

docsPnmCmDsOfdmRxMerEntry OBJECT-TYPE
     SYNTAX      DocsPnmCmDsOfdmRxMerEntry
     MAX-ACCESS  not-accessible
     STATUS      current
     DESCRIPTION
         "The conceptual row of the docsPnmCmDsOfdmRxMerTable. An instance
         is dynamically created and exists for an associated ifIndex upon
         which the test defined by this table can take place.

         The conceptual rows do not persist across device resets. "
     INDEX { ifIndex }
     ::= { docsPnmCmDsOfdmRxMerTable 1 }

DocsPnmCmDsOfdmRxMerEntry ::=
    SEQUENCE {
        docsPnmCmDsOfdmRxMerFileEnable          TruthValue,
        docsPnmCmDsOfdmRxMerPercentile          Unsigned32,
        docsPnmCmDsOfdmRxMerMean                Unsigned32,
        docsPnmCmDsOfdmRxMerStdDev              Unsigned32,
        docsPnmCmDsOfdmRxMerThrVal              Unsigned32,
        docsPnmCmDsOfdmRxMerThrHighestFreq      Unsigned32,
        docsPnmCmDsOfdmRxMerMeasStatus          MeasStatusType,
        docsPnmCmDsOfdmRxMerFileName            SnmpAdminString
     }

docsPnmCmDsOfdmRxMerFileEnable OBJECT-TYPE
     SYNTAX      TruthValue
     MAX-ACCESS  read-write
     STATUS      current
     DESCRIPTION
        "This attribute causes the CM to begin the RxMer measurement for the
        purpose of creating a file of RxMer data. When the measurement is
        complete the FileEnable attribute is set internally to 'false' by the CM.

        Interaction with other table rows:

        - This object is subject to the rules specified by the
        'docsPnmCmCtlStatus' object. Therefore this object returns
        'inconsistentValue' if set to 'true' while the value of
        'docsPnmCmCtlStatus' is any value other than 'ready'.

        - Setting this value to 'true' will change the value of the
        'docsPnmCmDsOfdmRxMerMeasStatus' to 'busy' while the test is in progress.

        - This object returns 'inconsistentValue' if set to 'true' while the
        CM is in DOCSIS Light Sleep (DLS) mode or the CM is in battery-backup mode.

        - A default value for 'docsPnmCmDsOfdmRxMerFileName' is defined; thus,
        this object may be set to 'true' without explicitly setting this this value.

        - Setting this object to a value of 'false' instructs the CM to stop
        the measurement.

        - This object returns 'true' if the CM is actively taking a measurement.
        Otherwise it returns 'false'. "
     REFERENCE
         "Information Model Mapping: CM-SP-CM-OSSI    
          CmDsOfdmRxMer::FileEnable"
     DEFVAL { false }
     ::= { docsPnmCmDsOfdmRxMerEntry 1 }

docsPnmCmDsOfdmRxMerPercentile OBJECT-TYPE
     SYNTAX      Unsigned32 (0..255)
     UNITS       "percent"
     MAX-ACCESS  read-write
     STATUS      current
     DESCRIPTION
        "This attribute specifies the percentile (such as 2nd percentile or 5th
        percentile) of all active subcarriers in an OFDM channel at which the
        ThresholdRxMerValue occurs. That is, (Percentile) % of the subcarriers
        have RxMER <= ThresholdRxMerValue. "
     REFERENCE
         "Information Model Mapping: CM-SP-CM-OSSI    
          CmDsOfdmRxMer::Percentile"
     DEFVAL { 2 }
     ::= { docsPnmCmDsOfdmRxMerEntry 2 }

docsPnmCmDsOfdmRxMerMean OBJECT-TYPE
     SYNTAX      Unsigned32 (0..65535)
     UNITS       "HundredthdB"
     MAX-ACCESS  read-only
     STATUS      current
     DESCRIPTION
        "This attribute is the mean of the dB values of the RxMER measurements
        of all active subcarriers. The mean is computed directly on the dB
        values as follows:
              Mean = sum of (RxMER dB values) / number of RxMER values
        "
     REFERENCE
         "Information Model Mapping: CM-SP-CM-OSSI    
          CmDsOfdmRxMer::Mean"
     ::= { docsPnmCmDsOfdmRxMerEntry 3 }

docsPnmCmDsOfdmRxMerStdDev OBJECT-TYPE
     SYNTAX      Unsigned32 (0..65535)
     UNITS       "HundredthdB"
     MAX-ACCESS  read-only
     STATUS      current
     DESCRIPTION
        "This attribute is the standard deviation of the dB values of the RxMER
        measurements of all active subcarriers. The standard deviation is
        computed directly on the dB values as follows:
          StdDev = sqrt(sum of (RxMER dB values - RxMER_mean)^2 / number of RxMER values)"
     REFERENCE
         "Information Model Mapping: CM-SP-CM-OSSI    
          CmDsOfdmRxMer::StdDev"
     ::= { docsPnmCmDsOfdmRxMerEntry 4 }

docsPnmCmDsOfdmRxMerThrVal OBJECT-TYPE
     SYNTAX      Unsigned32 (0..255)
     UNITS       "quarterDb"
     MAX-ACCESS  read-only
     STATUS      current
     DESCRIPTION
        "This attribute is the RxMER value corresponding to the specified
        Percentile value. The CM sorts the subcarriers in ascending order of
        RxMER, resulting in a post-sorting subcarrier index ranging from 1 to
        the number of active subcarriers. If the percentile value corresponds
        to a non-integer post-sorting subcarrier index, the post-sorting index
        is truncated (floor function is applied), that is, the post-sorting
        index is selected which is the greatest integer less than or equal to
        the corresponding percentile value. For example, if there are 3677
        active subcarriers and the 2nd percentile is specified, the CM computes
        floor(3677*0.02) = 73. That is, the RxMER value of the 73rd subcarrier
        in the sorted list is associated with the 2nd percentile. "
     REFERENCE
         "Information Model Mapping: CM-SP-CM-OSSI    
          CmDsOfdmRxMer::ThresholdRxMerValue"
     ::= { docsPnmCmDsOfdmRxMerEntry 5 }

docsPnmCmDsOfdmRxMerThrHighestFreq OBJECT-TYPE
     SYNTAX      Unsigned32
     UNITS       "Hz"
     MAX-ACCESS  read-only
     STATUS      current
     DESCRIPTION
        "This attribute is the frequency in Hz of the highest-frequency
        subcarrier having RxMER = ThresholdRxMerValue."
     REFERENCE
         "Information Model Mapping: CM-SP-CM-OSSI    
          CmDsOfdmRxMer::ThresholdRxMerHighestFreq"
     ::= { docsPnmCmDsOfdmRxMerEntry 6 }

docsPnmCmDsOfdmRxMerMeasStatus OBJECT-TYPE
     SYNTAX      MeasStatusType
     MAX-ACCESS  read-only
     STATUS      current
     DESCRIPTION
        "This attribute is used to determine the status of the measurement.
        The PNM server will query this value to determine when the file
        is ready for transfer. "
     REFERENCE
         "Information Model Mapping: CM-SP-CM-OSSI    
          CmDsOfdmRxMer::MeasStatus"
     ::= { docsPnmCmDsOfdmRxMerEntry 7 }

docsPnmCmDsOfdmRxMerFileName OBJECT-TYPE
     SYNTAX      SnmpAdminString
     MAX-ACCESS  read-write
     STATUS      current
     DESCRIPTION
        "This attribute is the name of the file at the CM which is to be
        downloaded by the PNM server.

        This value can only be changed while a test is not in progress. An attempt
        to set this value while the value of 'docsPnmCmDsOfdmRxMerMeasStatus' is
        'busy' will return 'inconsistentValue'.

        If the value of this object is the DEFVAL (empty string), then a default
        filename value will be used. Otherwise the value set will be used as
        the filename. If a default filename is generated, then that
        value will be returned in this object and will represent the
        filename that was used for the test. All subsequent tests should
        set this object to a meaningful value or to an 'empty string'
        value (to generate a new default filename) before starting
        a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMDsMer_<CM MAC address>_<epoch>

        For example:  PNMDsMer_0010181A2D11_1403405123

        The data file is comprised of a header plus the Subcarrier RxMER Data
        The header is comprised of ordered fixed-length fields. Unless
        otherwise specified, the header fields contain hex values that are
        right-justified within the field. If necessary the field is left-padded
        with zero values.

        The file type is either '504E4D04' or '504E4E04' (with Versioning)"
     REFERENCE
         "Information Model Mapping: CM-SP-CM-OSSI    
          CmDsOfdmRxMer::FileName"
     DEFVAL { "" }
     ::= { docsPnmCmDsOfdmRxMerEntry 8 }


-- ---------------------------------------------------------------------
-- The CM Downstream OFDM MER for the Profile Table
-- ---------------------------------------------------------------------
docsPnmCmDsOfdmMerMarTable OBJECT-TYPE
     SYNTAX      SEQUENCE OF DocsPnmCmDsOfdmMerMarEntry
     MAX-ACCESS  not-accessible
     STATUS      current
     DESCRIPTION
        "The purpose of this item is to provide an estimate of the MER margin
        available on the downstream data channel with respect to a modulation
        profile. The  profile may be a profile that the modem has already been
        assigned or a candidate profile. This is similar to the MER Margin reported
        in the OPT-RSP Message [MULPIv3.1].

        The CM calculates the Required Average MER for the profile based on the bit
        loading for the profile and the Required MER per Modulation Order provided in
        the CmDsOfdmRequiredQamMer Table. For profiles with mixed modulation orders,
        this value is computed  as an arithmetic mean of the required MER values for
        each non-excluded subcarrier in the Modulated Spectrum.The CM then measures the
        RxMER per subcarrier and calculates the Average MER for the Active Subcarriers
        used in the Profile and stores the value as MeasuredAvgMer. The Operator may also
        compute the value for Required Average MER for the profile and set that value
        for the test.

        The CM also counts the number of MER per Subcarrier values below the
        threshold determined by the CmDsOfdmRequiredQamMer and the ThrshldOffset. The
        CM reports that value as NumSubcarriersBelowThrshld.

        This table will have a row for each ifIndex for the modem."
     REFERENCE
         "Information Model Mapping: CM-SP-CM-OSSI    
          CmDsOfdmMerMargin"
     ::= { docsPnmCmObjects 6}

docsPnmCmDsOfdmMerMarEntry OBJECT-TYPE
     SYNTAX      DocsPnmCmDsOfdmMerMarEntry
     MAX-ACCESS  not-accessible
     STATUS      current
     DESCRIPTION
         "The conceptual row of the docsPnmCmDsOfdmMerMarTable. An instance
         is dynamically created and exists for an associated ifIndex upon
         which the test defined by this table can take place.

         The conceptual rows do not persist across device resets. "

     INDEX { ifIndex }
     ::= { docsPnmCmDsOfdmMerMarTable 1 }

DocsPnmCmDsOfdmMerMarEntry ::=
    SEQUENCE {
        docsPnmCmDsOfdmMerMarProfileId                Unsigned32,
        docsPnmCmDsOfdmMerMarThrshldOffset            Unsigned32,
        docsPnmCmDsOfdmMerMarMeasEnable               TruthValue,
        docsPnmCmDsOfdmMerMarNumSymPerSubCarToAvg     Unsigned32,
        docsPnmCmDsOfdmMerMarReqAvgMer                Unsigned32,
        docsPnmCmDsOfdmMerMarNumSubCarBelowThrshld    Unsigned32,
        docsPnmCmDsOfdmMerMarMeasuredAvgMer           Unsigned32,
        docsPnmCmDsOfdmMerMarAvgMerMargin             Integer32,
        docsPnmCmDsOfdmMerMarMeasStatus               MeasStatusType
     }

docsPnmCmDsOfdmMerMarProfileId OBJECT-TYPE
     SYNTAX      Unsigned32 (0..15)
     MAX-ACCESS  read-write
     STATUS      current
     DESCRIPTION
        "This attribute represents the Downstream Profile ID of the Profile.
        The profile may be a profile that the modem has already been assigned
        or a candidate profile.

        This value can only be changed while a test is not in progress. An attempt
        to set this value while the value of 'docsPnmCmDsOfdmMerMarMeasStatus' is
        'busy' will return 'inconsistentValue'. "
     REFERENCE
         "Information Model Mapping: CM-SP-CM-OSSI    
          CmDsOfdmMerMargin::ProfileId"
     DEFVAL { 0 }
     ::= { docsPnmCmDsOfdmMerMarEntry 1 }

docsPnmCmDsOfdmMerMarThrshldOffset OBJECT-TYPE
     SYNTAX      Unsigned32
     UNITS       "quarterDb"
     MAX-ACCESS  read-write
     STATUS      current
     DESCRIPTION
        "This attribute represents the number of dB below the
        RequiredDsOfdmQamMer value for a given modulation order that is likely
        to cause uncorrectable errors. Measurements of Subcarrier MER that are
        this number of dB or more below the RequiredDsOfdmQamMer for the
        Subcarrier for the profile being tested, will cause the CM to increment
        the count of the 'docsPnmCmDsOfdmMerMarNumSubCarBelowThrshld' attribute.

        This value can only be changed while a test is not in progress. An attempt
        to set this value while the value of 'docsPnmCmDsOfdmMerMarMeasStatus' is
        'busy' will return 'inconsistentValue'. "
      REFERENCE
         "Information Model Mapping: CM-SP-CM-OSSI    
          CmDsOfdmMerMargin::ThrshldOffset"
     DEFVAL { 0 }
     ::= { docsPnmCmDsOfdmMerMarEntry 2 }

docsPnmCmDsOfdmMerMarMeasEnable OBJECT-TYPE
     SYNTAX      TruthValue
     MAX-ACCESS  read-write
     STATUS      current
     DESCRIPTION
        "This attribute causes the CM to begin the measurement. When the
        measurement is complete the MeasEnable attribute is set internally to
        'false' by the CM.

        Setting this object to a value of 'false' instructs the CM to stop
        the measurement.

        This object returns 'true' if the CM is actively taking a measurement.
        Otherwise it returns 'false'.

        Interaction with other table rows:

        - This object returns 'inconsistentValue' if set to 'true' while the
        value of 'docsPnmCmDsOfdmMerMarMeasStatus' is a value of 'busy' for this row
        OR for any row in the table. That is, ONLY ONE ROW IN THE TABLE MAY BE
        ALLOWED TO BE 'true' AT THE SAME TIME.

        - This object returns 'inconsistentValue' if set to 'true' while the
        CM is in DOCSIS Light Sleep (DLS) mode or the CM is in battery-backup mode.

        - Setting this object to a value of 'true' will change the value of the
        'docsPnmCmDsOfdmMerMarMeasStatus' to 'busy'. "
      REFERENCE
         "Information Model Mapping: CM-SP-CM-OSSI    
          CmDsOfdmMerMargin::MeasEnable"
     DEFVAL { false }
     ::= { docsPnmCmDsOfdmMerMarEntry 3 }

docsPnmCmDsOfdmMerMarNumSymPerSubCarToAvg OBJECT-TYPE
     SYNTAX      Unsigned32 (0..65535)
     MAX-ACCESS  read-write
     STATUS      current
     DESCRIPTION
        "This attribute represents the number of symbols that will be used in
        the calculation of the average MER per subcarrier.

        This value can only be changed while a test is not in progress. An attempt
        to set this value while the value of 'docsPnmCmDsOfdmMerMarMeasStatus' is
        'busy' will return 'inconsistentValue'. "
      REFERENCE
         "Information Model Mapping: CM-SP-CM-OSSI    
          CmDsOfdmMerMargin::NumSymPerSubcarToAvg"
     DEFVAL { 8 }
     ::= { docsPnmCmDsOfdmMerMarEntry 4 }

docsPnmCmDsOfdmMerMarReqAvgMer  OBJECT-TYPE
     SYNTAX      Unsigned32
     UNITS       "quarterDb"
     MAX-ACCESS  read-write
     STATUS      current
     DESCRIPTION
        "This attribute represents the minimum required average MER. This value can
        either be computed by the entity requesting the test or be computed by the
        test when the attribute uses the default value 0. The CM subtracts this value
        from the MeasuredAvgMer to obtain the AverageMerMargin. If this value is not
        provided by the PNM server (i.e., it is the default value of zero), the CM
        computes the value as the average of the required MER for all of the subcarriers,
        based on the values in the CmDsOfdmRequiredQamMer table, for the Modulation order
        used for each of the subcarriers for the profile being analyzed. For profiles
        with mixed modulation orders, this value is computed by averaging as an arithmetic
        mean of the required MER values for each set of non-excluded subcarriers in the
        modulated spectrum."
     REFERENCE
         "Information Model Mapping: CM-SP-CM-OSSI    
          CmDsOfdmMerMargin::ReqAvgMer"
     DEFVAL { 0 }
     ::= { docsPnmCmDsOfdmMerMarEntry 5 }

docsPnmCmDsOfdmMerMarNumSubCarBelowThrshld  OBJECT-TYPE
     SYNTAX      Unsigned32 (0..65535)
     MAX-ACCESS  read-only
     STATUS      current
     DESCRIPTION
        "This object represents the count of the  number of subcarriers which were
         below the docsPnmCmDsOfdmMerMarReqAvgMer for the 'docsPnmCmDsOfdmMerMarThrshldOffset'
         object."
     REFERENCE
         "Information Model Mapping: CM-SP-CM-OSSI    
          CmDsOfdmMerMargin::NumSubcarBelowThrshld"
     ::= { docsPnmCmDsOfdmMerMarEntry 6 }

docsPnmCmDsOfdmMerMarMeasuredAvgMer  OBJECT-TYPE
     SYNTAX      Unsigned32
     UNITS       "hundrethdB"
     MAX-ACCESS  read-only
     STATUS      current
     DESCRIPTION
        "This attribute is the arithmetic mean of all MER dB values measured over all of
        the subcarriers in the encompassed spectrum. That is, the average is taken
        of all the dB values."
     REFERENCE
         "Information Model Mapping: CM-SP-CM-OSSI    
          CmDsOfdmMerMargin::MeasuredAvgMer"
     ::= { docsPnmCmDsOfdmMerMarEntry 7 }

docsPnmCmDsOfdmMerMarAvgMerMargin  OBJECT-TYPE
     SYNTAX      Integer32
     UNITS       "hundrethdB"
     MAX-ACCESS  read-only
     STATUS      current
     DESCRIPTION
        "This attribute represents the difference between the
        'docsPnmCmDsOfdmMerMarMeasuredAvgMer' and the 'docsPnmCmDsOfdmMerMarReqAvgMer'."
     REFERENCE
         "Information Model Mapping: CM-SP-CM-OSSI    
          CmDsOfdmMerMargin::AverageMerMargin"
     ::= { docsPnmCmDsOfdmMerMarEntry 8 }

docsPnmCmDsOfdmMerMarMeasStatus  OBJECT-TYPE
     SYNTAX      MeasStatusType
     MAX-ACCESS  read-only
     STATUS      current
     DESCRIPTION
        "This attribute is used to determine the status of the measurement.
        The PNM server will query this value to determine when the data is ready
        for evaluation. "
     REFERENCE
         "Information Model Mapping: CM-SP-CM-OSSI    
          CmDsOfdmMerMargin::MeasStatus"
     ::= { docsPnmCmDsOfdmMerMarEntry 9 }

-- ---------------------------------------------------------------------
-- The CM Downstream OFDM Codeword Error Summary Per Profile
-- ---------------------------------------------------------------------
docsPnmCmDsOfdmFecTable OBJECT-TYPE
     SYNTAX      SEQUENCE OF DocsPnmCmDsOfdmFecEntry
     MAX-ACCESS  not-accessible
     STATUS      current
     DESCRIPTION
        "The purpose of the table is to provide a series of codword error rate
        measurements on a per profle basis over a set period of time.

        This table will have a row for each ifIndex for the modem. "
     REFERENCE
         "Information Model Mapping: CM-SP-CM-OSSI    
          CmDsOfdmFecSummary"
     ::= { docsPnmCmObjects 7}

docsPnmCmDsOfdmFecEntry OBJECT-TYPE
     SYNTAX      DocsPnmCmDsOfdmFecEntry
     MAX-ACCESS  not-accessible
     STATUS      current
     DESCRIPTION
         "The conceptual row of the docsPnmCmDsOfdmFecTable. An instance
         is dynamically created and exists for an associated ifIndex upon
         which the test defined by this table can take place.

         The conceptual rows do not persist across device resets. "
     INDEX { ifIndex }
     ::= { docsPnmCmDsOfdmFecTable 1 }

DocsPnmCmDsOfdmFecEntry ::=
    SEQUENCE {
        docsPnmCmDsOfdmFecSumType        INTEGER,
        docsPnmCmDsOfdmFecFileEnable     TruthValue,
        docsPnmCmDsOfdmFecMeasStatus     MeasStatusType,
        docsPnmCmDsOfdmFecFileName       SnmpAdminString
     }

docsPnmCmDsOfdmFecSumType OBJECT-TYPE
     SYNTAX      INTEGER {other(1),
                          interval10min(2),
                          interval24hr(3)
                         }
     MAX-ACCESS  read-write
     STATUS      current
     DESCRIPTION
        "This attribute is the type of summary test to be performed. If set to
        'interval10min(2)', when enabled the CM must perform a test of 10
        minutes in duration recording codeword data every second for a total of
        600 measurements. If set to 'interval24hr(3)', when enabled the CM must
        perform a test of 24hours in duration recording codeword data every 60
        seconds for a total of 1440 measurements. "
     REFERENCE
         "Information Model Mapping: CM-SP-CM-OSSI    
          CmDsOfdmFecSummary::SummaryType"
     DEFVAL { interval10min }
     ::= { docsPnmCmDsOfdmFecEntry 1 }

docsPnmCmDsOfdmFecFileEnable OBJECT-TYPE
     SYNTAX      TruthValue
     MAX-ACCESS  read-write
     STATUS      current
     DESCRIPTION
        "When this attribute is set to 'true' the CM must begin the SummaryType
        codeword error summary test. While the test is in progress, the CM must
        return a MeasStatus value of 'busy'. When the measurement is complete
        the CM must set the MeasEnable attribute to 'false'. If this attribute
        is set to 'false' during a test, the CM must stop the test.

        Interaction with other table rows:

        - This object is subject to the rules specified by the
        'docsPnmCmCtlStatus' object. Therefore this object returns
        'inconsistentValue' if set to 'true' while the value of
        'docsPnmCmCtlStatus' is any value other than 'ready'.

        - This object returns 'inconsistentValue' if set to 'true' while the
        CM is in DOCSIS Light Sleep (DLS) mode or the CM is in battery-backup mode.

        - A default value for 'docsPnmCmDsOfdmFecFileName' is defined; thus,
        this object may be set to 'true' without explicitly setting this value.

        - Setting this object to a value of 'true' will change the value of the
        'docsPnmCmDsOfdmFecMeasStatus' to 'busy'.

        The CM must return the value of 'true' if it is actively taking a
        measurement; otherwise it must return 'false'."
     REFERENCE
         "Information Model Mapping: CM-SP-CM-OSSI    
          CmDsOfdmFecSummary::FileEnable"
     DEFVAL { false }
     ::= { docsPnmCmDsOfdmFecEntry 2 }

docsPnmCmDsOfdmFecMeasStatus OBJECT-TYPE
     SYNTAX      MeasStatusType
     MAX-ACCESS  read-only
     STATUS      current
     DESCRIPTION
        "This attribute is used to determine the status of the measurement.
        The PNM server will query this value to determine when the file
        is ready for transfer. "
     REFERENCE
         "Information Model Mapping: CM-SP-CM-OSSI    
          CmDsOfdmFecSummary::MeasStatus"
     ::= { docsPnmCmDsOfdmFecEntry 3 }

docsPnmCmDsOfdmFecFileName OBJECT-TYPE
     SYNTAX      SnmpAdminString
     MAX-ACCESS  read-write
     STATUS      current
     DESCRIPTION
        "This attribute is the name of the file at the CM which is to be
        transferred to the PNM server.

        This value can only be changed while a test is not in progress. An attempt
        to set this value while the value of 'docsPnmCmDsOfdmFecMeasStatus' is
        'busy' will return 'inconsistentValue'.

        If the value of this object is the DEFVAL (empty string), then a default
        filename value will be used. Otherwise the value set will be used as
        the filename. If a default filename is generated, then that value
        will be returned in this object and will represent the filename
        that was used for the test. All subsequent tests should set this
        object to a meaningful value or to an 'empty string' value
        (to generate a new default filename) before starting a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMFecSum_<CM MAC address>_<epoch>

        For example:  PNMFecSum_0010181A2D11_1403405123

        The data file is comprised of a header plus a set of FEC Summary Data for
        each profile. The header is comprised of ordered fixed-length fields.
        Unless otherwise specified, the header fields contain hex values that are
        right-justified within the field. If necessary the field is left-padded
        with zero values.

        The file type is either '504E4D08' or '504E4E08' (with Versioning)"
     REFERENCE
         "Information Model Mapping: CM-SP-CM-OSSI    
          CmDsOfdmFecSummary::FileName"
     DEFVAL { "" }
     ::= { docsPnmCmDsOfdmFecEntry 4 }

-- ---------------------------------------------------------------------
-- The CM OFDM Downstream Required QAM MER
-- ---------------------------------------------------------------------
docsPnmCmDsOfdmReqMERObjects       OBJECT IDENTIFIER ::= { docsPnmCmObjects 8 }

docsPnmCmDsOfdmReqMerQam16   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam16"
     DEFVAL { 60 }
     ::= { docsPnmCmDsOfdmReqMERObjects 1 }

docsPnmCmDsOfdmReqMerQam64   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam64"
     DEFVAL { 84 }
     ::= { docsPnmCmDsOfdmReqMERObjects 2 }

docsPnmCmDsOfdmReqMerQam128   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam128"
     DEFVAL { 96 }
     ::= { docsPnmCmDsOfdmReqMERObjects 3 }

docsPnmCmDsOfdmReqMerQam256   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam256"
     DEFVAL { 108 }
     ::= { docsPnmCmDsOfdmReqMERObjects 4 }

docsPnmCmDsOfdmReqMerQam512   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam512"
     DEFVAL { 122 }
     ::= { docsPnmCmDsOfdmReqMERObjects 5 }

docsPnmCmDsOfdmReqMerQam1024   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam1024"
     DEFVAL { 136 }
     ::= { docsPnmCmDsOfdmReqMERObjects 6 }

docsPnmCmDsOfdmReqMerQam2048   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam2048"
     DEFVAL { 148 }
     ::= { docsPnmCmDsOfdmReqMERObjects 7 }

docsPnmCmDsOfdmReqMerQam4096   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam4096"
      DEFVAL { 164 }
     ::= { docsPnmCmDsOfdmReqMERObjects 8 }

docsPnmCmDsOfdmReqMerQam8192   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam8192"
     DEFVAL { 184 }
     ::= { docsPnmCmDsOfdmReqMERObjects 9 }

docsPnmCmDsOfdmReqMerQam16384   OBJECT-TYPE
     SYNTAX      Unsigned32
     UNITS       "quarterdB"
     MAX-ACCESS  read-write
     STATUS      current
     DESCRIPTION
        "This attribute represents the minimum required MER value for this
        Modulation Order. It is used in determining the SNR Margin for the
        Candidate Downstream Profile. "
     REFERENCE
         "Information Model Mapping: CM-SP-CM-OSSI    
          CmDsOfdmRequiredQamMer::MerQam16384"
     DEFVAL { 208 }
     ::= { docsPnmCmDsOfdmReqMERObjects 10 }


-- ---------------------------------------------------------------------
-- The Downstream Histogram Table
-- ---------------------------------------------------------------------
docsPnmCmDsHistTable OBJECT-TYPE
     SYNTAX      SEQUENCE OF DocsPnmCmDsHistEntry
     MAX-ACCESS  not-accessible
     STATUS      current
     DESCRIPTION
        "The purpose of the downstream histogram is to provide a measurement of
        nonlinear effects in the channel such as amplifier compression and laser
        clipping. For example, laser clipping causes one tail of the histogram
        to be truncated and replaced with a spike. The CM captures the histogram
        of time domain samples at the wideband front end of the receiver (full
        downstream band). The histogram is two-sided; that is, it encompasses
        values from far-negative to far-positive values of the samples. The
        histogram will have 255 or 256 equally spaced bins.
        These bins typically correspond to the 8 MSBs of the wideband
        analog-to-digital converter (ADC) for the case of 255 or 256 bins.
        The histogram dwell count, a 32-bit unsigned integer, is the number of
        samples observed while counting hits for a given bin, and may have the
        same value for all bins. The histogram hit count, a 32-bit unsigned
        integer, is the number of samples falling in a given bin. The CM
        reports the dwell count per bin and the hit count per bin. When
        enabled, the CM computes a histogram with a dwell of at least 10
        million samples at each bin in 30 seconds or less. The CM continues
        accumulating histogram samples until it is restarted, disabled or times
        out. If the highest dwell count approaches its 32-bit overflow value,
        the CM stops counting and sets the docsPnmCmDsHistMeasStatus attribute to
        'sampleReady'. The CM reports the capture time of the histogram
        measurement in the Header Elements of the file for TFTP download
        using the 32-bit Universal Time Code.

        This table will have a row for each docsCableMaclayer type
        ifIndex for the modem."
     REFERENCE
         "Information Model Mapping: CM-SP-CM-OSSI    
          CmDsHist"
     ::= { docsPnmCmObjects 9}

docsPnmCmDsHistEntry OBJECT-TYPE
     SYNTAX      DocsPnmCmDsHistEntry
     MAX-ACCESS  not-accessible
     STATUS      current
     DESCRIPTION
         "The conceptual row of the docsPnmCmDsHistTable. An instance
         is dynamically created and exists for an associated ifIndex
         of the RF MAC interface upon which the test defined by this
         table can take place.

         The conceptual rows do not persist across device resets."
     INDEX { ifIndex }
     ::= { docsPnmCmDsHistTable 1 }

DocsPnmCmDsHistEntry ::=
    SEQUENCE {
        docsPnmCmDsHistEnable                  TruthValue,
        docsPnmCmDsHistTimeOut                 Unsigned32,
        docsPnmCmDsHistMeasStatus              MeasStatusType,
        docsPnmCmDsHistFileName                SnmpAdminString
     }

docsPnmCmDsHistEnable OBJECT-TYPE
     SYNTAX      TruthValue
     MAX-ACCESS  read-write
     STATUS      current
     DESCRIPTION
        "Setting this object to a value of 'true' instructs the CM to begin
        collection of histogram data and when enabled, the CM continues
        producing new data at its own rate.

        Setting this object to a value of 'false' instructs the CM to stop
        the collection of histogram data.

        This object returns 'true' if the CM is actively collecting histogram
        data. Otherwise it returns 'false'.

        A restart may be accomplished by setting this attribute to
        'false' and then back to 'true'.

        Interaction with other table rows:

        - This object is subject to the rules specified by the
        'docsPnmCmCtlStatus' object. Therefore this object returns
        'inconsistentValue' if set to 'true' while the value of
        'docsPnmCmCtlStatus' is any value other than 'ready'.

        - This object returns 'inconsistentValue' if set to 'true' while the
        CM is in DOCSIS Light Sleep (DLS) mode or the CM is in battery-backup mode.

        - Setting this object to a value of 'true' will change the value of the
        'docsPnmCmDsHistMeasStatus' to 'busy'. "
     REFERENCE
         "Information Model Mapping: CM-SP-CM-OSSI    
          CmDsHist::Enable"
     DEFVAL { false }
     ::= { docsPnmCmDsHistEntry 1 }

docsPnmCmDsHistTimeOut OBJECT-TYPE
     SYNTAX      Unsigned32 (0..65535)
     UNITS       "seconds"
     MAX-ACCESS  read-write
     STATUS      current
     DESCRIPTION
        "This object sets a seconds time-out timer for capturing histogram data.
        This attribute is used to automatically clear the Enable
        attribute when the timeout expires. If the value of this
        attribute is zero, the CM will collect data until the value
        is changed, stopped, or until any dwell counter approaches
        its 32 bit rollover value. If the Timeout attribute is
        re-written while Enable is 'true', the CM will restart the
        timeout timer with the new Timeout value and continue
        collecting data.

        When the timeout expires the 'docsPnmCmDsHistEnable' object will be set to
        'false' and the capture will stop. When this happens, the data collected up
        to this point will be saved in the the file defined by the
        'docsPnmCmDsHistFileName', and the value of 'docsPnmCmDsHistMeasStatus'
        will be set to 'sampleReady'.

        Setting this value does not start a capture. Captures can only be started by
        setting the 'docsPnmCmDsHistEnable' object.

        If this object is written while the 'docsPnmCmDsHistEnable' object is 'true',
        the timer is restarted.

        If this object is set to a value of 'zero', there is no timeout and the
        collection of data will continue indefinitely.

        This object returns the value that it was last set with. "
     REFERENCE
         "Information Model Mapping: CM-SP-CM-OSSI    
          CmDsHist::Timeout"
     DEFVAL { 1800 }
     ::= { docsPnmCmDsHistEntry 2 }

docsPnmCmDsHistMeasStatus OBJECT-TYPE
     SYNTAX      MeasStatusType
     MAX-ACCESS  read-only
     STATUS      current
     DESCRIPTION
        "This attribute is used to determine the status of the measurement.
        The PNM server will query this value to determine when the file
        is ready for transfer. "
     REFERENCE
         "Information Model Mapping: CM-SP-CM-OSSI    
          CmDsHist::MeasStatus"
     ::= { docsPnmCmDsHistEntry 3 }

docsPnmCmDsHistFileName OBJECT-TYPE
     SYNTAX      SnmpAdminString
     MAX-ACCESS  read-write
     STATUS      current
     DESCRIPTION
        "This object is the name of the file at the CM which is to be
        transferred to the PNM server. The data is stored as 32 bit integers
        for the hit and dwell count values.

        This value can only be changed while a test is not in progress. An
        attempt to set this value while the value of 'docsPnmCmDsHistMeasStatus'
        is 'busy' will return 'inconsistentValue'.

        If the value of this object is the DEFVAL (empty string), then a
        default filename value will be used. Otherwise the value set will be
        used as the filename. If a default filename is generated, then
        that value will be returned in this object and will represent
        the filename that was used for the test. All subsequent tests
        should set this object to a meaningful value or to an
        'empty string' value (to generate a new default filename)
        before starting a new test.

        If a default filename value is used, it is generated as the test name
        plus the CM MAC Address plus the 'epoch time'. The epoch time (also known
        as 'unix time') is defined as the number of seconds that have elapsed
        since midnight Coordinated Universal Time (UTC),Thursday, 1 January 1970.
        Hence, the format would be:

            PNMHist_<CM MAC address>_<epoch>

        For example:  PNMHist_0010181A2D11_1403405123

        The data file is comprised of a header plus the Histogram Data. The header
        is comprised of ordered fixed-length fields. Unless otherwise specified,
        the header fields contain hex values that are right-justified within the
        field. If necessary the field is left-padded with zero values.

        The file type is either '504E4D05' or '504E4E05' (with Versioning)"
     REFERENCE
         "Information Model Mapping: CM-SP-CM-OSSI    
          CmDsHist::FileName"
         DEFVAL { "" }
     ::= { docsPnmCmDsHistEntry 4 }

-- ---------------------------------------------------------------------
-- The Upstream Pre Equalizer Coefficients Table
-- ---------------------------------------------------------------------
docsPnmCmUsPreEqTable OBJECT-TYPE
     SYNTAX      SEQUENCE OF DocsPnmCmUsPreEqEntry
     MAX-ACCESS  not-accessible
     STATUS      current
     DESCRIPTION
        "This object provides access to CM upstream pre-equalizer coefficients.
        The CM pre-equalizer coefficients and the CMTS upstream adaptive
        equalizer coefficient update values, when taken together describe the
        linear response of the upstream cable plant for a given CM. During the
        ranging process, the CMTS computes adaptive equalizer coefficients based
        on upstream probes; these coefficients describe the residual channel
        remaining after any pre-equalization. The CMTS sends these equalizer
        coefficients to the CM as a set of Transmit Equalization Adjust
        coefficients as part of the ranging process.

        The CM Pre-Equalizer coefficients are expressed as 16 bit two's
        complement numbers using s2.13 format. The power averaged over all
        coefficients approximately 1, in order to avoid excessive clipping and
        quantization noise. The Pre-Equalizer coefficient update values sent to
        the CM by the CMTS in the RNG-RSP are expressed as 16 bit two's
        complement numbers using s1.14 format.

        The CM provides the capability to report its upstream pre-equalizer
        coefficients (full set or summary) upon request. The CM also provides
        the capability to also report the most recent set of Transmit
        Equalization Adjust coefficients which were applied to produce the
        reported set of upstream pre-equalizer coefficients. The CM indicates
        the status of the most recent Transmit Equalization Adjust coefficients
        sent to it by the CMTS. If the CM was able to apply the coefficients it
        sets the status to success(2). If the CM was unable to fully apply the
        adjustments (for example, due to excess tilt or ripple in the channel),
        and it was necessary for the CM to clip the coefficients, it sets the
        status to clipped(3). If the CM modified the coefficients other than by
        simply clipping them, it sets the status to other(1). If for
        some reason the CM is unable to apply the adjustments at all, it sets
        the status to rejected(4).

        The 'docsPnmCmUsPreEqFileEnable' object is used to create files. Other
        objects are updated as read.

        This table will have a row for each ifIndex for the modem."
    REFERENCE
         "Information Model Mapping: CM-SP-CM-OSSI    
          CmUsPreEq"
     ::= { docsPnmCmObjects 10}

docsPnmCmUsPreEqEntry OBJECT-TYPE
     SYNTAX      DocsPnmCmUsPreEqEntry
     MAX-ACCESS  not-accessible
     STATUS      current
     DESCRIPTION
         "The conceptual row of the docsPnmCmUsPreEqTable. An instance
         is dynamically created and exists for an associated ifIndex upon
         which the test defined by this table can take place.

         The conceptual rows do not persist across device resets."
     INDEX { ifIndex }
     ::= { docsPnmCmUsPreEqTable 1 }

DocsPnmCmUsPreEqEntry ::=
    SEQUENCE {
        docsPnmCmUsPreEqFileEnable               TruthValue,
        docsPnmCmUsPreEqAmpRipplePkToPk          ThousandthdB,
        docsPnmCmUsPreEqAmpRippleRms             ThousandthdB,
        docsPnmCmUsPreEqAmpSlope                 Integer32,
        docsPnmCmUsPreEqGrpDelayRipplePkToPk     Unsigned32,
        docsPnmCmUsPreEqGrpDelayRippleRms        Unsigned32,
        docsPnmCmUsPreEqPreEqCoAdjStatus         INTEGER,
        docsPnmCmUsPreEqMeasStatus               MeasStatusType,
        docsPnmCmUsPreEqLastUpdateFileName       SnmpAdminString,
        docsPnmCmUsPreEqFileName                 SnmpAdminString,
        docsPnmCmUsPreEqAmpMean                  ThousandthdB,
        docsPnmCmUsPreEqGrpDelaySlope            Integer32,
        docsPnmCmUsPreEqGrpDelayMean             Integer32
     }

docsPnmCmUsPreEqFileEnable OBJECT-TYPE
     SYNTAX      TruthValue
     MAX-ACCESS  read-write
     STATUS      current
     DESCRIPTION
        "This object causes the files defined by the 'docsPnmCmUsPreEqFileName' and
        the 'docsPnmCmUsPreEqlastUpdateFileName' objects to be created. The files,
        once created, are available via the 'docsPnmBulkFileTable' mechanism.
        The 'docsPnmCmUsPreEqMeasStatus' object can be checked to determine the
        outcome of setting this object.

        Interaction with other table rows:

        - This object is subject to the rules specified by the
        'docsPnmCmCtlStatus' object. Therefore this object returns
        'inconsistentValue' if set to 'true' while the value of
        'docsPnmCmCtlStatus' is any value other than 'ready'.

        - Setting this value to 'true' will change the value of the
        'docsPnmCmUsPreEqMeasStatus' to 'busy' while the file generation is in
        progress.

        - This object returns 'inconsistentValue' if set to 'true' while the
        CM is in DOCSIS Light Sleep (DLS) mode or the CM is in battery-backup mode.

        - Default values for 'docsPnmCmUsPreEqFileName' and
        'docsPnmCmUsPreEqLastUpdateFileName' are defined; thus, this object may be set
        to 'true' without explicitly setting these values.

        - This object returns 'true' if the CM is actively generating the files.
        Otherwise it returns 'false'."
     REFERENCE
         "Information Model Mapping: CM-SP-CM-OSSI    
          CmUsPreEq::FileEnable"
     DEFVAL { false }
     ::= { docsPnmCmUsPreEqEntry 1 }

docsPnmCmUsPreEqAmpRipplePkToPk OBJECT-TYPE
     SYNTAX      ThousandthdB
     UNITS       "dB"
     MAX-ACCESS  read-only
     STATUS      current
     DESCRIPTION
        "This attribute represents the value of the peak to peak ripple in the
        magnitude of the equalizer coefficients. This attribute represents the
        ripple across the entire OFDMA channel. This attribute is not stored in
        the data files.

        Note: An algorithm for calculating the ripple and slope for these
        measurements is provided in section D.3 of the DOCSIS 3.1 CM
        OSSI Specification."
     REFERENCE
         "Information Model Mapping: CM-SP-CM-OSSI    
          CmUsPreEq::AmplitudeRipplePkToPk"
     ::= { docsPnmCmUsPreEqEntry 2 }

docsPnmCmUsPreEqAmpRippleRms OBJECT-TYPE
     SYNTAX      ThousandthdB
     UNITS       "dB"
     MAX-ACCESS  read-only
     STATUS      current
     DESCRIPTION
        "This attribute represents the value of the RMS ripple in the magnitude
        of the equalizer coefficients. This attribute represents the ripple
        across the entire OFDMA channel. This attribute is not stored in the
        data files.

        Note: An algorithm for calculating the ripple and slope for these
        measurements is provided in section D.3 of the DOCSIS 3.1 CM
        OSSI Specification."
     REFERENCE
         "Information Model Mapping: CM-SP-CM-OSSI    
          CmUsPreEq::AmplitudeRippleRMS"
     ::= { docsPnmCmUsPreEqEntry 3 }

docsPnmCmUsPreEqAmpSlope OBJECT-TYPE
     SYNTAX      Integer32
     UNITS       "ThousandthdB/MHz"
     MAX-ACCESS  read-only
     STATUS      current
     DESCRIPTION
        "This attribute represents the slope in 0.001 dB per MHz in the
        magnitude of the equalizer coefficients. This attribute
        represents the slope across the entire OFDMA channel. This
        attribute is not stored in the data files.

        Note: An algorithm for calculating the ripple and slope for these
        measurements is provided in section D.3 of the DOCSIS 3.1 CM
        OSSI Specification."
     REFERENCE
         "Information Model Mapping: CM-SP-CM-OSSI    
          CmUsPreEq::AmplitudeSlope"
     ::= { docsPnmCmUsPreEqEntry 4 }

docsPnmCmUsPreEqGrpDelayRipplePkToPk OBJECT-TYPE
     SYNTAX      Unsigned32
     UNITS       "nsec"
     MAX-ACCESS  read-only
     STATUS      current
     DESCRIPTION
        "This attribute represents the peak-to-peak Group Delay Ripple
        expressed in units of 0.001 nsec. This attribute represents the
        group delay variation across the entire OFDMA channel. This
        attribute is not stored in the data files.
        The slope component calculated for the GroupDelaySlope is
        subtracted from the frequency domain data and the peak-to-peak
        ripple is calculated from the resultant data."
     REFERENCE
         "Information Model Mapping: CM-SP-CM-OSSI    
          CmUsPreEq::GroupDelayRipplePkToPk"
     ::= { docsPnmCmUsPreEqEntry 5 }

docsPnmCmUsPreEqGrpDelayRippleRms OBJECT-TYPE
     SYNTAX      Unsigned32
     UNITS       "nsec"
     MAX-ACCESS  read-only
     STATUS      current
     DESCRIPTION
        "This attribute represents the RMS value of the Group Delay
         Ripple expressed in units of 0.001 nsec. This attribute
         represents the group delay variation across the entire OFDMA
         channel. The slope component calculated for the GroupDelaySlope
         is subtracted from the frequency domain data and the RMS ripple
         is calculated from the resultant dataThis attribute is not
         stored in the data files. "
     REFERENCE
         "Information Model Mapping: CM-SP-CM-OSSI    
          CmUsPreEq::GroupDelayRippleRms"
     ::= { docsPnmCmUsPreEqEntry 6 }

docsPnmCmUsPreEqPreEqCoAdjStatus OBJECT-TYPE
     SYNTAX      INTEGER {other(1),
                          success(2),
                          clipped(3),
                          rejected(4)
                         }
     MAX-ACCESS  read-only
     STATUS      current
     DESCRIPTION
        "This object represents whether the last set of Pre-Equalization
        coefficient adjustments that were fully applied or were only partially
        applied due to excessive ripple or tilt in the Pre-Equalization
        coefficient values. "
     REFERENCE
         "Information Model Mapping: CM-SP-CM-OSSI    
          CmUsPreEq::PreEqCoAdjStatus"
     ::= { docsPnmCmUsPreEqEntry 7 }

docsPnmCmUsPreEqMeasStatus OBJECT-TYPE
     SYNTAX      MeasStatusType
     MAX-ACCESS  read-only
     STATUS      current
     DESCRIPTION
        "This attribute is used to determine the status of the measurement.
        The PNM server will query this value to determine when the file
        is ready for transfer.
        Summary Metrics: These values are not calculated unless a specific
        query of any of the summary metrics has been performed. "
     REFERENCE
         "Information Model Mapping: CM-SP-CM-OSSI    
          CmUsPreEq::MeasStatus"
     ::= { docsPnmCmUsPreEqEntry 8 }

docsPnmCmUsPreEqLastUpdateFileName OBJECT-TYPE
     SYNTAX      SnmpAdminString
     MAX-ACCESS  read-write
     STATUS      current
     DESCRIPTION
        "This attribute is the name of the file at the CM which is to be
        transferred to the PNM server. The data represents the values sent
        to the CM by the CMTS in the last RNG-RSP that contained
        Pre-Equalization updates and is stored as 16 bit integers for the I
        and Q data.

        This object cannot be changed while a file generation is in progress.
        It will return a value of 'inconsistentValue' if set while the value of
        'docsPnmCmUsPreEqMeasStatus' is set to a value of 'busy'.

        If the value of this object is the DEFVAL (empty string), then a default
        filename value will be used. Otherwise the value set will be used as
        the filename. If a default filename is generated, then that
        value will be returned in this object and will represent the
        filename that was used for the test. All subsequent tests should
        set this object to a meaningful value or to an 'empty string'
        value (to generate a new default filename) before starting a
        new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMUsPreEqLastUpdate_<CM MAC address>_<epoch>

        For example:  PNMUsPreEqLastUpdate_0010181A2D11_1403405123

        The data file is comprised of a header plus the Pre-EQ Data.
        The header is composed of ordered fixed-length fields. Unless
        otherwise specified, the header fields contain hex values that are
        right-justified within the field. If necessary the field is left-padded
        with zero values.

        The file type is either '504E4D07' or '504E4E07' (with Versioning)"
     REFERENCE
         "Information Model Mapping: CM-SP-CM-OSSI    
          CmUsPreEq::LastUpdateFileName"
     DEFVAL { "" }
     ::= { docsPnmCmUsPreEqEntry 9 }

docsPnmCmUsPreEqFileName OBJECT-TYPE
     SYNTAX      SnmpAdminString
     MAX-ACCESS  read-write
     STATUS      current
     DESCRIPTION
        "This attribute is the name of the file at the CM which is to be
        transferred to the PNM server. The data represents the current value of
        the Pre-Equalization values for all of the active subcarriers and is
        stored as 16 bit integers for the I and Q data.

        This object cannot be changed while a file generation is in progress.
        It will return a value of 'inconsistentValue' if set while the value of
        'docsPnmCmUsPreEqMeasStatus' is set to a value of 'busy'.

        If the value of this object is the DEFVAL (empty string), then a default
        filename value will be used. Otherwise the value set will be used as
        the filename. If a default filename is generated, then that
        value will be returned in this object and will represent the
        filename that was used for the test. All subsequent tests should
        set this object to a meaningful value or to an 'empty string'
        value (to generate a new default filename) before starting
        a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMUsPreEq_<CM MAC address>_<epoch>

        For example:  PNMUsPreEq_0010181A2D11_1403405123

        The data file is comprised of a header plus the Pre-EQ Data
        The header is comprised of ordered fixed-length fields. Unless
        otherwise specified, the header fields contain hex values that are
        right-justified within the field. If necessary the field is left-padded
        with zero values.

        The file type is either '504E4D06' or '504E4E06' (with Versioning)"
     REFERENCE
         "Information Model Mapping: CM-SP-CM-OSSI    
          CmUsPreEq::FileName"
     DEFVAL { "" }
     ::= { docsPnmCmUsPreEqEntry 10 }

docsPnmCmUsPreEqAmpMean OBJECT-TYPE
     SYNTAX      ThousandthdB
     UNITS       "dB"
     MAX-ACCESS  read-only
     STATUS      current
     DESCRIPTION
        "This attribute represents the mean in 0.001 dB, of the
        magnitude of the equalizer coefficients.

        Note: An algorithm for calculating the ripple and slope for these
        measurements is provided in section D.3 of the DOCSIS 3.1 CM
        OSSI Specification."
     REFERENCE
         "Information Model Mapping: CM-SP-CM-OSSI    
          CmUsPreEq::AmplitudeMean"
     ::= { docsPnmCmUsPreEqEntry 11 }

docsPnmCmUsPreEqGrpDelaySlope OBJECT-TYPE
     SYNTAX      Integer32
     UNITS       "ThousandthNsec/MHz"
     MAX-ACCESS  read-only
     STATUS      current
     DESCRIPTION
        "This attribute represents the slope in 0.001 nsec per MHz in
        the group delay of the equalizer coefficients. This attribute
        represents the slope across the entire OFDM channel.

        Note: An algorithm for calculating the ripple and slope for these
        measurements is provided in section D.3 of the DOCSIS 3.1 CM
        OSSI Specification."
     REFERENCE
         "Information Model Mapping: CM-SP-CM-OSSI    
          CmUsPreEq::GroupDelaySlope"
     ::= { docsPnmCmUsPreEqEntry 12 }

docsPnmCmUsPreEqGrpDelayMean OBJECT-TYPE
     SYNTAX      Integer32
     UNITS       "ThousandthNsec"
     MAX-ACCESS  read-only
     STATUS      current
     DESCRIPTION
        "This attribute represents the mean of the group delay in units
         of 0.001 nsec."
     REFERENCE
         "Information Model Mapping: CM-SP-CM-OSSI    
          CmUsPreEq::GroupDelayMean"
     ::= { docsPnmCmUsPreEqEntry 13 }

-- ---------------------------------------------------------------------
-- The CM Downstream OFDM Modulation Profile
-- ---------------------------------------------------------------------
docsPnmCmDsOfdmModProfTable OBJECT-TYPE
     SYNTAX      SEQUENCE OF DocsPnmCmDsOfdmModProfEntry
     MAX-ACCESS  not-accessible
     STATUS      current
     DESCRIPTION
        "The purpose of the table is to provide the per subcarrier bit load
        of the modulation profiles.

        This table will have a row for each ifIndex for the modem."
     REFERENCE
         "Information Model Mapping: CM-SP-CM-OSSI    
          CmDsOfdmModulationProfile"
     ::= { docsPnmCmObjects 11}

docsPnmCmDsOfdmModProfEntry OBJECT-TYPE
     SYNTAX      DocsPnmCmDsOfdmModProfEntry
     MAX-ACCESS  not-accessible
     STATUS      current
     DESCRIPTION
         "The conceptual row of the docsPnmCmDsOfdmModProfTable. An instance
         is dynamically created and exists for an associated ifIndex upon
         which the test defined by this table can take place.

         The conceptual rows do not persist across device resets."
     INDEX { ifIndex }
     ::= { docsPnmCmDsOfdmModProfTable 1 }

DocsPnmCmDsOfdmModProfEntry ::=
    SEQUENCE {
        docsPnmCmDsOfdmModProfFileEnable      TruthValue,
        docsPnmCmDsOfdmModProfMeasStatus      MeasStatusType,
        docsPnmCmDsOfdmModProfFileName        SnmpAdminString
     }

docsPnmCmDsOfdmModProfFileEnable OBJECT-TYPE
     SYNTAX      TruthValue
     MAX-ACCESS  read-write
     STATUS      current
     DESCRIPTION
        "When this attribute is set to 'true' the CM must begin the Modulation
        Profile Summary report. While the report is in progress, the CM must
        return a MeasStatus value of 'busy'. When the measurement is complete
        the CM must set the FileEnable attribute to 'false'. If this attribute
        is set to 'false' during a report, the CM must stop the report.

        Interaction with other table rows:

        - This object returns 'inconsistentValue' if set to 'true' while the
        CM is in DOCSIS Light Sleep (DLS) mode or the CM is in battery-backup mode.

        - A default value for 'docsPnmCmDsOfdmModProfFileName' is defined; thus,
        this object may be set to 'true' without explicitly setting this value.

        - Setting this object to a value of 'true' will change the value of the
        'docsPnmCmDsOfdmModProfMeasStatus' to 'busy'.

        The CM must return the value of 'true' if it is actively compiling the
        report; otherwise it must return 'false'."
     REFERENCE
         "Information Model Mapping: CM-SP-CM-OSSI    
          CmDsOfdmModulationProfile::FileEnable"
     DEFVAL { false }
     ::= { docsPnmCmDsOfdmModProfEntry 1 }

docsPnmCmDsOfdmModProfMeasStatus OBJECT-TYPE
     SYNTAX      MeasStatusType
     MAX-ACCESS  read-only
     STATUS      current
     DESCRIPTION
        "This attribute is used to determine the status of the measurement.
        The PNM server will query this value to determine when the file
        is ready for transfer."
     REFERENCE
         "Information Model Mapping: CM-SP-CM-OSSI    
          CmDsOfdmModulationProfile::MeasStatus"
     ::= { docsPnmCmDsOfdmModProfEntry 2 }

docsPnmCmDsOfdmModProfFileName OBJECT-TYPE
     SYNTAX      SnmpAdminString
     MAX-ACCESS  read-write
     STATUS      current
     DESCRIPTION
        "This attribute is the name of the file at the CM which is to be
        transferred to the PNM server.

        This value can only be changed while a test is not in progress. An attempt
        to set this value while the value of 'docsPnmCmDsOfdmModProfMeasStatus' is
        'busy' will return 'inconsistentValue'.

        If the value of this object is the DEFVAL (empty string), then a default
        filename value will be used. Otherwise the value set will be used as
        the filename. If a default filename is generated, then that value
        will be returned in this object and will represent the filename
        that was used for the test. All subsequent tests should set this
        object to a meaningful value or to an 'empty string' value
        (to generate a new default filename) before starting a new test.

        If a default filename value is used, it is generated as the test name
        plus the CM MAC Address plus the 'epoch time'. The epoch time (also known
        as 'unix time') is defined as the number of seconds that have elapsed
        since midnight Coordinated Universal Time (UTC), Thursday, 1 January 1970.
        Hence, the format would be:

            PNMModProfile_<CM MAC address>_<epoch>

        For example:  PNMModProfile_0010181A2D11_1403405123

        The data file is comprised of a header plus the Modulation Profile Data.
        The header is comprised of ordered fixed-length fields. Unless
        otherwise specified, the header fields contain hex values that are
        right-justified within the field. If necessary the field is left-padded
        with zero values.
        The file type is either '504E4D0A' or '504E4E0A' (with Versioning)"
     REFERENCE
         "Information Model Mapping: CM-SP-CM-OSSI    
          CmDsOfdmModulationProfile::FileName"
     DEFVAL { "" }
     ::= { docsPnmCmDsOfdmModProfEntry 3 }


--
-- DOCS-IF3-MIB extension
--
-- This section of objects extends the Spectrum Analyzer objects that are
-- defined in the DOCS-IF-MIB. These objects allow the Spectrum Analyzer Test
-- function to take advantage of the bulk-data collection mechanism and the
-- docsPnmCmCtlStatus objects defined by this MIB.
--
-- FileName, FileEnable, and MeasStatus objects are added to the
-- 'docsIf3CmSpectrumAnalysisCtrlCmd' set of attributes from the IF3 MIB.
-- Additionally, since this MIB adds the 'dsSpectrumAnalyzer' enumeration to
-- the 'docsnmCmCtlTest' object, it is expected that any Spectrum Analyzer Test
-- (defined here or by the DOCS-IF3-MIB, will now be controlled by the
-- 'docsPnmCmCtlStatus' object. This serves to limit the ability of the CM to run
-- only one test at a time.


-- ---------------------------------------------------------------------
-- The CM Spectrum Analysis Extension Objects
-- ---------------------------------------------------------------------

docsIf3CmSpectrumAnalysisCtrlCmdFileEnable OBJECT-TYPE
     SYNTAX      TruthValue
     MAX-ACCESS  read-write
     STATUS      current
     DESCRIPTION
        "This attribute, when set to 'true', causes the CM to begin a Spectrum
        Analysis measurement with the parameters defined by the
        docsIf3CmSpectrumAnalysisCtrlCmd set of attributes. In order to set
        this object to 'true', the Enable must already be set to 'true'.

        When the measurement is completed successfully, a file is generated
        and is made available for transfer and the MeasStatus attribute is set to
        'sampleReady'. The file will contain one complete snapshot of the spectrum
         data.

        Setting this object to a value of 'false' instructs the CM to stop
        the measurement.

        Interaction with other table rows:

         - This object is subject to the rules specified by the
        'docsPnmCmCtlStatus' object. Therefore this object returns
        'inconsistentValue' if set to 'true' while the value of
        'docsPnmCmCtlStatus' is any value other than 'ready'.

        - This object returns 'inconsistentValue' if set to 'true' while the
        CM is unable to perform a spectrum measurement for any reason. Examples
        might include DOCSIS Light Sleep (DLS) mode or battery-backup mode.

       - A default value for 'docsIf31CmSpectrumAnalysisCtrlCmdFileName' is defined;
        thus, this object may be set to 'true' without explicitly setting this value.

        - Setting this object to a value of 'true' will change the value of the
        'docsIf31CmSpectrumAnalysisCtrlCmdMeasStatus' to 'busy'. After completion,
        'docsIf31CmSpectrumAnalysisCtrlCmdMeasStatus' will be changed to reflect
        the status of the test.

        -This object will return a value of 'true' if it is actively taking a
        measurement; otherwise it returns 'false'."
     REFERENCE
         "Information Model Mapping: CM-SP-CM-OSSI    
          CmSpectrumAnalysisCtrlCmd::FileEnable"
     DEFVAL { false }
     ::= { docsIf3CmSpectrumAnalysisCtrlCmd 10 }

docsIf3CmSpectrumAnalysisCtrlCmdMeasStatus OBJECT-TYPE
     SYNTAX      MeasStatusType
     MAX-ACCESS  read-only
     STATUS      current
     DESCRIPTION
        "This attribute is used to determine the status of the measurement.
        An application server will query this value to determine when the file
        is ready for transfer. "
    REFERENCE
         "Information Model Mapping: CM-SP-CM-OSSI    
          CmSpectrumAnalysisCtrlCmd::MeasStatus"
     ::= { docsIf3CmSpectrumAnalysisCtrlCmd 11 }

docsIf3CmSpectrumAnalysisCtrlCmdFileName OBJECT-TYPE
     SYNTAX      SnmpAdminString
     MAX-ACCESS  read-write
     STATUS      current
     DESCRIPTION
        "This attribute is the name of the file containing the spectrum
        analysis data.

        This value can only be changed while a test is not in progress.
        An attempt to set this value while the value of MeasStatus is
        'busy' will return 'inconsistentValue'.

        If the value of this object is the DEFVAL (empty string), then
        a default filename value will be used. Otherwise, the value set
        will be used as the filename. If a default filename is
        generated, then that value will be returned in this object and
        will represent the filename that was used for the test. All
        subsequent tests should set this object to a meaningful value
        or to an 'empty string' value (to generate a new default
        filename) before starting a new test.

        If a default filename value is used, it is generated as the test
        name plus the CM MAC Address plus the 'epoch time'. The epoch
        time (also known as 'unix time') is defined as the number of
        seconds that have elapsed since midnight Coordinated Universal
        Time (UTC), Thursday, 1 January 1970.
        Hence, the format would be:
        PNMSpecAnData_<CM MAC address>_<epoch>

        For example: PNMSpecAnData_0010181A2D11_1403405123

        The data file is comprised of a header plus the Spectrum Analysis
        Data.
        The header is comprised of ordered fixed-length fields. Unless
        otherwise specified, the header fields contain hex values that are
        right-justified within the field. If necessary the field is left-padded
        with zero values.

        The file type is either '504E4D09' or '504E4E09' (with Versioning)


        If the size of the data the CM is commanded to collect would exceed the
        maximum file-size limit of the data collection mechanism, the CM will
        limit the file size accordingly and set the 'MeasStatus' attribute to a
        value of 'sampleTruncated'. If this occurs, the file will contain valid
        data, from the beginning of the capture, but will represent fewer bins
        than configured for the measurement.
        "
    REFERENCE
         "Information Model Mapping: CM-SP-CM-OSSI    
          CmSpectrumAnalysisCtrlCmd::FileName"
     DEFVAL { "" }
     ::= { docsIf3CmSpectrumAnalysisCtrlCmd 12 }

-- ---------------------------------------------------------------------
-- CMTS PNM Objects
-- ---------------------------------------------------------------------

-- ---------------------------------------------------------------------
-- CMTS Downstream PNM Objects
-- ---------------------------------------------------------------------

-- ---------------------------------------------------------------------
-- The CMTS Symbol Capture
-- ---------------------------------------------------------------------
docsPnmCmtsDsOfdmSymCapTable OBJECT-TYPE
     SYNTAX      SEQUENCE OF DocsPnmCmtsDsOfdmSymCapEntry
     MAX-ACCESS  not-accessible
     STATUS      current
     DESCRIPTION
       "Downstream OFDM Symbol Capture is a PNM Test described in [PHYv3.1] 
        Downstream Symbol Capture section. The CmtsDsOfdmSymCapTable defines 
        the management interface for the operator to configure, execute, 
        and monitor the Downstream OFDM Symbol Capture test.
        
        The CmtsDsOfdmSymCapTable provides partial
        functionality of a network analyzer to analyze the response of the
        cable plant.

        At the CMTS, the transmitted frequency-domain modulation values of one
        full OFDM symbol before the IFFT are captured and made available for
        analysis. The frequency domain samples are expressed as 16-bit two's
        complement numbers using s3.12 format. This includes the I and Q
        modulation values of all subcarriers in the active bandwidth of the
        OFDM channel, including data subcarriers, pilots, PLC preamble symbols
        and excluded subcarriers. This capture will result in a number of
        samples that depends on the OFDM channel width.

        As examples, for 50 kHz subcarrier spacing in a 192 MHz channel with 204.8
        MHz sampling rate, 3800 samples will be captured; for 25 kHz subcarrier
        spacing in a 192 MHz channel with 204.8 MHz sampling rate, 7600 samples
        will be captured; for 50 kHz subcarrier spacing in a 24 MHz channel with
        a reduced sampling rate of 25.6 MHz, 475 samples would be captured. Note:
        Excluded subcarriers in the guard band on either side of the encompassed
        spectrum are not captured.

        Capturing the input and output of the cable plant
        is equivalent to a wideband sweep of the channel, which permits full
        characterization of the linear and nonlinear response of the downstream
        plant. The MAC provides signaling via the PLC Trigger Message to ensure
        that the same symbol is captured at the CMTS and CM.

        The Downstream Symbol Capture is controlled by setting the
        'docsPnmCmtsDsOfdmSymTrigEnable' object. The status of the capture is
        obtained by reading the value of the 'docsPnmCmDsOfdmSymMeasStatus'
        object.
        
        The CCAP should create a row in this table for each ifIndex of a 
        downstream channel.
        The CCAP MAY support simultaneous Downstream Symbol Capture tests on more 
        than one OFDM channel at a time.
        The CCAP should reject configuring a value for the DestinationIndex
        of the DsOfdmSymbolCapture object if that value does not exist in 
        the corresponding DestinationIndex attribute of the DataTransferCfg instance."
     REFERENCE 
        "Information Model Mapping: CM-SP-CCAP-OSSI 
         DsOfdmSymbolCapture"
     ::= { docsPnmCmtsObjects 1}

docsPnmCmtsDsOfdmSymCapEntry OBJECT-TYPE
     SYNTAX      DocsPnmCmtsDsOfdmSymCapEntry
     MAX-ACCESS  not-accessible
     STATUS      current
     DESCRIPTION
         "The conceptual row of the 'docsPnmCmtsDsOfdmSymCapTable'. An instance
         is dynamically created and exists for an associated ifIndex of the
         physical downstream channel upon which the test defined by this table
         can take place.

         The conceptual rows do not persist across device resets. "
     INDEX { ifIndex  }
     ::= { docsPnmCmtsDsOfdmSymCapTable 1 }

DocsPnmCmtsDsOfdmSymCapEntry ::=
    SEQUENCE {
        docsPnmCmtsDsOfdmSymTrigEnable            TruthValue,
        docsPnmCmtsDsOfdmSymTrigGroupId           Unsigned32,
        docsPnmCmtsDsOfdmSymFirstActSubCarIdx     Unsigned32,
        docsPnmCmtsDsOfdmSymLastActSubCarIdx      Unsigned32,
        docsPnmCmtsDsOfdmSymRxWindowing           TruthValue,
        docsPnmCmtsDsOfdmSymTransactionId         Unsigned32,
        docsPnmCmtsDsOfdmSymSampleRate            Unsigned32,
        docsPnmCmtsDsOfdmSymFftLength             Unsigned32,
        docsPnmCmtsDsOfdmSymMeasStatus            MeasStatusType,
        docsPnmCmtsDsOfdmSymCaptFileName          SnmpAdminString,
        docsPnmCmtsDsOfdmSymDestinationIndex      Unsigned32
     }

docsPnmCmtsDsOfdmSymTrigEnable OBJECT-TYPE
     SYNTAX      TruthValue
     MAX-ACCESS  read-write
     STATUS      current
     DESCRIPTION
        "Setting this object to a value of 'true' instructs the CMTS to insert
        a Trigger Message Block in the PLC with a Group ID matching the CM's
        TriggerGroupID. The CMTS captures the Symbol that it designated in the
        Trigger Message Block. The TriggerEnable is a one-shot enable and the
        attribute is disabled when the CMTS has completed the acquisition of
        the designated Symbol.

        Interaction with other table rows:

        - This object returns 'inconsistentValue' if set to 'true' while the
        value of 'docsPnmCmtsDsOfdmSymTrigMeasStatus' is a value of 'busy' for
        this row OR for any row in the table. That is, ONLY ONE ROW IN THE TABLE
        MAY BE ALLOWED TO BE 'true' AT THE SAME TIME.

        - Default values for 'docsPnmCmtsDsOfdmSymCaptFileName',
        and 'docsPnmCmtsDsOfdmSymTrigGroupId' objects are defined; thus, this
        object may be set to 'true' without explicitly setting these values.
        Care should be taken to insure these values are correct for the desired
        test case.

        - Setting this object to a value of 'true' will change the value of the
        'docsPnmCmtsDsOfdmSymTrigMeasStatus' to 'busy'. "
     REFERENCE 
        "Information Model Mapping: CM-SP-CCAP-OSSI 
         DsOfdmSymbolCapture::TriggerEnable"
     DEFVAL { false }
     ::= { docsPnmCmtsDsOfdmSymCapEntry 1 }

docsPnmCmtsDsOfdmSymTrigGroupId OBJECT-TYPE
     SYNTAX      Unsigned32 (0..65535)
     MAX-ACCESS  read-write
     STATUS      current
     DESCRIPTION
        "This attribute is used by the CMTS to be inserted in the PLC Trigger
        Message Block to identify a CM or a group of CMs expected to perform
        Symbol Capture measurements for the designated symbol.

        This value can only be changed while a test is not in progress. An attempt
        to set this value while the value of 'docsPnmCmtsDsOfdmSymMeasStatus' is
        'busy' will return 'inconsistentValue'."
     REFERENCE 
        "Information Model Mapping: CM-SP-CCAP-OSSI 
         DsOfdmSymbolCapture::TriggerGroupId"
     DEFVAL { 0 }
     ::= { docsPnmCmtsDsOfdmSymCapEntry 2 }

docsPnmCmtsDsOfdmSymFirstActSubCarIdx OBJECT-TYPE
     SYNTAX      Unsigned32 (0..65535)
     MAX-ACCESS  read-only
     STATUS      current
     DESCRIPTION
        "This object is used to denote the subcarrier index of the lowest
        frequency of the Encompassed Spectrum for the OFDM channel. "
     REFERENCE 
        "Information Model Mapping: CM-SP-CCAP-OSSI 
         DsOfdmSymbolCapture::FirstActiveSubcarrierIndex"
     ::= { docsPnmCmtsDsOfdmSymCapEntry 3 }

docsPnmCmtsDsOfdmSymLastActSubCarIdx OBJECT-TYPE
     SYNTAX      Unsigned32 (0..65535)
     MAX-ACCESS  read-only
     STATUS      current
     DESCRIPTION
        "This object is used to denote the subcarrier index of the highest
        frequency of the Encompassed Spectrum for the OFDM channel."
     REFERENCE 
        "Information Model Mapping: CM-SP-CCAP-OSSI 
         DsOfdmSymbolCapture::LastActiveSubcarrierIndex"
     ::= { docsPnmCmtsDsOfdmSymCapEntry 4 }

docsPnmCmtsDsOfdmSymRxWindowing OBJECT-TYPE
     SYNTAX      TruthValue
     MAX-ACCESS  read-only
     STATUS      current
     DESCRIPTION
        "This attribute is a flag indicating if vendor proprietary
        windowing was enabled during the capture. "
     REFERENCE 
        "Information Model Mapping: CM-SP-CCAP-OSSI 
         DsOfdmSymbolCapture::RxWindowing"
     ::= { docsPnmCmtsDsOfdmSymCapEntry 5 }

docsPnmCmtsDsOfdmSymTransactionId OBJECT-TYPE
     SYNTAX      Unsigned32 (0..255)
     MAX-ACCESS  read-only
     STATUS      current
     DESCRIPTION
        "This attribute is the Transaction ID sent by the CMTS in the Trigger
        Message Block. Prior to completion of a measurement this attribute has
        no meaning. "
     REFERENCE 
        "Information Model Mapping: CM-SP-CCAP-OSSI 
         DsOfdmSymbolCapture::TransactionId"
     ::= { docsPnmCmtsDsOfdmSymCapEntry 6 }

docsPnmCmtsDsOfdmSymSampleRate OBJECT-TYPE
     SYNTAX      Unsigned32
     UNITS       "Hz"
     MAX-ACCESS  read-only
     STATUS      current
     DESCRIPTION
        "This attribute is the FFT sample rate in use by the CM for the
        channel; typically the sample rate for the downstream channel will
        be 204.8MHz."
     REFERENCE 
        "Information Model Mapping: CM-SP-CCAP-OSSI 
         DsOfdmSymbolCapture::SampleRate"
     ::= { docsPnmCmtsDsOfdmSymCapEntry 7 }

docsPnmCmtsDsOfdmSymFftLength OBJECT-TYPE
     SYNTAX      Unsigned32 (512  | 1024 | 2048 |4096 | 8192)
     MAX-ACCESS  read-only
     STATUS      current
     DESCRIPTION
        "This attribute is the FFT length in use by the CM for the channel;
        typically this value is 4096 or 8192 for the Downstream Channel. "
     REFERENCE 
        "Information Model Mapping: CM-SP-CCAP-OSSI 
         DsOfdmSymbolCapture::FftLength"
     ::= { docsPnmCmtsDsOfdmSymCapEntry 8 }

docsPnmCmtsDsOfdmSymMeasStatus OBJECT-TYPE
     SYNTAX      MeasStatusType
     MAX-ACCESS  read-only
     STATUS      current
     DESCRIPTION
        "This attribute is used to determine the status of the measurement.
        The PNM server will query this value to determine when the measurement
        is complete."
     REFERENCE 
        "Information Model Mapping: CM-SP-CCAP-OSSI 
         DsOfdmSymbolCapture::MeasStatus"
     ::= { docsPnmCmtsDsOfdmSymCapEntry 9 }

docsPnmCmtsDsOfdmSymCaptFileName OBJECT-TYPE
     SYNTAX      SnmpAdminString
     MAX-ACCESS  read-write
     STATUS      current
     DESCRIPTION
        "This attribute is the name of the file with the captured symbol data at
        the CMTS that is to be downloaded using TFTP by the PNM server.

        This value can only be changed while a test is not in progress. An attempt
        to set this value while the value of 'docsPnmCmtsDsOfdmSymMeasStatus' is
        'busy' will return 'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), plus the current timestamp and the ifIndex of the interface
        on which the test runs. The timestamp is formatted as shown below:
        <Year:4d>-<Month:2d>-<Day:2d>_<Hour:2d>:<Minute:2d>:<Second:2d>.<Millisecond:3d>

        Hence, the format would be:

        PNMCcapSymCap_<Unique CCAP Identifier>_<Timestamp>_<ifIndex>

        For example:
        PNMCcapSymCap_ccap1.boulder.cablelabs.com_2018-06-26_10:50:14.451_24935767


        The data file is comprised of a header plus the Symbol Capture Data.
        The header is comprised of ordered fixed-length fields. Unless
        otherwise specified, the header fields contain hex values that are
        right-justified within the field. If necessary the field is left-padded
        with zero values.

        The file type is either '504E4D65' or '504E4E65' (with Versioning)"
     REFERENCE 
        "Information Model Mapping: CM-SP-CCAP-OSSI 
         DsOfdmSymbolCapture::Filename"
     DEFVAL { "" }
     ::= { docsPnmCmtsDsOfdmSymCapEntry 10 }
     
docsPnmCmtsDsOfdmSymDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         DsOfdmSymbolCapture::DestinationIndex"
     ::= { docsPnmCmtsDsOfdmSymCapEntry 11 }

-- ---------------------------------------------------------------------
-- The CMTS Noise Power Ratio Table
-- ---------------------------------------------------------------------
docsPnmCmtsDsOfdmNoisePwrRatioTable OBJECT-TYPE
     SYNTAX      SEQUENCE OF DocsPnmCmtsDsOfdmNoisePwrRatioEntry
     MAX-ACCESS  not-accessible
     STATUS      current
     DESCRIPTION
       "Downstream OFDM Noise Power Ratio is a PNM Test described in [PHYv3.1] 
        Downstream Noise Power Ratio (NPR) Measurement section. The 
        CmtsDsOfdmNoisePwrRatioTable defines the management interface for the 
        operator to configure and execute the Downstream OFDM Noise Power Ratio
        test.
        The purpose of downstream NPR measurement is to view the noise,
        interference and intermodulation products underlying a portion of the
        OFDM signal. As an out-of-service test, the CMTS can define an exclusion
        band of zero-valued subcarriers which forms a spectral notch in the
        downstream OFDM signal for all profiles of a given downstream channel.
        The CM provides its normal spectral capture measurements, or symbol
        capture, which permit analysis of the notch depth. A possible use case
        is to observe LTE interference occurring within an OFDM band; another
        is to observe intermodulation products resulting from signal-level
        alignment issues. Since the introduction and removal of a notch affects
        all profiles, causing possible link downtime, this feature is intended
        for infrequent maintenance.
        The CCAP creates a row in the CmtsDsOfdmNoisePwrRatioTable for each
        ifIndex of a downstream channel.
        The CCAP MAY support simultaneous Downstream NPR Measurement tests on 
        more than one OFDM channel at a time." 
     REFERENCE
         "Information Model Mapping: CM-SP-CCAP-OSSI    
          DsOfdmNoisePowerRatio"
     ::= { docsPnmCmtsObjects 2}

docsPnmCmtsDsOfdmNoisePwrRatioEntry OBJECT-TYPE
     SYNTAX      DocsPnmCmtsDsOfdmNoisePwrRatioEntry
     MAX-ACCESS  not-accessible
     STATUS      current
     DESCRIPTION
         "The conceptual row of the 'docsPnmCmtsDsOfdmNoisePwrRatioTable'. An instance
         is dynamically created and exists for an associated ifIndex of the
         physical downstream channel upon which the test defined by this table
         can take place.

         The conceptual rows do not persist across device resets. "
     INDEX { ifIndex  }
     ::= { docsPnmCmtsDsOfdmNoisePwrRatioTable 1 }

DocsPnmCmtsDsOfdmNoisePwrRatioEntry ::=
    SEQUENCE {
        docsPnmCmtsDsOfdmNprStartSubcar     Unsigned32,
        docsPnmCmtsDsOfdmNprStopSubcar      Unsigned32,
        docsPnmCmtsDsOfdmNprEnable          TruthValue,
        docsPnmCmtsDsOfdmNprDuration        Unsigned32
     }

docsPnmCmtsDsOfdmNprStartSubcar OBJECT-TYPE
     SYNTAX      Unsigned32 (0..8191)
     MAX-ACCESS  read-write
     STATUS      current
     DESCRIPTION
        "This attribute is the Subcarrier index corresponding to the frequency
        at the start of the spectral notch.

        This value can only be changed while the value of
        'docsPnmCmtsDsOfdmNprEnable' is 'false'. An attempt to set this
        value while the value of 'docsPnmCmtsDsOfdmNprEnable' is 'true'
        will return 'inconsistentValue'."
     REFERENCE
         "Information Model Mapping: CM-SP-CCAP-OSSI    
          DsOfdmNoisePowerRatio::StartSubcarrier"
     ::= { docsPnmCmtsDsOfdmNoisePwrRatioEntry 1 }

docsPnmCmtsDsOfdmNprStopSubcar OBJECT-TYPE
     SYNTAX      Unsigned32 (0..8191)
     MAX-ACCESS  read-write
     STATUS      current
     DESCRIPTION
        "This object is the Subcarrier index corresponding to the frequency
        at the upper end of the spectral notch.

        This value can only be changed while the value of
        'docsPnmCmtsDsOfdmNprEnable' is 'false'. An attempt to set this
        value while the value of 'docsPnmCmtsDsOfdmNprEnable' is 'true'
        will return 'inconsistentValue'. "
     REFERENCE
         "Information Model Mapping: CM-SP-CCAP-OSSI    
          DsOfdmNoisePowerRatio::StopSubcarrier"
     ::= { docsPnmCmtsDsOfdmNoisePwrRatioEntry 2 }

docsPnmCmtsDsOfdmNprEnable OBJECT-TYPE
     SYNTAX      TruthValue
     MAX-ACCESS  read-write
     STATUS      current
     DESCRIPTION
        "This attribute is used to enable the CCAP to create the spectral notch. 
         The CCAP may require the interface to have an ifAdminStatus of 'down' before
         allowing the Enable value to be successfully set to 'true' for this test. 
         
         If the CCAP is unable to create the excluded subcarrier notch while 
         executing a Downstream OFDM Noise Power Ration test, it must reject the test
         and respond with a failure notification. 
         
         The CCAP should set the value of DsOfdmNoisePowerRation::Enable to 'false' when 
         the Downstream OFDM Noise Power Ratio operation is complete."
     REFERENCE
         "Information Model Mapping: CM-SP-CCAP-OSSI    
          DsOfdmNoisePowerRatio::Enable"
     DEFVAL { false }
     ::= { docsPnmCmtsDsOfdmNoisePwrRatioEntry 3 }

docsPnmCmtsDsOfdmNprDuration OBJECT-TYPE
     SYNTAX      Unsigned32 (0..65535)
     UNITS       "seconds"
     MAX-ACCESS  read-write
     STATUS      current
     DESCRIPTION
        "This object indicates the length of time in seconds that the spectral
        notch is to be maintained. The CMTS may make the excluded subcarriers
        active after the expiration of the Duration attribute. There is no
        expectation that CMTS will re-activate the excluded subcarriers
        immediately after the expiration of the timer. It is recommended that
        the CMTS use the OCD message to create the spectral notch.
        
        The CCAP should only allow the value of DsOfdmNoisePowerRatio::Duration 
        to be changed while the value of DsOfdmNoisePowerRatio::'Enable' is 'false'.

        This value can only be changed while value of
        'docsPnmCmtsDsOfdmNprEnable' is 'false'. An attempt to set this
        value while the value of 'docsPnmCmtsDsOfdmNprEnable' is 'true'
        will return 'inconsistentValue'. "
     REFERENCE
         "Information Model Mapping: CM-SP-CCAP-OSSI    
          DsOfdmNoisePowerRatio::Duration"
     DEFVAL { 600 }
     ::= { docsPnmCmtsDsOfdmNoisePwrRatioEntry 4 }

-- ---------------------------------------------------------------------
-- CMTS Upstream PNM Objects
-- ---------------------------------------------------------------------


-- ---------------------------------------------------------------------
-- The CMTS Upstream Capture for Active and Quiet Probes
-- ---------------------------------------------------------------------
docsPnmCmtsUsOfdmaAQProbeTable OBJECT-TYPE
     SYNTAX      SEQUENCE OF DocsPnmCmtsUsOfdmaAQProbeEntry
     MAX-ACCESS  not-accessible
     STATUS      current
     DESCRIPTION
       "Upstream OFDMA Active and Quiet Probe is a PNM Test described in [PHYv3.1]
        Upstream Capture for Active and Quiet Probe section. The 
        CmtsUsOfdmaAQProbeTable defines the management interface for the operator 
        to configure, execute, and monitor the Upstream OFDMA Active and Quiet 
        Probe test.
        The purpose of upstream capture is to measure plant response and view
        the underlying noise floor, by capturing at least one OFDMA symbol
        during a scheduled active or quiet probe. An active probe provides the
        partial functionality of a network analyzer, since the input is known
        and the output is captured. This permits full characterization of the
        linear and nonlinear response of the upstream cable plant. A quiet probe
        provides an opportunity to view the underlying noise and ingress while
        no traffic is being transmitted in the OFDMA band being measured.

        The PNM server selects an active CM to analyze by specifying its MAC
        address, or performs a quiet probe measurement. When enabled to perform
        the capture, the CCAP selects a specified transmitting CM, or quiet
        period when no CMs are transmitting, for the capture. The CCAP sets up
        the capture as described in MULPIv3.1, selecting either an active SID
        corresponding to the specified MAC address or the idle SID, and defining
        an active or quiet probe. The active probe symbol for this capture
        normally includes all non-excluded subcarriers across the upstream OFDMA
        channel, with pre-equalization on or off as specified in the MIB. The quiet
        probe symbol normally includes all subcarriers, that is, during the quiet
        probe time there are no transmissions in the given upstream OFDMA channel.
        For the quiet probe, the CCAP captures samples of at least one full OFDMA
        symbol including the guard interval. The CCAP begins the capture with the
        first symbol of the specified probe. The sample rate is the FFT sample rate
        (102.4 Msps).

        The CCAP reports the list of excluded subcarriers, the cyclic prefix length,
        and the transmit window rolloff period in order to fully define the
        transmitted waveform. The CMTS also reports the index of the starting sample
        used by the receiver for its FFT. For possible comparison with other events,
        the CCAP reports the timestamp corresponding to the beginning of the probe.
        In the case where the P-MAPs for the OFDMA upstream being analyzed are being
        sent in an OFDM downstream, the timestamp reported is the extended timestamp,
        while in a case with OFDMA upstream channels but no OFDM downstream channels,
        the reported timestamp is the D3.0 timestamp. For an active probe, the CMTS
        reports the contents of the Probe Information Element (P-IE) message
        describing that probe. 
        
        The CCAP may support simultaneous Upstream Capture for Active and Quiet Probe 
        tests on more than one OFDMA channel at a time.
        
        The CCAP should reject configuring a value for the DestinationIndex of the 
        UsOfdmaActiveAndQuietProbe object if that value does not exist in the 
        corresponding DestinationIndex attribute of the DataTransferCfg instance.
        
        The CCAP should create a row in the CmtsUsOfdmaAQProbeTable 
        for each ifIndex of an upstream channel."
     REFERENCE
        "Information Model Mapping: CM-SP-CCAP-OSSI    
         UsOfdmaActiveAndQuietProbes"
     ::= { docsPnmCmtsObjects 3}

docsPnmCmtsUsOfdmaAQProbeEntry OBJECT-TYPE
     SYNTAX      DocsPnmCmtsUsOfdmaAQProbeEntry
     MAX-ACCESS  not-accessible
     STATUS      current
     DESCRIPTION
         "The conceptual row of the 'docsPnmCmtsUsOfdmaAQProbeTable'. An
         instance is dynamically created and exists for an associated ifIndex
         of the physical upstream channel upon which the test defined by this
         table can take place.

         The conceptual rows do not persist across device resets. "
     INDEX { ifIndex  }
     ::= { docsPnmCmtsUsOfdmaAQProbeTable 1 }

DocsPnmCmtsUsOfdmaAQProbeEntry ::=
    SEQUENCE {
        docsPnmCmtsUsOfdmaAQProbeCmMacAddr          MacAddress,
        docsPnmCmtsUsOfdmaAQProbeUseIdleSid         TruthValue,
        docsPnmCmtsUsOfdmaAQProbePreEqOn            TruthValue,
        docsPnmCmtsUsOfdmaAQProbeEnable             TruthValue,
        docsPnmCmtsUsOfdmaAQProbeTimeout            Unsigned32,
        docsPnmCmtsUsOfdmaAQProbeNumSymToCapt       Unsigned32,
        docsPnmCmtsUsOfdmaAQProbeMaxCaptSymbols     Unsigned32,
        docsPnmCmtsUsOfdmaAQProbeNumSamples         Unsigned32,
        docsPnmCmtsUsOfdmaAQProbeTimeStamp          OCTET STRING,
        docsPnmCmtsUsOfdmaAQProbeMeasStatus         MeasStatusType,
        docsPnmCmtsUsOfdmaAQProbeFileName           SnmpAdminString,
        docsPnmCmtsUsOfdmaAQProbeFreqDomainSamples  TruthValue,
        docsPnmCmtsUsOfdmaAQProbeDestinationIndex   Unsigned32
     }

docsPnmCmtsUsOfdmaAQProbeCmMacAddr OBJECT-TYPE
     SYNTAX      MacAddress
     MAX-ACCESS  read-write
     STATUS      current
     DESCRIPTION
        "This attribute represents the MAC address of the CM transmitting the
        probe to be measured.

        This object cannot be changed while a capture is in progress. It will
        return a value of 'inconsistentValue' if set while the value of
        'docsPnmCmtsUsOfdmaAQProbeMeasStatus' is set to a value of 'busy'. "
     REFERENCE 
        "Information Model Mapping: CM-SP-CCAP-OSSI 
         UsOfdmaActiveAndQuietProbe::CmMacAddress"
     DEFVAL { '000000000000'H }
     ::= { docsPnmCmtsUsOfdmaAQProbeEntry 1 }

docsPnmCmtsUsOfdmaAQProbeUseIdleSid OBJECT-TYPE
     SYNTAX      TruthValue
     MAX-ACCESS  read-write
     STATUS      current
     DESCRIPTION
        "This attribute, when enabled, causes the CMTS to measure the channel
        during a quiet period when no CM is transmitting.

        This object cannot be changed while a capture is in progress. It will
        return a value of 'inconsistentValue' if set while the value of
        'docsPnmCmtsUsOfdmaAQProbeMeasStatus' is set to a value of 'busy'. "
     REFERENCE 
        "Information Model Mapping: CM-SP-CCAP-OSSI 
         UsOfdmaActiveAndQuietProbe::UseIdleSid"
     DEFVAL { false }
     ::= { docsPnmCmtsUsOfdmaAQProbeEntry 2 }

docsPnmCmtsUsOfdmaAQProbePreEqOn OBJECT-TYPE
     SYNTAX      TruthValue
     MAX-ACCESS  read-write
     STATUS      current
     DESCRIPTION
        "This attribute, when enabled, causes the CMTS to enable
        pre-equalization in the Probe Information Element for the CM
        transmitting the probe to be measured.

        This object cannot be changed while a capture is in progress. It will
        return a value of 'inconsistentValue' if set while the value of
        'docsPnmCmtsUsOfdmaAQProbeMeasStatus' is set to a value of 'busy'. "
     REFERENCE 
        "Information Model Mapping: CM-SP-CCAP-OSSI 
         UsOfdmaActiveAndQuietProbe::PreEqualizationOn"
     DEFVAL { true }
     ::= { docsPnmCmtsUsOfdmaAQProbeEntry 3 }

docsPnmCmtsUsOfdmaAQProbeEnable OBJECT-TYPE
     SYNTAX      TruthValue
     MAX-ACCESS  read-write
     STATUS      current
     DESCRIPTION
        "When set to true, this attribute causes the CCAP to begin a test of a probe
         for the CM whose MAC address is specified in the CmMacAddress attribute or for
         a quiet period if the UseIdleSid attribute is enabled. The Enable attribute is
         set to 'false' internally by the CCAP when the test has been completed,
         if the Timeout value has expired, or if the CCAP has encountered a test
         failure. If the value of Enable is 'true' the CCAP is actively measuring the 
         I/Q values of the probe under the specified PNM test, and if under this condition
         Enable is set to false, the CCAP will abort the test."
     REFERENCE 
        "Information Model Mapping: CM-SP-CCAP-OSSI 
         UsOfdmaActiveAndQuietProbe::Enable"
     DEFVAL { false }
     ::= { docsPnmCmtsUsOfdmaAQProbeEntry 4 }

docsPnmCmtsUsOfdmaAQProbeTimeout OBJECT-TYPE
     SYNTAX      Unsigned32 (0..65535)
     UNITS       "seconds"
     MAX-ACCESS  read-write
     STATUS      current
     DESCRIPTION
        "This attribute provides a timeout for the measurement if the CMTS is
        unable to perform the measurement for some reason. A value of zero for
        the Timeout attribute means that the measurement continues to be active
        until the measurement is completed or until the Enable attribute is cleared.

        This object cannot be changed while a capture is in progress. It will
        return a value of 'inconsistentValue' if set while the value of
        'docsPnmCmtsUsOfdmaAQProbeMeasStatus' is set to a value of 'busy'. "
     REFERENCE 
        "Information Model Mapping: CM-SP-CCAP-OSSI 
         UsOfdmaActiveAndQuietProbe::Timeout"
     DEFVAL { 1800 }
     ::= { docsPnmCmtsUsOfdmaAQProbeEntry 5 }

docsPnmCmtsUsOfdmaAQProbeNumSymToCapt OBJECT-TYPE
     SYNTAX      Unsigned32 (0..65535)
     UNITS       "symbols"
     MAX-ACCESS  read-write
     STATUS      current
     DESCRIPTION
        "This object represents the number of symbols the CMTS is to capture
        for the modem whose probe is being measured or the number of symbol
        times to measure for the idle Sid.

        This object cannot be changed while a capture is in progress. It will
        return a value of 'inconsistentValue' if set while the value of
        'docsPnmCmtsUsOfdmaAQProbeMeasStatus' is set to a value of 'busy'. "
     REFERENCE 
        "Information Model Mapping: CM-SP-CCAP-OSSI 
         UsOfdmaActiveAndQuietProbe::NumSymbolsToCapture"
     DEFVAL { 1 }
     ::= { docsPnmCmtsUsOfdmaAQProbeEntry 6 }

docsPnmCmtsUsOfdmaAQProbeMaxCaptSymbols OBJECT-TYPE
     SYNTAX      Unsigned32 (0..65535)
     UNITS       "symbols"
     MAX-ACCESS  read-only
     STATUS      current
     DESCRIPTION
        "This attribute represents the number of symbols the CCAP can capture
        for one measurement and is reported based on the channel's configuration.
        Typically, for 50 kHz Subcarrier Spacing, the CCAP can capture two symbols,
        and for 25 kHz, the CCAP can capture one symbol. In order to capture more 
        than one symbol, the CCAP would need to schedule multiple probe opportunities
        for the CM whose probe is being measured. "
     REFERENCE 
        "Information Model Mapping: CM-SP-CCAP-OSSI 
         UsOfdmaActiveAndQuietProbe::MaxCapturedSymbols"
     ::= { docsPnmCmtsUsOfdmaAQProbeEntry 7 }

docsPnmCmtsUsOfdmaAQProbeNumSamples OBJECT-TYPE
     SYNTAX      Unsigned32 (0..65535)
     UNITS       "samples"
     MAX-ACCESS  read-only
     STATUS      current
     DESCRIPTION
        "For FrequencyDomainSamples set to True, this attribute represents 
        the number of FFT samples present in the probe capture data. This 
        corresponds to the Encompassed Spectrum of the OFDMA channel divided
        by the subcarrier spacing. For FrequencyDomainSamples set to False, 
        this attribute represents the number of time-domain input samples 
        (i.e. prior to the FFT engine) present in the probe capture data 
        and includes the cyclic prefix, if configured. This is calculated 
        as the sample rate (102.4 E6) divided by the subcarrier spacing 
        plus the number of samples for the cyclic prefix (if enabled for the
        measurement). 
        For example, with 50 kHz subcarrier spacing this is 2048 samples
        plus 640 samples for the cyclic prefix (assuming the cyclic prefix 
        is configured for 6.25 microseconds)."
     REFERENCE 
        "Information Model Mapping: CM-SP-CCAP-OSSI 
         UsOfdmaActiveAndQuietProbe::NumSamples"
     ::= { docsPnmCmtsUsOfdmaAQProbeEntry 8 }

docsPnmCmtsUsOfdmaAQProbeTimeStamp OBJECT-TYPE
     SYNTAX      OCTET STRING (SIZE (8))
     MAX-ACCESS  read-only
     STATUS      current
     DESCRIPTION
        "This object represents the timestamp corresponding to the time when the
        measurement was performed. In the case in which the Primary Downstream
        is an OFDM channel this is the 64 bit timestamp. In the case in which
        the Primary Downstream is an SC-QAM channel this is the 32 bit timestamp.
        If the 32 bit timestamp is used, the 32 most significant bits of the
        timestamp are set to zero. "
     REFERENCE 
        "Information Model Mapping: CM-SP-CCAP-OSSI 
         UsOfdmaActiveAndQuietProbe::Timestamp"
     ::= { docsPnmCmtsUsOfdmaAQProbeEntry 9 }

docsPnmCmtsUsOfdmaAQProbeMeasStatus OBJECT-TYPE
     SYNTAX      MeasStatusType
     MAX-ACCESS  read-only
     STATUS      current
     DESCRIPTION
        "This attribute is used to determine the status of the measurement.
        When the Status = 'SampleReady', the CCAP has completed the measurement
        and the Enable attribute has been cleared."
     REFERENCE 
        "Information Model Mapping: CM-SP-CCAP-OSSI 
         UsOfdmaActiveAndQuietProbe::MeasStatus"
     ::= { docsPnmCmtsUsOfdmaAQProbeEntry 10 }

docsPnmCmtsUsOfdmaAQProbeFileName OBJECT-TYPE
     SYNTAX      SnmpAdminString
     MAX-ACCESS  read-write
     STATUS      current
     DESCRIPTION
        "This attribute is the name of the file, with the captured probe data,
        at the CMTS that is to be downloaded using TFTP to the PNM server.

        This value can only be changed while a test is not in progress. An attempt
        to set this value while the value of 'docsPnmCmtsUsOfdmaAQProbeMeasStatus'
        is 'busy' will return 'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), plus the current timestamp and the ifIndex of the interface
        on which the test runs. The timestamp is formatted as shown below:
        <Year:4d>-<Month:2d>-<Day:2d>_<Hour:2d>:<Minute:2d>:<Second:2d>.<Millisecond:3d>

        Hence, the format would be:

            PNMCcapAQProbe_<Unique CCAP Identifier>_<Timestamp>_<ifIndex>

        For example:
        PNMCcapAQProbe _ccap1.boulder.cablelabs.com_2018-06-26_10:50:14.451_24935767

        The data file is comprised of a header plus the Probe Capture Data.
        The header is comprised of ordered fixed-length fields. Unless
        otherwise specified, the header fields contain hex values that are
        right-justified within the field. If necessary the field is left-padded
        with zero values.

        The file type is either '504E4D66' or '504E4E66' (with Versioning)"
     REFERENCE 
        "Information Model Mapping: CM-SP-CCAP-OSSI 
         UsOfdmaActiveAndQuietProbe::Filename"
     DEFVAL {""}
     ::= { docsPnmCmtsUsOfdmaAQProbeEntry 11 }
     
docsPnmCmtsUsOfdmaAQProbeFreqDomainSamples OBJECT-TYPE
     SYNTAX      TruthValue
     MAX-ACCESS  read-write
     STATUS      current
     DESCRIPTION
        "This attribute configures the collection of output samples
         in the time domain or the frequency domain. 'True' means the
         values are in the frequency domain. 'False' means they are in
         the time domain."
     REFERENCE 
        "Information Model Mapping: CM-SP-CCAP-OSSI 
         UsOfdmaActiveAndQuietProbe::FrequencyDomainSamples"
     DEFVAL { true }
     ::= { docsPnmCmtsUsOfdmaAQProbeEntry 12 }
     
docsPnmCmtsUsOfdmaAQProbeDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         UsOfdmaActiveAndQuietProbe::DestinationIndex"
     ::= { docsPnmCmtsUsOfdmaAQProbeEntry 13 }
     

-- ---------------------------------------------------------------------
-- The CMTS Upstream Impulse Noise Statistics
-- ---------------------------------------------------------------------
docsPnmCmtsUsImpNoiseTable OBJECT-TYPE
     SYNTAX      SEQUENCE OF DocsPnmCmtsUsImpNoiseEntry
     MAX-ACCESS  not-accessible
     STATUS      current
     DESCRIPTION
       "Upstream Impulse Noise is a PNM Test described in [PHYv3.1] 
        Upstream Impulse Noise Statistics section. The CmtsUsImpNoiseTable
        defines the management interface for the operator to configure, 
        execute, and monitor the Upstream Impulse Noise test.
        
        This table provides statistics of burst/impulse noise occurring in a
        selected narrow band. A bandpass filter is positioned in an unoccupied
        upstream band. A threshold is set, energy exceeding the threshold
        triggers the measurement of an event, and energy falling below the
        threshold ends the event. An optional feature allows the threshold to
        be set to zero, in which case the average power in the band will be
        measured. The measurement is time-stamped using the DOCSIS 3.0 field of the
        64-bit extended timestamp (bits 9-40, where bit 0 is the LSB), which
        provides a resolution of 98 ns and a range of 7 minutes.
        
        The CCAP may support simultaneous Upstream Impulse Noise tests on 
        more than one RF port at a time.

        The CCAP provides the capability to capture the following statistics
        in a selected band up to 5.12 MHz wide: Timestamp of event, Duration of
        event, Average power of event.

        The CCAP provides a time history buffer of up to 1024 events. In steady
        state operation, a ring buffer provides the measurements of the last 1024
        events that occurred while the measurement was enabled. 
        
        The CCAP should create a row in the docsPnmCmtsUsImpNoiseTable for each
        ifIndex of an upstream RF Port.
        
        Initiation and termination of impulse noise samples collection is controlled by 
        UsImpulseNoise attributes FreeRunDuration, StartTriggerLevel, and EndTriggerLevel. 
        
        The CCAP should collect Upstream Impulse Noise samples when UsImpNoiseEnable is set to 'true'
        and FreeRunDuration is configured for a nonzero value, regardless of the values configured for 
        StartTriggerLevel and EndTriggerLevel. The CCAP should stop collecting Upstream Impulse Noise      
        samples and terminate the Upstream Impulse Noise test when the time corresponding to the value     
        of FreeRunDuration expires.     
        
        If the configured value of FreeRunDuration is nonzero, the CCAP will capture at most one 
        impulse noise event.
        
        The CCAP should collect Upstream Impulse Noise samples when UsImpNoiseEnable is set to 'true', 
        FreeRunDuration is configured with zero, StartTriggerLevel is configured with a nonzero value,
        and the burst noise on the upstream RF port exceeds the value configured for StartTriggerLevel.
        The CCAP should stop collection of Upstream Impulse Noise samples for a burst noise event 
        when FreeRunDuration is configured with zero, StartTriggerLevel and EndTriggerLevel are 
        configured with a nonzero value, and the burst noise on the upstream RF port falls below 
        the configured value for EndTriggerLevel.
        
        If the configured value of FreeRunDuration is zero, the configured value of StartTriggerLevel 
        is nonzero, and the configured value of EndTriggerLevel is nonzero, the CCAP could capture 
        multiple burst noise events before the sample capture is terminated when UsImpNoiseEnable is 
        set to 'false'.
        
        If the configured values of FreeRunDuration and EndTriggerLevel are zero and the configured 
        value of StartTriggerLevel is nonzero, the CCAP will capture at most one impulse noise event
        before the sample capture is terminated when UsImpNoiseEnable is set to 'false'.

        The CCAP should measure average power in the band when UsImpNoiseEnable is set to 'true'
        and configured values for FreeRunDuration and StartTriggerLevel are zero, and the configured
        value for EndTriggerLevel is zero or nonzero. The average power in the band will be measured 
        until sample collection is terminated when UsImpNoiseEnable is set to 'false'.
        The CCAP should reject configuring a value for the DestinationIndex of the UsImpulseNoise 
        object if that value does not exist in the corresponding DestinationIndex attribute of
        the DataTransferCfg instance."
     REFERENCE 
        "Information Model Mapping: CM-SP-CCAP-OSSI 
         UsImpulseNoise"
     ::= { docsPnmCmtsObjects 4}

docsPnmCmtsUsImpNoiseEntry OBJECT-TYPE
     SYNTAX      DocsPnmCmtsUsImpNoiseEntry
     MAX-ACCESS  not-accessible
     STATUS      current
     DESCRIPTION
         "The conceptual row of the docsPnmCmtsUsImpNoiseTable. An instance
         is dynamically created and exists for an associated ifIndex of the
         physical upstream channel upon which the test defined by this table
         can take place.

         The conceptual rows do not persist across device resets. "
     INDEX { ifIndex  }
     ::= { docsPnmCmtsUsImpNoiseTable 1 }

DocsPnmCmtsUsImpNoiseEntry ::=
    SEQUENCE {
        docsPnmCmtsUsImpNoiseEnable            TruthValue,
        docsPnmCmtsUsImpNoiseFreeRunDuration   Unsigned32,
        docsPnmCmtsUsImpNoiseStTrigLvl         Unsigned32,
        docsPnmCmtsUsImpNoiseEndTrigLvl        Unsigned32,
        docsPnmCmtsUsImpNoiseCenterFrq         Unsigned32,
        docsPnmCmtsUsImpNoiseMeasBw            Unsigned32,
        docsPnmCmtsUsImpNoiseNumEvtsCnted      Unsigned32,
        docsPnmCmtsUsImpNoiseLastEvtTimeStamp  OCTET STRING,
        docsPnmCmtsUsImpNoiseLastEvtDuration   Unsigned32,
        docsPnmCmtsUsImpNoiseLastEvtAvgPwr     Integer32,
        docsPnmCmtsUsImpNoiseMeasStatus        MeasStatusType,
        docsPnmCmtsUsImpNoiseFileName          SnmpAdminString,
        docsPnmCmtsUsImpNoiseDestinationIndex  Unsigned32
     }

docsPnmCmtsUsImpNoiseEnable OBJECT-TYPE
     SYNTAX      TruthValue
     MAX-ACCESS  read-write
     STATUS      current
     DESCRIPTION
        "This attribute causes the CCAP to begin the collection of the
         configured Impulse Noise events.  If the FreeRunDuration is set to
         a value greater than zero, the StartTriggerLevel is ignored and
         measurement of the signal power at the RF port begins when the
         Enable is set to true. The Enable attribute is cleared internally
         if FreeRunDuration has expired. If the FreeRunDuration is equal
         to zero and the Enable attribute is set to true, clearing the
         Enable causes the CCAP to stop the capture and generate the file
         of impulse noise data. If the NumEventsCounted is zero when the
         Enable is cleared, no file will be created.

        Interaction with other table rows:

        - This object returns 'inconsistentValue' if set to 'true' while the
        value of 'docsPnmCmtsUsImpNoiseMeasStatus' is a value of 'busy'.

        - Setting this object to a value of 'true' will change the value of the
        'docsPnmCmtsUsImpNoiseMeasStatus' to 'busy'. "
     REFERENCE 
        "Information Model Mapping: CM-SP-CCAP-OSSI 
         UsImpulseNoise::Enable"
     DEFVAL { false }
     ::= { docsPnmCmtsUsImpNoiseEntry 1 }

docsPnmCmtsUsImpNoiseFreeRunDuration OBJECT-TYPE
     SYNTAX      Unsigned32 (0..65536)
     UNITS       "seconds"
     MAX-ACCESS  read-write
     STATUS      current
     DESCRIPTION
       "This attribute, when configured with a nonzero value, provides 
        length of time to perform the Upstream Impulse Noise measurement 
        when the Enable attribute is set to true. 

        This object cannot be changed while a capture is in progress. It will
        return a value of 'inconsistentValue' if set while the value of
        'docsPnmCmtsUsImpNoiseMeasStatus' is set to a value of 'busy'. "
     REFERENCE 
        "Information Model Mapping: CM-SP-CCAP-OSSI 
         UsImpulseNoise::FreeRunDuration"
     DEFVAL { 60 }
     ::= { docsPnmCmtsUsImpNoiseEntry 2 }

docsPnmCmtsUsImpNoiseStTrigLvl OBJECT-TYPE
     SYNTAX      Unsigned32
     UNITS       "microvolts"
     MAX-ACCESS  read-write
     STATUS      current
     DESCRIPTION
        "This attribute, when configured with a nonzero value, is the burst 
         noise threshold which, when exceeded after the Enable attribute is set
         to true and FreeRunDuration is configured with value zero, starts the 
         Impulse Noise measurement. 
         If the value of UsImpulseNoise::Enable is set to 'true' with a nonzero 
         value configured for StartTriggerLevel and a zero value configured for 
         FreeRunDuration, an individual burst event starts when the burst noise 
         exceeds the StartTriggerLevel.

         This object cannot be changed while a capture is in progress. It will
         return a value of 'inconsistentValue' if set while the value of
         'docsPnmCmtsUsImpNoiseMeasStatus' is set to a value of 'busy'."
     REFERENCE 
        "Information Model Mapping: CM-SP-CCAP-OSSI 
         UsImpulseNoise::StartTriggerLevel"
     DEFVAL { 300 }
     ::= { docsPnmCmtsUsImpNoiseEntry 3 }

docsPnmCmtsUsImpNoiseEndTrigLvl OBJECT-TYPE
     SYNTAX      Unsigned32
     UNITS       "microvolts"
     MAX-ACCESS  read-write
     STATUS      current
     DESCRIPTION
       "This attribute, when configured with a nonzero value, is the lower 
        burst noise threshold for the Upstream Impulse Noise measurement 
        which terminates the measurement after it is started. Measurement
        of an individual burst event ends when the burst noise falls below 
        the EndTriggerLevel. If the EndTriggerLevel and the FreeRunDuration 
        are both set to zero and StartTriggerLevel is configured with a nonzero 
        value, at most a single Impulse Noise Event will be recorded when 
        triggered by a burst event exceeding the StartTriggerLevel.

        This object cannot be changed while a capture is in progress. It will
        return a value of 'inconsistentValue' if set while the value of
        'docsPnmCmtsUsImpNoiseMeasStatus' is set to a value of 'busy'. "
     REFERENCE 
        "Information Model Mapping: CM-SP-CCAP-OSSI 
         UsImpulseNoise::EndTriggerLevel"
     DEFVAL { 150 }
     ::= { docsPnmCmtsUsImpNoiseEntry 4 }

docsPnmCmtsUsImpNoiseCenterFrq OBJECT-TYPE
     SYNTAX      Unsigned32
     UNITS       "Hz"
     MAX-ACCESS  read-write
     STATUS      current
     DESCRIPTION
        "This attribute defines the center frequency for the noise power measurement.

        This object cannot be changed while a capture is in progress. It will
        return a value of 'inconsistentValue' if set while the value of
        'docsPnmCmtsUsImpNoiseMeasStatus' is set to a value of 'busy'. "
     REFERENCE 
        "Information Model Mapping: CM-SP-CCAP-OSSI 
         UsImpulseNoise::CenterFrequency"
     DEFVAL { 7000000 }
     ::= { docsPnmCmtsUsImpNoiseEntry 5 }

docsPnmCmtsUsImpNoiseMeasBw OBJECT-TYPE
     SYNTAX      Unsigned32 (160 |320 |640 |1280 |2560 |5120)
     UNITS       "kHz"
     MAX-ACCESS  read-write
     STATUS      current
     DESCRIPTION
        "This attribute defines the bandwidth for the noise power measurement.
        The MeasurementBw is the -3 dB bandwidth; the occupied bandwidth is
        typically 1.25 times the measurement bandwidth.

        This object cannot be changed while a capture is in progress. It will
        return a value of 'inconsistentValue' if set while the value of
        'docsPnmCmtsUsImpNoiseMeasStatus' is set to a value of 'busy'. "
     REFERENCE 
        "Information Model Mapping: CM-SP-CCAP-OSSI 
         UsImpulseNoise::MeasurementBandwidth"
     DEFVAL { 2560 }
     ::= { docsPnmCmtsUsImpNoiseEntry 6 }

docsPnmCmtsUsImpNoiseNumEvtsCnted OBJECT-TYPE
     SYNTAX      Unsigned32 (0..65535)
     MAX-ACCESS  read-only
     STATUS      current
     DESCRIPTION
        "This attribute is used to indicate how many impulse noise events have
        been recorded since the enable was set to true. This value will be 1024
        in steady state, after the ring buffer has filled with measurements. If
        the StartTriggerLevel is set to zero then the NumEventsCounted will be
        set to 1 when the FreeRunDuration has expired and the Enable has been
        internally cleared. "
     REFERENCE 
        "Information Model Mapping: CM-SP-CCAP-OSSI 
         UsImpulseNoise::NumEventsCounted"
     ::= { docsPnmCmtsUsImpNoiseEntry 7 }

docsPnmCmtsUsImpNoiseLastEvtTimeStamp OBJECT-TYPE
     SYNTAX      OCTET STRING (SIZE (8))
     MAX-ACCESS  read-only
     STATUS      current
     DESCRIPTION
        "This attribute provides represents the timestamp corresponding to the
         start of the last recorded event. The measurement is time-stamped using
         the 64-bit extended timestamp. If the CMTS is not using the 64-bit
         Extended Timestamp, then the 8 bit value is constructed from the 32-bit
         DOCSIS 3.0 Timestamp as follows:

         Bits 63 through 41 = 0
         Bits 40 through 9 = 32-bit DOCSIS 3.0 Timestamp
         Bits 8 through 0 = 0"

     REFERENCE 
        "Information Model Mapping: CM-SP-CCAP-OSSI 
         UsImpulseNoise::LastEventTimestamp"
     ::= { docsPnmCmtsUsImpNoiseEntry 8 }

docsPnmCmtsUsImpNoiseLastEvtDuration OBJECT-TYPE
     SYNTAX      Unsigned32
     UNITS       "nanoseconds"
     MAX-ACCESS  read-only
     STATUS      current
     DESCRIPTION
        "This attribute provides represents the time corresponding to the
        duration of the last recorded event. The EventDuration is expressed in
        ns."
     REFERENCE 
        "Information Model Mapping: CM-SP-CCAP-OSSI 
         UsImpulseNoise::LastEventDuration"
     ::= { docsPnmCmtsUsImpNoiseEntry 9 }

docsPnmCmtsUsImpNoiseLastEvtAvgPwr OBJECT-TYPE
     SYNTAX      Integer32
     UNITS       "dBmV"
     MAX-ACCESS  read-only
     STATUS      current
     DESCRIPTION
        "This attribute represents the average power measured during the last
        recorded event. The LastEventAveragePower is expressed in units of dBmV
        with 32-bit fixed point, fractional, two's complement notation encoded
        using the S5.26 format."
     REFERENCE 
        "Information Model Mapping: CM-SP-CCAP-OSSI 
         UsImpulseNoise::LastEventAveragePower"
     ::= { docsPnmCmtsUsImpNoiseEntry 10 }

docsPnmCmtsUsImpNoiseMeasStatus OBJECT-TYPE
     SYNTAX      MeasStatusType
     MAX-ACCESS  read-only
     STATUS      current
     DESCRIPTION
        "This attribute is used to determine the status of the command. When
         the Status is sampleReady, the CCAP has completed the measurement
         and the Enable attribute has been cleared. If the StartTriggerLevel
         is set to a non zero value and the Enable attribute is set to true,
         then collection of Impulse Noise events is in progress and the
         MeasStatus attribute will return a value of 'busy'.  If the Enable
         attribute is cleared while collection of Impulse Noise events is
         active, the MeasStatus attribute will be set to 'sampleReady."
     REFERENCE 
        "Information Model Mapping: CM-SP-CCAP-OSSI 
         UsImpulseNoise::MeasStatus"
    ::= { docsPnmCmtsUsImpNoiseEntry 11 }

docsPnmCmtsUsImpNoiseFileName OBJECT-TYPE
     SYNTAX      SnmpAdminString
     MAX-ACCESS  read-write
     STATUS      current
     DESCRIPTION
        "This attribute is the name of the file with the captured impulse noise
        data at the CMTS that is to be downloaded using TFTP to the PNM server.

        This value can only be changed while a test is not in progress. An attempt
        to set this value while the value of 'docsPnmCmtsUsImpNoiseMeasStatus'
        is 'busy' will return 'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), plus the current timestamp and ifIndex of the interface on
        which the test runs. The timestamp is formatted as shown below:
        <Year:4d>-<Month:2d>-<Day:2d>_<Hour:2d>:<Minute:2d>:<Second:2d>.<Millisecond:3d>

        Hence, the format would be:
        PNMCcapImpNoise_<Unique CCAP Identifier>_<Timestamp>_<ifIndex>

        For example:
        PNMCcapImpNoise _ccap1.boulder.cablelabs.com_2018-06-26_10:50:14.451_24935767

        The data file is created when the Enable is cleared by the PNM server.
        If the NumEventsCounted attribute is zero when the Enable is cleared,
        then no file will be created by the CMTS.
        The header is comprised of ordered fixed-length fields. Unless
        otherwise specified, the header fields contain hex values that are
        right-justified within the field. If necessary the field is left-padded
        with zero values.

        The file type is either '504E4D67' or '504E4E67' (with Versioning)"
     REFERENCE 
        "Information Model Mapping: CM-SP-CCAP-OSSI 
         UsImpulseNoise::Filename"
     DEFVAL { "" }
     ::= { docsPnmCmtsUsImpNoiseEntry 12 }
     
docsPnmCmtsUsImpNoiseDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         UsImpulseNoise::DestinationIndex"
     ::= { docsPnmCmtsUsImpNoiseEntry 13 }

-- ---------------------------------------------------------------------
-- The CMTS Upstream Histogram
-- ---------------------------------------------------------------------
docsPnmCmtsUsHistTable OBJECT-TYPE
     SYNTAX      SEQUENCE OF DocsPnmCmtsUsHistEntry
     MAX-ACCESS  not-accessible
     STATUS      current
     DESCRIPTION
        "Upstream Histogram is a PNM Test described in [PHYv3.1] Upstream Histogram
         section. The CmtsUsHistTable defines the management interface for the 
         operator to configure, execute, and monitor the Upstream Histogram test.
         
         The Upstream Histogram provides a measurement of nonlinear effects
         in the channel such as amplifier compression and laser clipping.
         For example, laser clipping causes one tail of the histogram to be
         truncated and replaced with a spike.
         When the UpstreamHistogram Enable attribute is set to 'true',
         the CCAP will begin capturing the histogram of time domain
         samples at the wideband front end of the receiver (full upstream
         band). The histogram is two-sided; that is, it encompasses
         values from far-negative to far-positive values of the samples.
         The histogram will have a minimum of 255 or 256 equally spaced
         bins. These bins typically correspond to the 8 MSBs of the
         wideband analog-to-digital converter (ADC) for the case of 255
         or 256 bins. The histogram dwell count, a 32-bit unsigned integer,
         is the number of samples observed while counting hits for a given bin,
         and may have the same value for all bins. The histogram hit count, a
         32-bit unsigned integer, is the number of samples falling in a given bin.
         The CCAP will report the dwell count per bin and the hit count per bin.
         When enabled, the CCAP will compute a histogram with a dwell of at least
         10 million samples at each bin in 30 seconds or less. The CCAP will
         continue accumulating histogram samples until it is restarted, disabled
         or times out. If the highest dwell count approaches its 32-bit overflow
         value, the CCAP will save the current set of histogram values and reset
         the histogram, so that in a steady-state condition a complete measurement
         is always available. 
         The CCAP creates a row in the docsPnmCmtsUsHistTable for each ifIndex of
         an upstream RF port. The CCAP MAY support simultaneous Upstream Histogram 
         tests on more than one RF port at a time.
         The CCAP should reject configuring a value for the DestinationIndex 
         of the UpstreamHistogram object if that value does not exist in the 
         corresponding DestinationIndex attribute of the DataTransferCfg instance"
     REFERENCE 
        "Information Model Mapping: CM-SP-CCAP-OSSI 
         UsHistogram"
     ::= { docsPnmCmtsObjects 5}

docsPnmCmtsUsHistEntry OBJECT-TYPE
     SYNTAX      DocsPnmCmtsUsHistEntry
     MAX-ACCESS  not-accessible
     STATUS      current
     DESCRIPTION
         "The conceptual row of the docsPnmCmtsUsHistTable. An instance
         is dynamically created and exists for an associated ifIndex of
         an upstream RF port upon which the test defined by this table
         can take place.

         The conceptual rows do not persist across device resets. "
     INDEX { ifIndex }
     ::= { docsPnmCmtsUsHistTable 1 }

DocsPnmCmtsUsHistEntry ::=
    SEQUENCE {
        docsPnmCmtsUsHistEnable           TruthValue,
        docsPnmCmtsUsHistTimeOut          Unsigned32,
        docsPnmCmtsUsHistMeasStatus       MeasStatusType,
        docsPnmCmtsUsHistFileName         SnmpAdminString,
        docsPnmCmtsUsHistDestinationIndex Unsigned32
     }

docsPnmCmtsUsHistEnable OBJECT-TYPE
     SYNTAX      TruthValue
     MAX-ACCESS  read-write
     STATUS      current
     DESCRIPTION
        "Setting this object to a value of 'true' instructs the CCAP to begin
        collection of histogram data and when enabled, the CCAP continues
        producing new data at its own rate.

        This value is only allowed to be set to 'true' if the value of
        'docsPnmCmtsUsHistMeasStatus' is a value other than 'busy'. Setting
        this value to 'true' will change the value of the
        'docsPnmCmtsUsHistMeasStatus' to 'busy'.

        Setting this object to a value of 'false' instructs the CCAP to stop
        the collection of histogram data and to generate the file.

        This object returns 'true' if the CCAP is actively collecting histogram
        data. Otherwise it returns 'false'.

        A restart may be accomplished by setting this attribute to 'false' and
        then back to 'true'.

        Interaction with other table rows:

        - This object returns 'inconsistentValue' if set to 'true' while the
        value of 'docsPnmCmtsUsHistMeasStatus' is a value of 'busy' for this row
        OR for any row in the table. That is, ONLY ONE ROW IN THE TABLE MAY BE
        ALLOWED TO BE 'true' AT THE SAME TIME.

        - This object returns 'inconsistentValue' if set to 'true' while the
        CM is in DOCSIS Light Sleep (DLS) mode or the CM is in battery-backup mode.

        - Setting this object to a value of 'true' will change the value of the
        'docsPnmCmtsUsHistMeasStatus' to 'busy'. "
     REFERENCE 
        "Information Model Mapping: CM-SP-CCAP-OSSI 
         UsHistogram::Enable"
     DEFVAL { false }
     ::= { docsPnmCmtsUsHistEntry 1 }

docsPnmCmtsUsHistTimeOut OBJECT-TYPE
     SYNTAX      Unsigned32 (0..65535)
     UNITS       "seconds"
     MAX-ACCESS  read-write
     STATUS      current
     DESCRIPTION
       "This column in the table sets a seconds time-out timer for capturing
        histogram data. It is used to automatically clear the CmtsUsHistEnable when 
        the timeout expires. 
        
        If the value of Timeout is zero, the CCAP should collect 
        data until the timeout value is changed, the test is stopped, or until any dwell
        counter reaches its 32-bit rollover value. When the dwell count reaches its 32-bit 
        maximum the CCAP should end the test and report counts accumulated to that point. 
        
        If the Timeout attribute is re-written while CmtsUsHistEnable is 'true', the CCAP 
        should restart the timeout timer with the new Timeout value and continue collecting data.
        
        When the timeout expires, the CmtsUsHistEnable will be set to 'false' and the
        capture will stop. When this happens, the data collected up to this point will 
        be saved in the file defined by the 'FileName', and the value of 'MeasStatus' will 
        be set to 'sampleReady'.

        Setting this value does not start a capture. Captures can only be started by setting 
        the CmtsUsHistEnable to 'true'. If this column is written while the CmtsUsHistEnable is 
        'true', the timer is restarted. This column returns the value with which it was last set."
     REFERENCE 
        "Information Model Mapping: CM-SP-CCAP-OSSI 
         UsHistogram::Timeout"
     DEFVAL { 1800 }
     ::= { docsPnmCmtsUsHistEntry 2 }

docsPnmCmtsUsHistMeasStatus OBJECT-TYPE
     SYNTAX      MeasStatusType
     MAX-ACCESS  read-only
     STATUS      current
     DESCRIPTION
        "This attribute is used to determine the status of the command. 
         When the Status is 'sampleReady', the CCAP is ready for the 
         Histogram data to be read."
     REFERENCE 
        "Information Model Mapping: CM-SP-CCAP-OSSI 
         UsHistogram::MeasStatus"
     ::= { docsPnmCmtsUsHistEntry 3 }

docsPnmCmtsUsHistFileName OBJECT-TYPE
     SYNTAX      SnmpAdminString
     MAX-ACCESS  read-write
     STATUS      current
     DESCRIPTION
        "This object is the name of the file at the CCAP which is to be
        transferred to the PNM server. The data is stored as 32 bit integers
        for the hit and dwell count values. This value can only be changed
        while a test is not in progress. An attempt to set this value while the
        value of 'docsPnmCmtsUsHistMeasStatus' is 'busy' will return
        'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), current timestamp and the ifIndex of the interface on
        which the test runs. The timestamp is formatted as shown below:
        <Year:4d>-<Month:2d>-<Day:2d>_<Hour:2d>:<Minute:2d>:<Second:2d>.<Millisecond:3d>

        Hence, the format would be:

        PNMCcapHist_<Unique CCAP Identifier>_<Timestamp>_<ifIndex>

        For example:
        PNMCcapHist_ccap1.boulder.cablelabs.com_2018-06-26_10:50:14.451_24935767

        The data file is comprised of a header plus the Histogram Data. The header
        is comprised of ordered fixed-length fields. Unless otherwise specified,
        the header fields contain hex values that are right-justified within the
        field. If necessary the field is left-padded with zero values.

        The file type is either '504E4D68' or '504E4E68' (with Versioning)"
     REFERENCE 
        "Information Model Mapping: CM-SP-CCAP-OSSI 
         UsHistogram::Filename"
     DEFVAL { "" }
     ::= { docsPnmCmtsUsHistEntry 4 }
     
docsPnmCmtsUsHistDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         UsHistogram::DestinationIndex"
     ::= { docsPnmCmtsUsHistEntry 5 }

-- ---------------------------------------------------------------------
-- The CMTS Upstream OFDMA Channel Receive Power
-- ---------------------------------------------------------------------
docsPnmCmtsUsOfdmaRxPwrTable OBJECT-TYPE
     SYNTAX      SEQUENCE OF DocsPnmCmtsUsOfdmaRxPwrEntry
     MAX-ACCESS  not-accessible
     STATUS      current
     DESCRIPTION
       "Upstream OFDMA Receive Power is a PNM Test described in [PHYv3.1] 
        Upstream Channel Power section. The CmtsUsOfdmaRxPwrTable defines the 
        management interface for the operator to configure, execute, and 
        monitor the Upstream OFDMA Receive Power test.
        
        The purpose of the upstream channel power metric is to provide an
        estimate of the received power in a specified OFDMA channel at
        the F connector input of the CCAP line card for a given user. The
        measurement is based on upstream probes, which are typically the same
        probes used for pre-equalization adjustment.

        The CCAP measures the total power of the probe subcarriers received
        from the CM.

        For channels without boosted pilots, the CCAP calculates the average
        power per subcarrier (Paverage) and then calculates the power normalized
        to 1.6 MHz as a)Paverage + 10 * log10(32) for 50 kHz subcarrier spacing,
        or as b)Paverage + 10 *log10(64) for 25 kHz subcarrier spacing.

        For channels with boosted pilots, the CCAP calculates the average power
        per subcarrier (Paverage) and then calculates the power normalized to
        1.6 MHz as a)Paverage + 10 * log10(32) + 1 dB for 50 kHz subcarrier
        spacing, or as b)Paverage + 10 *log10(64) + 0.5 dB for 25 kHz subcarrier
        spacing.
        
        NOTE: The CCAP would also use that adjusted value for comparison with the
        Target Receive Power for the purposes of transmit power adjustments in the
        RNG-RSP. 
        
        When executing the Measure Upstream OFDMA Receive Power test the CCAP must 
        provide probe opportunities and make measurements over the number of averages
        configured in the column CmtsUsOfdmaRxPwrNumAvgs.
        
        The CCAP may support simultaneous Upstream OFDMA Rx Power tests on more than 
        one OFDMA channel at a time.
        
        The CCAP should create a row in the docsPnmCmtsUsOfdmaRxPwrTable table for
        each ifIndex of an upstream channel."
     REFERENCE 
        "Information Model Mapping: CM-SP-CCAP-OSSI 
         UsOfdmaRxPower"
     ::= { docsPnmCmtsObjects 6}

docsPnmCmtsUsOfdmaRxPwrEntry OBJECT-TYPE
     SYNTAX      DocsPnmCmtsUsOfdmaRxPwrEntry
     MAX-ACCESS  not-accessible
     STATUS      current
     DESCRIPTION
         "The conceptual row of the docsPnmCmtsUsOfdmaRxPwrTable. An instance
         is dynamically created and exists for an associated ifIndex upon
         which the test defined by this table can take place.

         The conceptual rows do not persist across device resets. "
     INDEX { ifIndex,
             docsPnmCmtsUsOfdmaRxPwrCmMac }
     ::= { docsPnmCmtsUsOfdmaRxPwrTable 1 }

DocsPnmCmtsUsOfdmaRxPwrEntry ::=
    SEQUENCE {
        docsPnmCmtsUsOfdmaRxPwrEnable           TruthValue,
        docsPnmCmtsUsOfdmaRxPwrCmMac            MacAddress,
        docsPnmCmtsUsOfdmaRxPwrPreEq            TruthValue,
        docsPnmCmtsUsOfdmaRxPwrNumAvgs          Unsigned32,
        docsPnmCmtsUsOfdmaRxPwrOnePtSixPsd      TenthdB,
        docsPnmCmtsUsOfdmaRxPwrMeasStatus       MeasStatusType
     }

docsPnmCmtsUsOfdmaRxPwrEnable OBJECT-TYPE
     SYNTAX      TruthValue
     MAX-ACCESS  read-write
     STATUS      current
     DESCRIPTION
        "When set to true, this attribute causes the CCAP to begin a test of the
         received upstream channel power for the CM whose MAC address was specified
         in the CmMac attribute. The Enable attribute is set to false internally
         by the CCAP when the Upstream OFDMA Receive Power test has been completed, 
         or if the CCAP encounters a test failure. If this attribute returns true, 
         the CCAP is actively measuring the received upstream channel power under the
         specified PNM test, and under this condition if Enable is set to value false,
         the CCAP will abort the test."
     REFERENCE 
        "Information Model Mapping: CM-SP-CCAP-OSSI 
         UsOfdmaRxPower::Enable"
     DEFVAL { false }
     ::= { docsPnmCmtsUsOfdmaRxPwrEntry 1 }

docsPnmCmtsUsOfdmaRxPwrCmMac OBJECT-TYPE
     SYNTAX      MacAddress
     MAX-ACCESS  not-accessible
     STATUS      current
     DESCRIPTION
        "This attribute represents the MAC address of the CM whose Received
        upstream channel power is being measured.

        This object cannot be changed while a capture is in progress. It will
        return a value of 'inconsistentValue' if set while the value of
        'docsPnmCmtsUsOfdmaRxPwrMeasStatus' is set to a value of 'busy'. "
     REFERENCE 
        "Information Model Mapping: CM-SP-CCAP-OSSI 
         UsOfdmaRxPower::CmMac"
     ::= { docsPnmCmtsUsOfdmaRxPwrEntry 2 }

docsPnmCmtsUsOfdmaRxPwrPreEq OBJECT-TYPE
     SYNTAX      TruthValue
     MAX-ACCESS  read-write
     STATUS      current
     DESCRIPTION
        "This attribute is used by the CMTS to enable or disable pre-equalization
        of the probe. The pre-equalization is controlled by a bit in the Probe
        Information Element sent in a MAP to the CM.

        This object cannot be changed while a capture is in progress. It will
        return a value of 'inconsistentValue' if set while the value of
        'docsPnmCmtsUsOfdmaRxPwrMeasStatus' is set to a value of 'busy'. "
     REFERENCE 
        "Information Model Mapping: CM-SP-CCAP-OSSI 
         UsOfdmaRxPower::PreEqOnOff"
     DEFVAL { true }
     ::= { docsPnmCmtsUsOfdmaRxPwrEntry 3 }

docsPnmCmtsUsOfdmaRxPwrNumAvgs OBJECT-TYPE
     SYNTAX      Unsigned32 (0..255)
     MAX-ACCESS  read-write
     STATUS      current
     DESCRIPTION
       "This column configures the number of measurements over which the 
        CCAP averages Upstream OFDMA Receive Power. The average is simply 
        the sum of the CmtsUsOfdmaRxPwrOnePtSixPsd values divided by the 
        CmtsUsOfdmaRxPwrNumAvgs.
        
        This column cannot be changed while a capture is in progress. It will
        return a value of 'inconsistentValue' if set while the value of
        'docsPnmCmtsUsOfdmaRxPwrMeasStatus' is set to a value of 'busy'. "
     REFERENCE 
        "Information Model Mapping: CM-SP-CCAP-OSSI 
         UsOfdmaRxPower::NumAverages"
     ::= { docsPnmCmtsUsOfdmaRxPwrEntry 4 }

docsPnmCmtsUsOfdmaRxPwrOnePtSixPsd OBJECT-TYPE
     SYNTAX      TenthdB
     UNITS       "dB"
     MAX-ACCESS  read-only
     STATUS      current
     DESCRIPTION
        "This attribute represents the average power of the probe measured by
        the CCAP, reported as the Power Spectral Density in an equivalent
        1.6 MHz spectrum, for the CM whose MAC address was specified in the
        CmMac attribute. If the NumberOfAverages attribute was greater than one,
        then this attribute represents the accumulated average 1.6 MHz PSD. "
     REFERENCE 
        "Information Model Mapping: CM-SP-CCAP-OSSI 
         UsOfdmaRxPower::RxPowerOnePtSixPsd"
     ::= { docsPnmCmtsUsOfdmaRxPwrEntry 5 }

docsPnmCmtsUsOfdmaRxPwrMeasStatus OBJECT-TYPE
     SYNTAX      MeasStatusType
     MAX-ACCESS  read-only
     STATUS      current
     DESCRIPTION
        "This attribute is used to determine the status of the measurement.
        When the Status = SampleReady, the CCAP is ready for the Upstream
        Power data to be read. "
     REFERENCE 
        "Information Model Mapping: CM-SP-CCAP-OSSI 
         UsOfdmaRxPower::MeasStatus"
     ::= { docsPnmCmtsUsOfdmaRxPwrEntry 6 }

-- ---------------------------------------------------------------------
-- The CMTS Upstream Receive Modulation Error Ratio (RxMER) Per Subcarrier
-- ---------------------------------------------------------------------
docsPnmCmtsUsOfdmaRxMerTable OBJECT-TYPE
     SYNTAX      SEQUENCE OF DocsPnmCmtsUsOfdmaRxMerEntry
     MAX-ACCESS  not-accessible
     STATUS      current
     DESCRIPTION
       "Upstream OFDMA Receive MER per Subcarrier is a PNM Test described 
        in [PHYv3.1] Upstream Receive Modulation Error Ratio (RxMER) 
        Per Subcarrier section. The CmtsUsOfdmaRxMerTable defines the management 
        interface for the operator to configure, execute, and monitor the 
        Upstream OFDMA Receive MER per Subcarrier test.
        
        This item provides measurements of the upstream receive modulation
        error ratio (RxMER) for each subcarrier. The CCAP measures the RxMER
        using an upstream probe, which is not subject to symbol errors as data
        subcarriers would be. The probes used for RxMER measurement are typically
        distinct from the probes used for pre-equalization adjustment. For the
        purposes of this measurement, RxMER is defined as the ratio of the average
        power of the ideal QAM constellation to the average error-vector power.
        The error vector is the difference between the equalized received probe
        value and the known correct probe value. If some subcarriers (such as
        exclusion bands) cannot be measured by the CCAP, the CCAP indicates that
        condition in the measurement data for those subcarriers.
        
        The CCAP should reject configuring a value for the DestinationIndex
        of the UsOfdmaRxMerPerSubcarrier object if that value does not exist
        in the corresponding DestinationIndex attribute of the DataTransferCfg instance.
        
        The CCAP may support simultaneous Upstream OFDMA RxMER per Subcarrier tests 
        on more than one OFDMA channel at a time.
        
        The CCAP should be capable of selecting a specified transmitting CM for 
        the Upstream OFDMA RxMER per Subcarrier test.
        
        The CCAP should provide probe opportunities and make measurements over 
        the number of averages specified for the Upstream OFDMA RxMER per Subcarrier test.
        
        The CCAP should create a row in the docsPnmCmtsUsOfdmaRxMerTable for each ifIndex 
        of an upstream channel."
     REFERENCE 
        "Information Model Mapping: CM-SP-CCAP-OSSI 
         UsOfdmaRxMerPerSubcarrier"
     ::= { docsPnmCmtsObjects 7}

docsPnmCmtsUsOfdmaRxMerEntry OBJECT-TYPE
     SYNTAX      DocsPnmCmtsUsOfdmaRxMerEntry
     MAX-ACCESS  not-accessible
     STATUS      current
     DESCRIPTION
         "The conceptual row of the docsPnmCmtsUsOfdmaRxMerTable. An instance
         is dynamically created and exists for an associated ifIndex upon
         which the test defined by this table can take place.

         The conceptual rows do not persist across device resets. "
     INDEX { ifIndex }
     ::= { docsPnmCmtsUsOfdmaRxMerTable 1 }

DocsPnmCmtsUsOfdmaRxMerEntry ::=
    SEQUENCE {
        docsPnmCmtsUsOfdmaRxMerEnable           TruthValue,
        docsPnmCmtsUsOfdmaRxMerCmMac            MacAddress,
        docsPnmCmtsUsOfdmaRxMerPreEq            TruthValue,
        docsPnmCmtsUsOfdmaRxMerNumAvgs          Unsigned32,
        docsPnmCmtsUsOfdmaRxMerMeasStatus       MeasStatusType,
        docsPnmCmtsUsOfdmaRxMerFileName         SnmpAdminString,
        docsPnmCmtsUsOfdmaRxMerDestinationIndex Unsigned32
     }

docsPnmCmtsUsOfdmaRxMerEnable OBJECT-TYPE
     SYNTAX      TruthValue
     MAX-ACCESS  read-write
     STATUS      current
     DESCRIPTION
        "When set to true, this attribute causes the CCAP to begin a test of 
         the received MER per subcarrier for the CM whose MAC address was specified
         in the CmMac attribute. The Enable attribute is set to false internally by
         the CCAP when the test has been completed, or if the CCAP encounters a test
         failure. If this attribute returns true, the CCAP is actively measuring the
         RxMER per subcarrier under the specified PNM test, and under this condition
         if a value of false is set, the CCAP will abort the test."
     REFERENCE 
        "Information Model Mapping: CM-SP-CCAP-OSSI 
         UsOfdmaRxMerPerSubcarrier::Enable"
     DEFVAL { false }
     ::= { docsPnmCmtsUsOfdmaRxMerEntry 1 }

docsPnmCmtsUsOfdmaRxMerCmMac OBJECT-TYPE
     SYNTAX      MacAddress
     MAX-ACCESS  read-write
     STATUS      current
     DESCRIPTION
        "This attribute represents the MAC address of the CM whose Rx MER is
        being measured.

        This object cannot be changed while a capture is in progress. It will
        return a value of 'inconsistentValue' if set while the value of
        'docsPnmCmtsUsOfdmaRxMerMeasStatus' is set to a value of 'busy'. "
     REFERENCE 
        "Information Model Mapping: CM-SP-CCAP-OSSI 
         UsOfdmaRxMerPerSubcarrier::CmMac"
     DEFVAL { '000000000000'H }
     ::= { docsPnmCmtsUsOfdmaRxMerEntry 2 }

docsPnmCmtsUsOfdmaRxMerPreEq OBJECT-TYPE
     SYNTAX      TruthValue
     MAX-ACCESS  read-write
     STATUS      current
     DESCRIPTION
        "This attribute is used by the CMTS to enable or disable Pre
        Equalization of the probe. The Pre Equalization is controlled by a
        bit in the Probe Information Element sent in a MAP to the CM.

        This object cannot be changed while a capture is in progress. It will
        return a value of 'inconsistentValue' if set while the value of
        'docsPnmCmtsUsOfdmaRxMerMeasStatus' is set to a value of 'busy'. "
     REFERENCE 
        "Information Model Mapping: CM-SP-CCAP-OSSI 
         UsOfdmaRxMerPerSubcarrier::PreEqOnOff"
     DEFVAL { true }
     ::= { docsPnmCmtsUsOfdmaRxMerEntry 3 }

docsPnmCmtsUsOfdmaRxMerNumAvgs OBJECT-TYPE
     SYNTAX      Unsigned32 (1..255)
     MAX-ACCESS  read-write
     STATUS      current
     DESCRIPTION
        "This attribute controls the number of probes the CCAP will use to
        calculate the Rx MER per subcarrier. The average will be computed
        using the 'leaky integrator' method, where reported Rx MER per
        subcarrier value = alpha*accumulated values + (1-alpha)*current value.
        Alpha is one minus the reciprocal of the number of averages. For
        example, if N=25, then alpha = 0.96. A value of 1 indicates no
        averaging. Re-writing the number of averages will restart the
        averaging process.  If there are no accumulated values, the
        accumulators are made equal to the first measured bin amplitudes.

        This object cannot be changed while a capture is in progress. It will
        return a value of 'inconsistentValue' if set while the value of
        'docsPnmCmtsUsOfdmaRxMerMeasStatus' is set to a value of 'busy'."
     REFERENCE 
        "Information Model Mapping: CM-SP-CCAP-OSSI 
         UsOfdmaRxMerPerSubcarrier::NumAverages"
     ::= { docsPnmCmtsUsOfdmaRxMerEntry 4 }

docsPnmCmtsUsOfdmaRxMerMeasStatus OBJECT-TYPE
     SYNTAX      MeasStatusType
     MAX-ACCESS  read-only
     STATUS      current
     DESCRIPTION
        "This attribute is used to determine the status of the measurement.
        When the MeasStatus = SampleReady, the CMTS is ready for the RxMER
        data to be read. "
     REFERENCE 
        "Information Model Mapping: CM-SP-CCAP-OSSI 
         UsOfdmaRxMerPerSubcarrier::MeasStatus"
     ::= { docsPnmCmtsUsOfdmaRxMerEntry 5 }

docsPnmCmtsUsOfdmaRxMerFileName OBJECT-TYPE
     SYNTAX      SnmpAdminString
     MAX-ACCESS  read-write
     STATUS      current
     DESCRIPTION
        "This attribute is the name of the file with the RxMER data for a
        specified CM at the CMTS that is to be downloaded using TFTP to the
        PNM server. This value can only be changed while a test is not in
        progress. An attempt to set this value while the value of
        'docsPnmCmtsUsOfdmaRxMerMeasStatus' is 'busy' will return
        'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), plus the current timestamp and the ifIndex of the interface
        on which the test runs. The timestamp is formatted as shown below:
        <Year:4d>-<Month:2d>-<Day:2d>_<Hour:2d>:<Minute:2d>:<Second:2d>.<Millisecond:3d>

        Hence, the format would be:

        PNMCcapRxMER_<Unique CCAP Identifier>_<Timestamp>_<ifIndex>

        For example:
        PNMCcapRxMER_ccap1.boulder.cablelabs.com_2018-06-26_10:50:14.451_24935767

        The data file is comprised of a header plus the RxMER Data. The header
        is comprised of ordered fixed-length fields. Unless otherwise specified,
        the header fields contain hex values that are right-justified within the
        field. If necessary the field is left-padded with zero values.

        The file type is either '504E4D69' or '504E4E69' (with Versioning)"
     REFERENCE 
        "Information Model Mapping: CM-SP-CCAP-OSSI 
         UsOfdmaRxMerPerSubcarrier::Filename"
     DEFVAL { "" }
     ::= { docsPnmCmtsUsOfdmaRxMerEntry 6 }
     
docsPnmCmtsUsOfdmaRxMerDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         UsOfdmaRxMerPerSubcarrier::DestinationIndex"
     ::= { docsPnmCmtsUsOfdmaRxMerEntry 7 }

-- ---------------------------------------------------------------------
-- The CMTS OFDMA Upstream Triggered Spectrum Capture
-- ---------------------------------------------------------------------
docsPnmCmtsUsSpecAnTable OBJECT-TYPE
     SYNTAX      SEQUENCE OF DocsPnmCmtsUsSpecAnEntry
     MAX-ACCESS  not-accessible
     STATUS      deprecated
     DESCRIPTION
        "The upstream triggered spectrum analysis measurement provides a
        wideband spectrum analyzer function in the CMTS which can be triggered
        to examine desired upstream transmissions as well as underlying
        noise/interference during a quiet period.

        The CMTS provides wideband upstream spectrum analysis capability
        covering the full upstream spectrum of the cable plant. The CMTS can
        be made to use 100 kHz or better resolution (bin spacing) in the
        wideband upstream spectrum measurement.

        Depending on the particular CMTS implementation, variable
        upstream spectrum analysis span is possible.

        It is also possible that the CMTS will provide the collection of
        time-domain input samples as an alternative to the frequency-domain
        upstream spectrum results.

        In pre-DOCSIS-3.1 mode, the CMTS provides the ability to trigger the
        spectrum sample capture and perform spectrum analysis using the
        following modes:
            - Free running
            - Trigger on minislot count
            - Trigger on SID (service identifier)
            - Trigger during quiet period (idle SID)

        In DOCSIS 3.1 mode, the CMTS provides the ability to trigger spectrum
        sample capture and perform spectrum analysis using the following modes:
            - Free running
            - A specified timestamp value
            - Minislot Number
            - A specified MAC address defining a SID, triggering at the beginning
            of the first minislot granted to that SID
            - The idle SID, triggering at the beginning of the first minislot
            granted to that SID
            - A specified active or quiet probe symbol, triggering at the beginning
            of the probe symbol "
     REFERENCE
        "DOCSIS 3.1 CCAP Operations Support System Interface Specification,
           CM-SP-CCAP-OSSI v3.1 , PNM section."
     ::= { docsPnmCmtsObjects 8}

docsPnmCmtsUsSpecAnEntry OBJECT-TYPE
     SYNTAX      DocsPnmCmtsUsSpecAnEntry
     MAX-ACCESS  not-accessible
     STATUS      deprecated
     DESCRIPTION
         "The conceptual row of the docsPnmCmtsUsSpecAnTable. An instance
         is dynamically created and exists for an associated ifIndex of an
         OFDMA upstream RF Port upon which the test defined by this table
         can take place.

         The conceptual rows do not persist across device resets. "
     INDEX { ifIndex }
     ::= { docsPnmCmtsUsSpecAnTable 1 }

DocsPnmCmtsUsSpecAnEntry ::=
    SEQUENCE {
        docsPnmCmtsUsSpecAnEnable           TruthValue,
        docsPnmCmtsUsSpecAnTrigMode         INTEGER,
        docsPnmCmtsUsSpecAnMiniSlotCnt      Unsigned32,
        docsPnmCmtsUsSpecAnSid              Unsigned32,
        docsPnmCmtsUsSpecAnMiniSlotNum      Unsigned32,
        docsPnmCmtsUsSpecAnCmMac            MacAddress,
        docsPnmCmtsUsSpecAnCenterFreq       Unsigned32,
        docsPnmCmtsUsSpecAnSpan             Unsigned32,
        docsPnmCmtsUsSpecAnNumberOfBins     Unsigned32,
        docsPnmCmtsUsSpecAnMeasStatus       MeasStatusType,
        docsPnmCmtsUsSpecAnFileName         SnmpAdminString
     }

docsPnmCmtsUsSpecAnEnable OBJECT-TYPE
     SYNTAX      TruthValue
     MAX-ACCESS  read-write
     STATUS      deprecated
     DESCRIPTION
        "This attribute causes the CMTS to begin the measurement of a probe
        for the selected CM or for a quiet period if the UseIdleSid attribute
        is enabled. The Enable attribute is cleared when the measurement has
        been completed. If the TriggerMode is FreeRunning then the Enable
        attribute will remain true until cleared by the PNM server.

        Interaction with other table rows:

        - This object returns 'inconsistentValue' if set to 'true' while the
        value of 'docsPnmCmtsUsSpecAnMeasStatus' is a value of 'busy'.

        - Default values are provided for read-write objects in this table; thus,
         this object may be set to 'true' without explicitly setting these values.
         However, the default values may not be appropriate and care should be
         taken to insure these values are correct for the desired test case.

        - Setting this object to a value of 'true' will change the value of the
        'docsPnmCmtsUsSpecAnMeasStatus' to 'busy'. "
     REFERENCE
         "DOCSIS 3.1 CCAP Operations Support System Interface Specification,
           CM-SP-CCAP-OSSI v3.1 , PNM section."
     DEFVAL { false }
     ::= { docsPnmCmtsUsSpecAnEntry 1 }

docsPnmCmtsUsSpecAnTrigMode OBJECT-TYPE
     SYNTAX      INTEGER {other(1),
                          freeRunning(2),
                          miniSlotCount(3),
                          sid(4),
                          idleSid(5),
                          minislotNumber(6),
                          cmMac(7),
                          quietProbeSymbol(8)
                         }
     MAX-ACCESS  read-write
     STATUS      deprecated
     DESCRIPTION
        "This attribute is used to control the trigger mode for the Spectrum
        Analysis capture.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSI v3.1 , PNM section."
     ::= { docsPnmCmtsUsSpecAnEntry 2 }

docsPnmCmtsUsSpecAnMiniSlotCnt OBJECT-TYPE
     SYNTAX      Unsigned32 (0..65535)
     MAX-ACCESS  read-write
     STATUS      deprecated
     DESCRIPTION
        "This attribute controls the numbe rof minislots the CMTS capturs
        during the Spectrum Analysis capture.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSI v3.1 , PNM section."
     DEFVAL { 0 }
     ::= { docsPnmCmtsUsSpecAnEntry 3 }

docsPnmCmtsUsSpecAnSid OBJECT-TYPE
     SYNTAX      Unsigned32 (0..65535)
     MAX-ACCESS  read-write
     STATUS      deprecated
     DESCRIPTION
        "This attribute is the SID corresponding to the CM which is granted a
        burst opportunity for the purpose of Spectrum Analysis. Typically the
        CMTS will schedule a unicast Station Maintenance opportunity for the
        CM with a grant size much longer than a normal Station Maintenance grant.
        This attribute is used when the TriggerMode is Sid.

        This object cannot be changed while a capture is in progress. It will
        return a value of 'inconsistentValue' if set while the value of
        'docsPnmCmtsUsSpecAnMeasStatus' is set to a value of 'busy'. "
     REFERENCE
         "DOCSIS 3.1 CCAP Operations Support System Interface Specification,
          CM-SP-CCAP-OSSI v3.1, PNM section."
     DEFVAL { 0 }
     ::= { docsPnmCmtsUsSpecAnEntry 4 }

docsPnmCmtsUsSpecAnMiniSlotNum OBJECT-TYPE
     SYNTAX      Unsigned32 (0..65535)
     MAX-ACCESS  read-write
     STATUS      deprecated
     DESCRIPTION
        "This attribute provides a mechanism by which the CMTS can begin the
        Spectrum Analysis at a subcarrier frequency corresponding to the
        MiniSlotNumber. This attribute is used when the TriggerMode is
        MiniSlotNumber.

        This object cannot be changed while a capture is in progress. It will
        return a value of 'inconsistentValue' if set while the value of
        'docsPnmCmtsUsSpecAnMeasStatus' is set to a value of 'busy'. "
     REFERENCE
         "DOCSIS 3.1 CCAP Operations Support System Interface Specification,
          CM-SP-CCAP-OSSI v3.1, PNM section."
     DEFVAL { 0 }
     ::= { docsPnmCmtsUsSpecAnEntry 5 }

docsPnmCmtsUsSpecAnCmMac OBJECT-TYPE
     SYNTAX      MacAddress
     MAX-ACCESS  read-write
     STATUS      deprecated
     DESCRIPTION
        "This attribute is used by the CCAP to trigger on a grant for any SID
        assigned to the CM and to perform the Spectrum Analysis Capture when
        the burst corresponding to that grant is received by the CCAP. This
        attribute is used when the TriggerMode is CmMac and is an alternative
        to using Sid for the TriggerMode.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSIv3.1, PNM section."
     DEFVAL { '000000000000'H }
     ::= { docsPnmCmtsUsSpecAnEntry 6 }

docsPnmCmtsUsSpecAnCenterFreq OBJECT-TYPE
     SYNTAX      Unsigned32
     UNITS       "Hz"
     MAX-ACCESS  read-write
     STATUS      deprecated
     DESCRIPTION
        "This attribute determines the center frequency of the Spectrum Analysis
        capture if the trigger mode is FreeRunning. If the trigger mode is not
        FreeRunning, the CMTS determines the value for the CenterFrequency
        attribute.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSIv3.1, PNM section."
     DEFVAL { 0 }
     ::= { docsPnmCmtsUsSpecAnEntry 7 }

docsPnmCmtsUsSpecAnSpan OBJECT-TYPE
     SYNTAX      Unsigned32 (0..65535)
     MAX-ACCESS  read-write
     STATUS      deprecated
     DESCRIPTION
        "This attribute determines the frequency span of the Spectrum Analysis
        capture if the trigger mode is FreeRunning. If the trigger mode is not
        FreeRunning, the CMTS determines the value for the Span attribute.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSIv3.1, PNM section."
     DEFVAL { 0 }
     ::= { docsPnmCmtsUsSpecAnEntry 8 }

docsPnmCmtsUsSpecAnNumberOfBins OBJECT-TYPE
     SYNTAX      Unsigned32 (0..65535)
     MAX-ACCESS  read-write
     STATUS      deprecated
     DESCRIPTION
        "This attribute determines the number of bins for the Spectrum Analysis
        capture if the trigger mode is FreeRunning. If the trigger mode is not
        FreeRunning, the CMTS determines the value for the NumberOfBins attribute.

        This object cannot be changed while a capture is in progress. It will
        return a value of 'inconsistentValue' if set while the value of
        'docsPnmCmtsUsSpecAnMeasStatus' is set to a value of 'busy'. "
     REFERENCE
         "DOCSIS 3.1 CCAP Operations Support System Interface Specification,
           CM-SP-CCAP-OSSIv3.1, PNM section."
     DEFVAL { 0 }
     ::= { docsPnmCmtsUsSpecAnEntry 9 }

docsPnmCmtsUsSpecAnMeasStatus OBJECT-TYPE
     SYNTAX      MeasStatusType
     MAX-ACCESS  read-only
     STATUS      deprecated
     DESCRIPTION
        "This attribute is used to determine the status of the measurement.
        The PNM server will query this value to determine when the file
        is ready for transfer. "
     REFERENCE
         "DOCSIS 3.1 CCAP Operations Support System Interface Specification,
           CM-SP-CCAP-OSSIv3.1, PNM section."
     ::= { docsPnmCmtsUsSpecAnEntry 10 }

docsPnmCmtsUsSpecAnFileName OBJECT-TYPE
     SYNTAX      SnmpAdminString
     MAX-ACCESS  read-write
     STATUS      deprecated
     DESCRIPTION
        "This attribute is the name of the file with the Spectrum Analysis data
        at the CMTS that is to be downloaded using TFTP to the PNM server.

        This value can only be changed while a test is not in progress. An attempt
        to set this value while the value of 'docsPnmCmtsUsSpecAnMeasStatus' is
        'busy' will return 'inconsistentValue'.

        If the value of this object is the DEFVAL (empty string), then
        a default filename value will be used. Otherwise the value set
        will be used as the filename. If a default filename is
        generated, then that value will be returned in this object and
        will represent the filename that was used for the test. All
        subsequent tests should set this object to a meaningful value
        or to an 'empty string' value (to generate a new default
        filename) before starting a new test.

        If a default filename value is used, it is generated as the test name
        plus a unique CCAP identifier (either a loopback address (IPv4 or IPv6)
        or FQDN), plus the 'epoch time'. The epoch time (also known as 'unix time')
        is defined as the number of seconds that have elapsed since midnight
        Coordinated Universal Time (UTC), Thursday, 1 January 1970.
        Hence, the format would be:

            PNMCcapSpecAn_<Unique CCAP Identifier>_<epoch>

        For example: PNMCcapSpecAn_ccap1.boulder.cablelabs_1403405123

        The data file is comprised of a header plus the Spectrum Analyzer Data.
        The header is comprised of ordered fixed-length fields. Unless
        otherwise specified, the header fields contain hex values that are
        right-justified within the field. If necessary the field is left-padded
        with zero values.

        The file type is either '504E4D6A' or '504E4E6A' (with Versioning)

         "
     REFERENCE
         "DOCSIS 3.1 CCAP Operations Support System Interface Specification,
           CM-SP-CCAP-OSSIv3.1, PNM section."
     DEFVAL { "" }
     ::= { docsPnmCmtsUsSpecAnEntry 11 }

-- ---------------------------------------------------------------------
-- CMTS OPT PNM Objects
-- ---------------------------------------------------------------------

-- ---------------------------------------------------------------------
-- The CMTS OPT Request Table
-- ---------------------------------------------------------------------
docsPnmCmtsOptReqTable OBJECT-TYPE
     SYNTAX      SEQUENCE OF DocsPnmCmtsOptReqEntry
     MAX-ACCESS  not-accessible
     STATUS      current
     DESCRIPTION
        "This table is used to initiate the OPT-REQ message for a given
         OFDM DS channel. The message and resulting tests and
         requirements are defined in the OPT-REQ TLV Encodings section of
         the MULPI Spec.  To use the object, the Operator or PMA
         Application uses the CM MAC address (CmMacAddr), the downstream
         OFDM channel configuration index (DsOfdmChannelCfgIndex), 
         and downstream OFDM profile configuration identifier 
         (DsOfdmProfileCfgProfileId) as the keys to initiate a test. The
         specific tests that are defined in MULPI are accessed with the
         ProfileTest attribute.  This attribute is a BITS data type and
         will allow one or more of the OPT tests to be configured to be
         performed by the CM.  Due to the nature of the ProfileTest
         attribute, one or more tests can be requested in a single
         message and thus different amounts of data need to be
         configured in order for the OPT Message to have the required
         TLVs.

         Some of these tests perform evaluations of thresholds or
         margins.  To facilitate these evaluations by the CM, these
         values are defined in the test request or the
         OptMerThresholdCfg table.
         To successfully initiate a test, the DsOfdmChanCfgIndex
         and an associated DsOfdmProfCfgId are required. 
         
         The CCAP should reject a request to initiate an OPT test when the
         DsOfdmChannelCfgIndex does not exist, or is not currently in use by the CM.
         
         The CCAP should reject a request if the referenced DsOfdmProfileCfgProfileId 
         is in use on the CM,or the value does not exist in the profiles associated 
         with the referenced DsOfdmChannelCfgIndex. 
         
         The CCAP should reject a request to run an OPT test on CM that is not operational.
         
         The CCAP should reject starting an OPT (i.e., setting OpCode to start(2) in the 
         OptReq object) for a unique combination of a CM, OFDM channel, and profile 
         if there is already an OPT running (i.e., the status in the OptResp object equals 
         testing(1)) for any profile on the same CM and OFDM channel.
         
         The CCAP should reject an OPT request that combines NCP tests (bit 5 or 6) with
         any other tests.
         
         The CCAP may support simultaneous Downstream OPT tests on more than one OFDM 
         channel at a time.
         
         This object supports the creation and deletion of multiple instances."
     REFERENCE 
        "Information Model Mapping: CM-SP-CCAP-OSSI 
         OptReq"
     ::= { docsPnmCmtsOptObjects 1 }

docsPnmCmtsOptReqEntry OBJECT-TYPE
     SYNTAX      DocsPnmCmtsOptReqEntry
     MAX-ACCESS  not-accessible
     STATUS      current
     DESCRIPTION
         "The conceptual row of the docsPnmCmtsOptReqTable.
          The conceptual rows do not persist across device resets."
     INDEX { docsPnmCmtsOptReqCmMacAddr,
             docsPnmCmtsOptReqDsOfdmChanCfgIndex,
             docsPnmCmtsOptReqDsOfdmProfCfgId }
     ::= { docsPnmCmtsOptReqTable 1 }

DocsPnmCmtsOptReqEntry ::=
    SEQUENCE {
        docsPnmCmtsOptReqCmMacAddr                           MacAddress,
        docsPnmCmtsOptReqDsOfdmChanCfgIndex                  InterfaceIndex,
        docsPnmCmtsOptReqDsOfdmProfCfgId                     Unsigned32,
        docsPnmCmtsOptReqOpCode                              INTEGER,
        docsPnmCmtsOptReqProfileTest                         BITS,
        docsPnmCmtsOptReqMaxDuration                         Unsigned32,
        docsPnmCmtsOptReqMaxCodewords                        Unsigned32,
        docsPnmCmtsOptReqMaxUncorrectableCws                 Unsigned32,
        docsPnmCmtsOptReqCwTaggingEnabled                    TruthValue,
        docsPnmCmtsOptReqNcpFields                           Unsigned32,
        docsPnmCmtsOptReqMaxNcpCrcFails                      Unsigned32,
        docsPnmCmtsOptReqStatus                              RowStatus,
        docsPnmCmtsOptReqMerThreshTemplateIndex              Unsigned32
        
     }

docsPnmCmtsOptReqCmMacAddr OBJECT-TYPE
     SYNTAX      MacAddress
     MAX-ACCESS  not-accessible
     STATUS      current
     DESCRIPTION
        "This attribute is a key which represents the MAC address for
         the referenced CM."
     REFERENCE 
        "Information Model Mapping: CM-SP-CCAP-OSSI 
         OptReq::CmMacAddr"
     ::= { docsPnmCmtsOptReqEntry 1 }

docsPnmCmtsOptReqDsOfdmChanCfgIndex OBJECT-TYPE
     SYNTAX      InterfaceIndex
     MAX-ACCESS  not-accessible
     STATUS      current
     DESCRIPTION
        "This key is the ifIndex of a Downstream OFDM channel 
         assigned to the modem."
     REFERENCE 
        "Information Model Mapping: CM-SP-CCAP-OSSI 
         OptReq::DsOfdmChannelCfgIndex"
     ::= { docsPnmCmtsOptReqEntry 2 }

docsPnmCmtsOptReqDsOfdmProfCfgId OBJECT-TYPE
     SYNTAX      Unsigned32 (0..15 |254|255)
     MAX-ACCESS  not-accessible
     STATUS      current
     DESCRIPTION
        "This attribute is a key that is the targeted profile being
         tested with OPT for the instance of DsOfdmProfileCfg.
         For Data Profile testing the ID of the profile that is being
         tested is used. The value 254 is used for RxMER statistics
         only.  The value 255 is used for NCP Profile Testing."
     REFERENCE 
        "Information Model Mapping: CM-SP-CCAP-OSSI 
         OptReq::DsOfdmProfChgId"
     ::= { docsPnmCmtsOptReqEntry 3 }

docsPnmCmtsOptReqOpCode OBJECT-TYPE
     SYNTAX      INTEGER {
                            other(1),
                            start(2),
                            abort(3),
                            fdxTriggeredStart(4)
                            }
     MAX-ACCESS  read-create
     STATUS      current
     DESCRIPTION
        "This attribute controls the testing to be performed by the CM
         receiving the OPT-REQ message.
         Defined values are listed below:
         other(1) - OPT-REQ OpCode type other than the following defined values
         start(2) - request for the cable modem receiving the OPT-REQ message to initiate the OFDM Profile Test
         abort(3) - request for the cable modem receiving the OPT-REQ message to abort a running OFDM Profile Test
         fdxTriggeredStart(4) - request for the cable modem receiving the OPT-REQ message to initiate the OFDM 
         Profile Test in compliance with [MULPIv4.0] FDX Triggered RxMER Measurements section. Note: This option is
         only applicable to DOCSIS 4.0 CCAP's."
     REFERENCE 
        "Information Model Mapping: CM-SP-CCAP-OSSI 
         OptReq::OpCode"
     DEFVAL { other }
     ::= { docsPnmCmtsOptReqEntry 4 }

docsPnmCmtsOptReqProfileTest OBJECT-TYPE
     SYNTAX      BITS {
                       rxMerSubCarrierStats(0),
                       rxMerSubCarrierThreshComp(1),
                       snrMarginCandidateProfile(2),
                       codewordStats(3),
                       codewordThreshComp(4),
                       ncpFieldStats(5),
                       ncpCrcThreshComp(6),
                       reserved(7),
                       other(8)
                        }
     MAX-ACCESS  read-create
     STATUS      current
     DESCRIPTION
        "This attribute defines which of the OPT tests are to be run by
         the CM.  The tests are encoded as individual bits: 
         
         rxMerSubCarrierStats(0)
         RxMER Statistics per Subcarrier

         rxMerSubCarrierThreshComp(1)
         RxMER per Subcarrier Threshold Comparison for Candidate Profile

         snrMarginCandidateProfile(2)
         SNR Margin for Candidate Profile

         codewordStats(3)
         Codeword Statistics for Candidate Profile

         codewordThreshComp(4)
         Codeword Threshold Comparison for Candidate Profile

         ncpFieldStats(5)
         NCP Field statistics

         ncpCrcThreshComp(6)
         NCP CRC Threshold Comparison

         reserved(7)
         Reserved

         other(8)
         Placeholder for vendor extensions

         When a given bit is set then that test will be performed by
         the CM.
         Note that the tests rxMerSubCarrierThreshComp(1),
         snrMarginCandidateProfile(2) require entries in the
         OptMerThreshold object for these tests to be performed.

         This attribute corresponds to TLV 1 in the OPT Request
         message."
     REFERENCE 
        "Information Model Mapping: CM-SP-CCAP-OSSI 
         OptReq::ProfileTest" 
     ::= { docsPnmCmtsOptReqEntry 5 }

docsPnmCmtsOptReqMaxDuration OBJECT-TYPE
     SYNTAX      Unsigned32  (1..180000)
     UNITS       "milliseconds"
     MAX-ACCESS  read-create
     STATUS      current
     DESCRIPTION
        "This attribute allows the tester to determine how long a test
         may run before returning results or aborting. MULPI requires
         this value to be not greater than 3 minutes or 180000 
         milliseconds.

         This attribute corresponds to TLV 4 in the OPT Request
         message."
     REFERENCE 
        "Information Model Mapping: CM-SP-CCAP-OSSI 
         OptReq::MaxDuration"
     ::= { docsPnmCmtsOptReqEntry 6 }

docsPnmCmtsOptReqMaxCodewords OBJECT-TYPE
     SYNTAX      Unsigned32
     UNITS       "Codewords"
     MAX-ACCESS  read-create
     STATUS      current
     DESCRIPTION
        "This attribute defines the maximum number of codewords that
         the CM should examine before the test is complete.  When
         either Nc or more codewords have been received, or Ne or more
         codeword errors have occurred, since the start of the test, the
         CM will send an OPT-RSP with a Complete status.
         This attribute is only present in the OPT-REQ message for
         Codeword tests:  codewordStats(3), codewordThreshComp(4).

         This attribute corresponds to TLV 5.1 in the OPT Request
         message."
     REFERENCE 
        "Information Model Mapping: CM-SP-CCAP-OSSI 
         OptReq::MaxCodewords"
     ::= { docsPnmCmtsOptReqEntry 7 }

docsPnmCmtsOptReqMaxUncorrectableCws OBJECT-TYPE
     SYNTAX      Unsigned32
     UNITS       "Codewords"
     MAX-ACCESS  read-create
     STATUS      current
     DESCRIPTION
        "This attribute defines the max num of uncorrectable codewords
         the CM should examine before the test is complete.  When
         either Nc or more codewords have been received, or Ne or more
         codeword errors have occurred, since the start of the test, the
         CM will send an OPT-RSP with a Complete status.
         This attribute is only present in the OPT-REQ message for
         Codeword tests:  codewordStats(3), codewordThreshComp(4).

         This attribute corresponds to TLV 5.2 in the OPT Request
         message."
     REFERENCE 
        "Information Model Mapping: CM-SP-CCAP-OSSI 
         OptReq::MaxUncorrectableCws"
     ::= { docsPnmCmtsOptReqEntry 8 }

docsPnmCmtsOptReqCwTaggingEnabled OBJECT-TYPE
     SYNTAX      TruthValue
     MAX-ACCESS  read-create
     STATUS      current
     DESCRIPTION
        "This attribute indicates whether Codeword Tagging is in use for
         this test. This attribute is defined as a Boolean with the
         value 'false' meaning that codeword tagging is disabled and a
         value of 'true' means that codeword tagging is enabled.  When
         codeword tagging is enabled, The CM will report codeword counts
         that include only codewords received on the profile in question
         for the duration of the test for which the 'T' bit is set to 1
         in the NCP pointing to the codeword. The location of the 'T'
         bit is specified in [DOCSIS PHYv3.1]. When codeword tagging is 
         enabled, LFSR synthetic traffic is all that is tagged.
         If codeword tagging is disabled, the CM only reports codeword
         counts that include all codewords received on the profile in
         question for the duration of the test.
         This attribute is only present in the OPT-REQ message for
         Codeword tests:  codewordStats(3), codewordThreshComp(4).
         This attribute corresponds to TLV 5.3 in the OPT Request
         message."
     REFERENCE 
        "Information Model Mapping: CM-SP-CCAP-OSSI 
         OptReq::CwTaggingEnabled"
     DEFVAL { false }
     ::= { docsPnmCmtsOptReqEntry 9 }

docsPnmCmtsOptReqNcpFields OBJECT-TYPE
     SYNTAX      Unsigned32
     MAX-ACCESS  read-create
     STATUS      current
     DESCRIPTION
        "This attribute defines the maximum number of NCP fields to be
         examined during the test.  When the CM has examined this number
         or more NCP fields, it returns the OPT Request with a completed
         test status and the collected statistical information.
         This attribute is only present in the OPT-REQ message for
         NcpFieldTests:  ncpFieldStats(5), ncpCrcThreshComp(6),
         This attribute corresponds to the TLV 6.1 in the OPT-REQ."
     REFERENCE 
        "Information Model Mapping: CM-SP-CCAP-OSSI 
         OptReq::NcpFields"
     ::= { docsPnmCmtsOptReqEntry 10 }

docsPnmCmtsOptReqMaxNcpCrcFails OBJECT-TYPE
     SYNTAX      Unsigned32
     MAX-ACCESS  read-create
     STATUS      current
     DESCRIPTION
        "This attribute defines the maximum number of NCP fields that
         are allowed to fail the NCP CRC checks to be examined during
         the test.  When the CM has examined this number or more NCP
         fields, it returns the OPT Request with a completed test
         status and the collected statistical information.
         This attribute is only present in the OPT-REQ message for
         NcpFieldTests:  ncpFieldStats(5), ncpCrcThreshComp(6),
         This attribute corresponds to the TLV 6.2 in the OPT-REQ."
     REFERENCE 
        "Information Model Mapping: CM-SP-CCAP-OSSI 
         OptReq::MaxNcpCrcFails"
     ::= { docsPnmCmtsOptReqEntry 11 }

docsPnmCmtsOptReqStatus OBJECT-TYPE
     SYNTAX      RowStatus
     MAX-ACCESS  read-create
     STATUS      current
     DESCRIPTION
        "The row status of this instance."
     ::= { docsPnmCmtsOptReqEntry 12 }
     
docsPnmCmtsOptReqMerThreshTemplateIndex OBJECT-TYPE
     SYNTAX      Unsigned32 (0..255)
     MAX-ACCESS  read-create
     STATUS      current
     DESCRIPTION
        "This attribute defines the TemplateIndex of the 
        OptMerThresholdTemplate objects for tests requiring 
        MER thresholds. Zero means no template is assigned for the test.
        If ProfileTest includes bits rxMerSubCarrierThreshComp(1) or 
        snrMarginCandidateProfile(2), the CCAP rejects setting opcode
        in the OptReq object to start(2) if MerThresholdTemplateIndex 
        equals zero or if there are not instances of the OptMerThresholdTemplate
        object with a TemplateIndex matching the value MerThresholdTemplateIndex
        and every modulation except zero-bit-loaded in the OFDM profile being 
        tested. Zero-bit-loaded modulations are not allowed in the threshold
        definition TLV (TLV 2.1) of the OPT-REQ in MULPI."
     REFERENCE 
        "Information Model Mapping: CM-SP-CCAP-OSSI 
         OptReq::MerThresholdTemplateIndex"
     DEFVAL { 0 }
     ::= { docsPnmCmtsOptReqEntry 13 }

-- ---------------------------------------------------------------------
-- The CMTS OPT MER Threshold Configuration Table - DEPRECATED
-- ---------------------------------------------------------------------
docsPnmCmtsOptMerThreshCfgTable OBJECT-TYPE
     SYNTAX      SEQUENCE OF DocsPnmCmtsOptMerThreshCfgEntry
     MAX-ACCESS  not-accessible
     STATUS      deprecated
     DESCRIPTION
        "This table is used to configure parameters for RxMER tests
         defined in docsPnmCmtsOptReqTable that require Pass/Fail
         criteria. It is necessary to define the parameters separately
         as the OPT-REQ message needs these values on a per modulation
         basis. This means that for each modulation order defined in a
         profile, the OPT-REQ includes a TLV entry for the required
         MER target value for each."
     REFERENCE
        "DOCSIS 3.1 CCAP Operations Support System Interface Specification,
           CM-SP-CCAP-OSSIv3.1, PNM section."
     ::= { docsPnmCmtsOptObjects 2 }

docsPnmCmtsOptMerThreshCfgEntry OBJECT-TYPE
     SYNTAX      DocsPnmCmtsOptMerThreshCfgEntry
     MAX-ACCESS  not-accessible
     STATUS      deprecated
     DESCRIPTION
         "The conceptual row of the docsPnmCmtsOptMerThreshCfgTable.
          The conceptual rows do not persist across device resets."
     INDEX { docsPnmCmtsOptReqDsOfdmChanCfgIndex,
             docsPnmCmtsOptReqDsOfdmProfCfgId,
             docsPnmCmtsOptMerThreshCfgModOrder }
     ::= { docsPnmCmtsOptMerThreshCfgTable 1 }

DocsPnmCmtsOptMerThreshCfgEntry ::=
    SEQUENCE {
        docsPnmCmtsOptMerThreshCfgModOrder                 DsOfdmModulationType,
        docsPnmCmtsOptMerThreshCfgRxMerVsBitloadingTarget  Unsigned32,
        docsPnmCmtsOptMerThreshCfgRxMerMargin              Unsigned32,
        docsPnmCmtsOptMerThreshCfgStatus                   RowStatus
     }

docsPnmCmtsOptMerThreshCfgModOrder OBJECT-TYPE
     SYNTAX      DsOfdmModulationType
     MAX-ACCESS  not-accessible
     STATUS      deprecated
     DESCRIPTION
        "This attribute is a key which represents the modulation types
         supported by the CCAP modulator. The value of zeroBitLoaded
         means that the subcarrier is BPSK modulated.
         This attribute corresponds to the TLV 2.1 in the OPT-REQ."
     ::= { docsPnmCmtsOptMerThreshCfgEntry 1 }

docsPnmCmtsOptMerThreshCfgRxMerVsBitloadingTarget OBJECT-TYPE
     SYNTAX      Unsigned32 (0..255)
     UNITS       "QuarterdB"
     MAX-ACCESS  read-create
     STATUS      deprecated
     DESCRIPTION
        "This attribute is the required value for the profile RxMER
        (refer to OPT-RSP) in units of 0.25dB (0xFF is 63.75dB).
        This is the required RxMER value that the CM uses to calculate
        the SNR margin for the profile. The default values for this
        attribute are defined in the PHY3.1 Spec as CM Minimum CNR
        Performance in AWGN Channel.
        This attribute corresponds to the TLV 2.2 in the OPT-REQ."
     ::= { docsPnmCmtsOptMerThreshCfgEntry 2 }

docsPnmCmtsOptMerThreshCfgRxMerMargin OBJECT-TYPE
     SYNTAX      Unsigned32
     UNITS       "dB"
     MAX-ACCESS  read-create
     STATUS      deprecated
     DESCRIPTION
        "The CM reports the number of subcarriers with a measured RxMER
         value that is at least this value below the target RxMER for
         the bitloading of the given subcarrier in the OPT-RSP message.
         This attribute corresponds to the TLV 2.3 in the OPT-REQ."
     ::= { docsPnmCmtsOptMerThreshCfgEntry 3 }

docsPnmCmtsOptMerThreshCfgStatus OBJECT-TYPE
     SYNTAX      RowStatus
     MAX-ACCESS  read-create
     STATUS      deprecated
     DESCRIPTION
        "The status of this instance."
     ::= { docsPnmCmtsOptMerThreshCfgEntry 4 }

-- ---------------------------------------------------------------------
-- The CMTS OPT Profile Change Configuration Table
-- ---------------------------------------------------------------------
docsPnmCmtsOptProfChgCfgTable OBJECT-TYPE
     SYNTAX      SEQUENCE OF DocsPnmCmtsOptProfChgCfgEntry
     MAX-ACCESS  not-accessible
     STATUS      current
     DESCRIPTION
        "This table allows the Operator to force changes in the assigned
         profiles on a given registered CM.
         The intent of this object is to replace the current set of DS 
         channel profiles that the CM is currently using with the new 
         value defined by DsProfileList. Instances of this object are
         not persistent and are not used for assigning modems profiles 
         upon CM re-initialization. Attempts to change profiles on a CM 
         that is not currently in an operational state are rejected 
         by the CCAP. If the CCAP receives a request to change a profile 
         on an OFDM channel that is not in the CM's RCS and the DsChannelId
         is not currently in use by the CM, the CCAP rejects the request. 
         If the CCAP receives a request to change a profile on the CM and one 
         or more profiles referenced in the DsProfileList do not exist, 
         the CCAP rejects the request. The CCAP rejects any DsProfileList
         that does not contain profile 0. This object supports the creation and 
         deletion of multiple instances. The CCAP may remove instances of this 
         object when the DBC operation to update the profile list for the CM 
         and Ds OFDM Channel has completed."
     REFERENCE 
        "Information Model Mapping: CM-SP-CCAP-OSSI 
         ProfChgCfg"
     ::= { docsPnmCmtsOptObjects 3 }

docsPnmCmtsOptProfChgCfgEntry OBJECT-TYPE
     SYNTAX      DocsPnmCmtsOptProfChgCfgEntry
     MAX-ACCESS  not-accessible
     STATUS      current
     DESCRIPTION
         "The conceptual row of the docsPnmCmtsOptProfChgCfgTable.
          The conceptual rows do not persist across device resets."
     INDEX { docsPnmCmtsOptReqCmMacAddr, docsPnmCmtsOptProfChgCfgIfIndex }
     ::= { docsPnmCmtsOptProfChgCfgTable 1 }

DocsPnmCmtsOptProfChgCfgEntry ::=
    SEQUENCE {
        docsPnmCmtsOptProfChgCfgIfIndex            InterfaceIndex,
        docsPnmCmtsOptProfChgCfgDsProfList         OCTET STRING,
        docsPnmCmtsOptProfChgCfgStatus             RowStatus
     }

docsPnmCmtsOptProfChgCfgIfIndex OBJECT-TYPE
     SYNTAX      InterfaceIndex
     MAX-ACCESS  not-accessible
     STATUS      current
     DESCRIPTION
        "This attribute is the ifIndex of the DS OFDM
         channel that the CMTS will instruct the CM to adjust it's
         profiles for."
     REFERENCE 
        "Information Model Mapping: CM-SP-CCAP-OSSI 
         ProfChgCfg::IfIndex"
     ::= { docsPnmCmtsOptProfChgCfgEntry 1 }

docsPnmCmtsOptProfChgCfgDsProfList OBJECT-TYPE
     SYNTAX      OCTET STRING (SIZE (1..4))
     MAX-ACCESS  read-create
     STATUS      current
     DESCRIPTION
        "This attribute is a list of N 1-byte downstream
         OFDM profile IDs assigned for the OFDM channel."
     REFERENCE 
        "Information Model Mapping: CM-SP-CCAP-OSSI 
         ProfChgCfg::DsProfList" 
     ::= { docsPnmCmtsOptProfChgCfgEntry 2 }

docsPnmCmtsOptProfChgCfgStatus OBJECT-TYPE
     SYNTAX      RowStatus
     MAX-ACCESS  read-create
     STATUS      current
     DESCRIPTION
        "The row status of this instance."
     ::= { docsPnmCmtsOptProfChgCfgEntry 3 }

-- ---------------------------------------------------------------------
-- The CMTS OPT Response Table
-- ---------------------------------------------------------------------
docsPnmCmtsOptRespTable OBJECT-TYPE
     SYNTAX      SEQUENCE OF DocsPnmCmtsOptRespEntry
     MAX-ACCESS  not-accessible
     STATUS      current
     DESCRIPTION
        "This table is used to read the OPT-RSP message for a given
         OFDM DS channel. One of the main issues for the modeling for
         OPT-RSP is that all OPT responses will not be alike.  Some
         tests will only require 1 test or maybe a combination of one
         or more tests.  As a result, this table needs to be able to
         gather the needed data for each CM and provide that to the PMA.
         Details of this operation can be found in MULPI Spec
         OFDM Downstream Profile Test Response (OPT-RSP).
         MER data from the CM will be recorded as a series of hex
         values (0x00 to 0xFF) that will represent the MER values that
         the CM has measured.  These values are gathered from the first
         active subcarrier to the last active subcarrier in the OFDM
         channel definition.  The data from the CM will not contain
         pairs of values (subcarrierId and MER value) but just the
         subcarrier MER value.  For the PMA to make sense of the data,
         the CCAP must provide the first active subcarrier to allow the
         PMA to know where it should start associating the values from
         the CM to the individual subcarriers defined in the channel.
         This information will need to be learned by the PMA from the 
         DsOfdmChannelStatus object (DsOfdmChannelStatus, FirstActiveSubcarrierNum). 
         Instances of this object are created when the response to an OptRequest
         is received by the CCAP.  Instances of this object may be removed by the
         CCAP in a vendor specific manner."
     REFERENCE 
        "Information Model Mapping: CM-SP-CCAP-OSSI 
         OptResp"
     ::= { docsPnmCmtsOptObjects 4 }

docsPnmCmtsOptRespEntry OBJECT-TYPE
     SYNTAX      DocsPnmCmtsOptRespEntry
     MAX-ACCESS  not-accessible
     STATUS      current
     DESCRIPTION
         "The conceptual row of the docsPnmCmtsOptRespTable.
          The conceptual rows do not persist across device resets."
     INDEX { docsPnmCmtsOptReqCmMacAddr,
            docsPnmCmtsOptReqDsOfdmChanCfgIndex,
            docsPnmCmtsOptReqDsOfdmProfCfgId }
     ::= { docsPnmCmtsOptRespTable 1 }

DocsPnmCmtsOptRespEntry ::=
    SEQUENCE {
        docsPnmCmtsOptRespStatus                    INTEGER,
        docsPnmCmtsOptRespFirstActiveSubcarrierNum  Unsigned32,
        docsPnmCmtsOptRespMerData                   OCTET STRING,
        docsPnmCmtsOptRespMerPassFailData           OCTET STRING,
        docsPnmCmtsOptRespNumSubcarriersBelowThresh Unsigned32,
        docsPnmCmtsOptRespSnrMarginData             Integer32,
        docsPnmCmtsOptRespCodewordCt                Counter32,
        docsPnmCmtsOptRespCorrectedCodewordCt       Counter32,
        docsPnmCmtsOptRespUncorrectableCodewordCt   Counter32,
        docsPnmCmtsOptRespNcpFieldCt                Counter32,
        docsPnmCmtsOptRespNcpCrcFailCt              Counter32
     }

docsPnmCmtsOptRespStatus OBJECT-TYPE
     SYNTAX      INTEGER {
                          other(0),
                          testing(1),
                          profileAlreadyUnderTest(2),
                          unavailableResources(3),
                          maxDurationExpired(4),
                          aborted(5),
                          complete(6),
                          profileAlreadyAssigned(7),
                          dsLockLost(8)
                         }
     MAX-ACCESS  read-only
     STATUS      current
     DESCRIPTION
        "This attribute allows the CCAP to return the status of a
         specific OPT test request.  The value of this attribute is
         found in the status portion of the OPT-RSP header that is
         returned from the CM when the OPT-REQ is received by the CM.
         The values include:
         other(0) -   The status is not one of the values below
         testing(1) - the CM has initiated the requested tests
         profileAlreadyUnderTest(2) - The CM received a request, but the
         profileId requested was already being used for an active test.
         unavailableResources(3) - The CM had an error with the request
         related to available resources to run the test collection.
         maxDurationExpired(4) - The CM has reported that for this test,
         the maximum duration value has expired.
         aborted(5) - The CM received an OPT-REQ request with an OpCode
         of abort and is aborting the tests requested.
         complete(6) - The CM has successfully completed the requested
         testing
         profileAlreadyAssigned(7) - The CM is reporting that the
         referenced profileId is already assigned and may not be used
         for the requested tests.
         dsLockLost(8) - The CM is reporting that the DS lock has been lost
         for this DS OFDM channel."
     REFERENCE 
        "Information Model Mapping: CM-SP-CCAP-OSSI 
         OptResp::Status"
     ::= { docsPnmCmtsOptRespEntry 1 }

docsPnmCmtsOptRespFirstActiveSubcarrierNum OBJECT-TYPE
     SYNTAX      Unsigned32 (148..7895)
     MAX-ACCESS  read-only
     STATUS      current
     DESCRIPTION
        "This attribute is the subcarrier index of the lowest
        subcarrier in the Occupied Bandwidth of the channel."
     REFERENCE 
        "Information Model Mapping: CM-SP-CCAP-OSSI 
         OptResp::FirstActiveSubcarrierNum"
     ::= { docsPnmCmtsOptRespEntry 2 }

docsPnmCmtsOptRespMerData OBJECT-TYPE
     SYNTAX      OCTET STRING (SIZE (0..7680))
     MAX-ACCESS  read-only
     STATUS      current
     DESCRIPTION
        "This attribute contains the MER data for the active subcarriers
         in the instance of the DsOfdmChannelCfg object.  The data represents
         Integer modulation error ratio measurements in 0.25 dB steps
         (0x00-0xFE represents 0-63.5 dB; 0xFF indicates no measurement
         available). These are encoded as a packed sequence of 8-bit
         values for N consecutive subcarriers (N less than or equal to
         7680) from lowest active subcarrier to the highest active
         subcarrier, including all the subcarriers in between.
         This attribute is a variable length and is dependent on the
         channel width and the number of active subcarriers that are
         available. This attribute is a channel level measurement and
         is independent of the profile
         being tested."
     REFERENCE 
        "Information Model Mapping: CM-SP-CCAP-OSSI 
         OptResp::MerData"
     ::= { docsPnmCmtsOptRespEntry 3 }

docsPnmCmtsOptRespMerPassFailData OBJECT-TYPE
     SYNTAX      OCTET STRING (SIZE (0..7680))
     MAX-ACCESS  read-only
     STATUS      current
     DESCRIPTION
        "This attribute contains a Pass/Fail indication for each
         subcarrier's RxMER (1 bit for each subcarrier). A value of 1
         indicates that the measured MER is greater than or equal to
         the target value in the OPT-REQ.
         A value of 0 indicates that the measured MER < target value
         in the OPT-REQ.  These are encoded as a sequence of 1-bit
         values for N consecutive subcarriers (N less than or equal to
         7680) from lowest active subcarrier."
     REFERENCE 
        "Information Model Mapping: CM-SP-CCAP-OSSI 
         OptResp::MerPassFailData"
     ::= { docsPnmCmtsOptRespEntry 4 }

docsPnmCmtsOptRespNumSubcarriersBelowThresh OBJECT-TYPE
     SYNTAX      Unsigned32
     MAX-ACCESS  read-only
     STATUS      current
     DESCRIPTION
        "This attribute indicates the number of subcarriers (less then
         or equal to 7680) whose RxMER is greater then or equal to the
         RxMER Margin below the RxMER target for the bitloading of the
         given subcarrier."
     REFERENCE 
        "Information Model Mapping: CM-SP-CCAP-OSSI 
         OptResp::NumSubcarriersBelowThresh"
     ::= { docsPnmCmtsOptRespEntry 5 }

docsPnmCmtsOptRespSnrMarginData OBJECT-TYPE
     SYNTAX      Integer32 (-128..127)
     UNITS       "QuarterdB"
     MAX-ACCESS  read-only
     STATUS      current
     DESCRIPTION
        "This attribute indicates the SNR margin of the candidate data
         profile (signed integer), in units of 0.25dB, calculation
         is as defined in the PHY4.0 Spec."
     REFERENCE 
        "Information Model Mapping: CM-SP-CCAP-OSSI 
         OptResp::SnrMarginData"
     ::= { docsPnmCmtsOptRespEntry 6 }

docsPnmCmtsOptRespCodewordCt OBJECT-TYPE
     SYNTAX      Counter32
     UNITS       "codewords"
     MAX-ACCESS  read-only
     STATUS      current
     DESCRIPTION
        "This attribute is a count of the measured number of codewords
         that the CM has successfully received during the testing
         interval for the profile being tested.  Unsigned integer
         count of codewords that were examined during testing.
         If Codeword Tagging is disabled, this count includes all
         codewords received on the profile in question for the
         duration of the test. If Codeword Tagging is enabled, this
         count includes only codewords received on the profile in
         question for the duration of the test for which the 'T' bit
         was set in the NCP pointing to the codeword. The location
         of the 'T' bit is specified in the PHYv4.0 Spec."
     REFERENCE 
        "Information Model Mapping: CM-SP-CCAP-OSSI 
         OptResp::CodewordCt"
     ::= { docsPnmCmtsOptRespEntry 7 }

docsPnmCmtsOptRespCorrectedCodewordCt OBJECT-TYPE
     SYNTAX      Counter32
     UNITS       "codewords"
     MAX-ACCESS  read-only
     STATUS      current
     DESCRIPTION
        "This attribute is a count of the measured number of codewords
         that the CM has successfully received and was able to correct
         during the testing interval for the profile being tested.
         Unsigned integer count of codewords that were examined during
         testing. If Codeword Tagging is disabled, this count includes
         all codewords received on the profile in question for the
         duration of the test. If Codeword Tagging is enabled, this
         count includes only codewords received on the profile in
         question for the duration of the test for which the 'T' bit
         was set in the NCP pointing to the codeword. The location of
         the 'T' bit is specified in the PHYv3.1 Spec."
     REFERENCE 
        "Information Model Mapping: CM-SP-CCAP-OSSI 
         OptResp::CorrectedCodewordCt"
     ::= { docsPnmCmtsOptRespEntry 8 }

docsPnmCmtsOptRespUncorrectableCodewordCt OBJECT-TYPE
     SYNTAX      Counter32
     UNITS       "codewords"
     MAX-ACCESS  read-only
     STATUS      current
     DESCRIPTION
        "This attribute is a count of the measured num of uncorrectable
         codewords that the CM has received during the testing interval
         for the profile being tested.  Unsigned integer count of
         codewords that failed pre-decoding LDPC syndrome check and
         passed BCH decoding. If Codeword Tagging is disabled, this
         count includes all codewords received on the profile in
         question for the duration of the test. If Codeword Tagging
         is enabled, this count includes only codewords received on
         the profile in question for the duration of the test for
         which the 'T' bit was set in the NCP pointing to the
         codeword. The location of the 'T' bit is specified in the
         PHYv3.1 Spec."
     REFERENCE 
        "Information Model Mapping: CM-SP-CCAP-OSSI 
         OptResp::UncorrectableCodewordCt"
     ::= { docsPnmCmtsOptRespEntry 9 }

docsPnmCmtsOptRespNcpFieldCt OBJECT-TYPE
     SYNTAX      Counter32
     MAX-ACCESS  read-only
     STATUS      current
     DESCRIPTION
        "This attribute records the number of NCP fields that were
         examined by the CM during the test interval."
     REFERENCE 
        "Information Model Mapping: CM-SP-CCAP-OSSI 
         OptResp::NcpFieldCt"
     ::= { docsPnmCmtsOptRespEntry 10 }

docsPnmCmtsOptRespNcpCrcFailCt OBJECT-TYPE
     SYNTAX      Counter32
     MAX-ACCESS  read-only
     STATUS      current
     DESCRIPTION
        "This attribute records the number of NCP fields that failed
         the NCP CRC check."
     REFERENCE 
        "Information Model Mapping: CM-SP-CCAP-OSSI 
         OptResp::NcpCrcFailCt"
     ::= { docsPnmCmtsOptRespEntry 11 }

-- ---------------------------------------------------------------------
-- The CMTS OPT MER Threshold Template  
-- ---------------------------------------------------------------------
docsPnmCmtsOptMerThreshTemplateTable OBJECT-TYPE
     SYNTAX      SEQUENCE OF DocsPnmCmtsOptMerThreshTemplateEntry
     MAX-ACCESS  not-accessible
     STATUS      current
     DESCRIPTION
        "For MER tests that require Pass or Fail criteria, it is necessary to define the
         parameters in a separate fashion as the OPT-REQ message needs these 
         values on a per modulation basis. This means that for each modulation 
         order defined in a profile, the OPT-REQ includes a TLV entry for the 
         required MER target value for each. A single threshold template, which
         consists of all instances of OptMerThresholdTemplate with the same 
         TemplateIndex, can be used in multiple OptReq objects.
         This table supports the creation and deletion of multiple instances."
     REFERENCE
        "Information Model Mapping: CM-SM-CCAP-OSSI
          OptMerThresholdTemplate "
     ::= { docsPnmCmtsOptObjects 5 }

docsPnmCmtsOptMerThreshTemplateEntry OBJECT-TYPE
     SYNTAX      DocsPnmCmtsOptMerThreshTemplateEntry
     MAX-ACCESS  not-accessible
     STATUS      current
     DESCRIPTION
         "The conceptual row of the docsPnmCmtsOptMerThreshTemplateTable.
          The conceptual rows do not persist across device resets."
     INDEX { docsPnmCmtsOptMerThreshTemplateIndex,
             docsPnmCmtsOptMerThreshTemplateModOrder }
     ::= { docsPnmCmtsOptMerThreshTemplateTable 1 }

DocsPnmCmtsOptMerThreshTemplateEntry ::=
    SEQUENCE {
        docsPnmCmtsOptMerThreshTemplateIndex                    Unsigned32,
        docsPnmCmtsOptMerThreshTemplateModOrder                 DsOfdmModulationType,
        docsPnmCmtsOptMerThreshTemplateRxMerVsBitloadingTarget  Unsigned32,
        docsPnmCmtsOptMerThreshTemplateRxMerMargin              Unsigned32,
        docsPnmCmtsOptMerThreshTemplateStatus                   RowStatus
     }

docsPnmCmtsOptMerThreshTemplateIndex  OBJECT-TYPE
   SYNTAX      Unsigned32 (1..255)
     MAX-ACCESS  not-accessible
     STATUS      current
     DESCRIPTION
        "This key represents the template index for all the modulations
         in a single template. Zero is reserved to mean no template in the 
         OptReq object."
       REFERENCE
        "Information Model Mapping: CM-SM-CCAP-OSSI 
          OptMerThresholdTemplate::TemplateIndex"
     ::= { docsPnmCmtsOptMerThreshTemplateEntry 1 }

docsPnmCmtsOptMerThreshTemplateModOrder OBJECT-TYPE
     SYNTAX      DsOfdmModulationType
     MAX-ACCESS  not-accessible
     STATUS      current
     DESCRIPTION
        "This key specifies the modulation types supported by the CCAP
         modulator. The modulation zeroValued(2) is not valid for
         MER threshold margin calculations.  This attribute corresponds
         to the TLV 2.1 in the OPT-REQ."
       REFERENCE
        "Information Model Mapping: CM-SM-CCAP-OSSI 
          OptMerThresholdTemplate::ModulationOrder "
     ::= { docsPnmCmtsOptMerThreshTemplateEntry 2 }

docsPnmCmtsOptMerThreshTemplateRxMerVsBitloadingTarget OBJECT-TYPE
     SYNTAX      Unsigned32 (0..255)
     UNITS       "quarterdB"
     MAX-ACCESS  read-create
     STATUS      current
     DESCRIPTION
        "This attribute is the required value for the profile RxMER (refer to OPT-RSP) 
          in units of 0.25dB (0xFF is 63.75dB). This is the required RxMER value that the
          CM uses to calculate the SNR margin for the profile. The default values for 
          this attribute are defined in [PHYv4.0] CM Minimum CNR Performance 
          in AWGN Channel. This attribute corresponds to the TLV 2.2 in the OPT-REQ."
     REFERENCE
        "Information Model Mapping: CM-SM-CCAP-OSSI 
          OptMerThresholdTemplate::RxMerVsBitloadingTarget"
     ::= { docsPnmCmtsOptMerThreshTemplateEntry 3 }

docsPnmCmtsOptMerThreshTemplateRxMerMargin OBJECT-TYPE
     SYNTAX      Unsigned32 
     UNITS       "dB"
     MAX-ACCESS  read-create
     STATUS      current
     DESCRIPTION
        "The CM reports the number of subcarriers with a measured RxMER 
          value that is at least this value below the target RxMER in units of 
          0.25dB (0xFF is 63.75dB) for the bitloading of the given subcarrier 
          in the OPT-RSP message. This attribute corresponds to the
         TLV 2.3 in the OPT-REQ."
      REFERENCE
        "Information Model Mapping: CM-SM-CCAP-OSSI 
          OptMerThresholdTemplate::RxMerMargin "
     ::= { docsPnmCmtsOptMerThreshTemplateEntry 4 }

docsPnmCmtsOptMerThreshTemplateStatus OBJECT-TYPE
     SYNTAX      RowStatus
     MAX-ACCESS  read-create
     STATUS      current
     DESCRIPTION
        "The row status of this instance."
     ::= { docsPnmCmtsOptMerThreshTemplateEntry 5 }


-- ---------------------------------------------------------------------
-- CMTS Upstream Triggered Spectrum Capture (UTSC) PNM Objects
-- ---------------------------------------------------------------------

-- ---------------------------------------------------------------------
-- The CMTS Upstream Triggered Spectrum Capture Capabilities Table
-- ---------------------------------------------------------------------
docsPnmCmtsUtscCapabTable OBJECT-TYPE
     SYNTAX      SEQUENCE OF DocsPnmCmtsUtscCapabEntry
     MAX-ACCESS  not-accessible
     STATUS      current
     DESCRIPTION
        "This table exposes capabilities supported by the CCAP
         for Upstream Triggered Spectrum Capture trigger modes, data
         output formats, and windowing function used when performing
         the discrete Fourier transform."
     REFERENCE
        "Information Model Mapping: CM-SM-CCAP-OSSI 
         UsTriggeredSpectrumCaptureCapab"
     ::= { docsPnmCmtsUtscObjects 1 }

docsPnmCmtsUtscCapabEntry OBJECT-TYPE
     SYNTAX      DocsPnmCmtsUtscCapabEntry
     MAX-ACCESS  not-accessible
     STATUS      current
     DESCRIPTION
         "The conceptual row of the docsPnmCmtsUtscCapabTable.
          The conceptual rows persist across device resets.
          A separate entry exists for every Upstream RF Port
          which supports the capability."
     INDEX { ifIndex }
     ::= { docsPnmCmtsUtscCapabTable 1 }

DocsPnmCmtsUtscCapabEntry ::=
    SEQUENCE {
        docsPnmCmtsUtscCapabTriggerMode           BITS,
        docsPnmCmtsUtscCapabOutputFormat          BITS,
        docsPnmCmtsUtscCapabWindow                BITS,
        docsPnmCmtsUtscCapabDescription           SnmpAdminString
        }

docsPnmCmtsUtscCapabTriggerMode OBJECT-TYPE
     SYNTAX      BITS {
                      other(0),
                      freeRunning(1),
                      miniSlotCount(2),
                      sid(3),
                      idleSid(4),
                      cmMac(5),
                      quietProbeSymbol(6),
                      burstIuc(7),
                      timestamp(8),
                      activeProbeSymbol(9)
                      }
     MAX-ACCESS  read-only
     STATUS      current
     DESCRIPTION
        "This attribute indicates which of the upstream triggered
         spectrum capture function trigger modes is supported by the
         CCAP. The attribute is reported in BITS format, with
         value 0 for each bit definition indicating the CCAP does not
         support the corresponding TriggerMode and value 1 for each bit
         definition indicating the CCAP supports the corresponding
         trigger mode. See the description of the
         UsTriggeredSpectrumCaptureCfg object TriggerMode attribute for
         more information about CCAP upstream triggered spectrum
         capture trigger modes. The value other(0) is provided for
         vendor proprietary and future extensions."
      REFERENCE
        "Information Model Mapping: CM-SM-CCAP-OSSI 
         UsTriggeredSpectrumCaptureCapab::TriggerMode"
     ::= { docsPnmCmtsUtscCapabEntry 1 }

docsPnmCmtsUtscCapabOutputFormat OBJECT-TYPE
     SYNTAX      BITS {
                      other(0),
                      timeIQ(1),
                      fftPower(2),
                      rawAdc(3),
                      fftIQ(4),
                      fftAmplitude(5),
                      fftDb(6)
                      }
     MAX-ACCESS  read-only
     STATUS      current
     DESCRIPTION
        "This attribute indicates which of the upstream triggered
         spectrum capture function data output formats are supported by
         the CCAP. This attribute is reported in BITS format,
         with value 0 for each bit definition indicating the CCAP does
         not support the corresponding OutputFormat and value for each
         bit definition 1 indicating the CCAP supports the
         corresponding output data format. See the description of the
         UsTriggeredSpectrumCaptureCfg object OutputFormat attribute for
         more information about CCAP upstream triggered spectrum capture
         output formats. The value other(0) is provided for vendor
         proprietary and future extensions."
     REFERENCE
        "Information Model Mapping: CM-SM-CCAP-OSSI 
         UsTriggeredSpectrumCaptureCapab::OutputFormat"
     ::= { docsPnmCmtsUtscCapabEntry 2 }

docsPnmCmtsUtscCapabWindow OBJECT-TYPE
     SYNTAX      BITS {
                      other(0),
                      rectangular(1),
                      hann(2),
                      blackmanHarris(3),
                      hamming(4),
                      flatTop(5),
                      gaussian(6),
                      chebyshev(7)
                      }
     MAX-ACCESS  read-only
     STATUS      current
     DESCRIPTION
        "This attribute indicates which of the upstream triggered
         spectrum capture function window formats are supported by the
         CCAP. This attribute is reported in BITS format, with
         value for each bit definition 0 indicating the CCAP does not
         support the corresponding Window option and value for each bit
         definition 1 indicating the CCAP supports the corresponding
         Window option. See the description of the
         UsTriggeredSpectrumCaptureCfg object Window attribute for more
         information about CCAP upstream triggered spectrum capture
         window options. The value other(0) is provided for vendor
         proprietary and future extensions."
     REFERENCE
        "Information Model Mapping: CM-SM-CCAP-OSSI 
         UsTriggeredSpectrumCaptureCapab::Window"
     ::= { docsPnmCmtsUtscCapabEntry 3 }

docsPnmCmtsUtscCapabDescription OBJECT-TYPE
     SYNTAX      SnmpAdminString
     MAX-ACCESS  read-only
     STATUS      current
     DESCRIPTION
        "This attribute reports a textual description of a CCAPs
         upstream triggered spectrum capture capabilities.  The format
         is vendor-specific.  Example content can include, but is not
         limited to:
         - Center Frequency range and resolution
         - Frequency Span range and resolution
         - Sampling rate each frequency span
         - Averaging range and resolution
         - Averaging method
         - Number of time domain IQ samples
         - Number of FFT bins"
     REFERENCE
        "Information Model Mapping: CM-SM-CCAP-OSSI 
         UsTriggeredSpectrumCaptureCapab::Description"
     ::= { docsPnmCmtsUtscCapabEntry 4 }

-- ---------------------------------------------------------------------
-- The CMTS Upstream Triggered Spectrum Capture Config Table
-- ---------------------------------------------------------------------
docsPnmCmtsUtscCfgTable OBJECT-TYPE
     SYNTAX      SEQUENCE OF DocsPnmCmtsUtscCfgEntry
     MAX-ACCESS  not-accessible
     STATUS      current
     DESCRIPTION
        "This table provides configuration functionality for the
         Upstream Triggered Spectrum Capture function.
         The CCAP is not required to persist instances of this object across reinitializations.
         The CCAP should reject configuring a value for the DestinationIndex of the
         UsTriggeredSpectrumCaptureCfg object if that value does not exist in the corresponding
         DestinationIndex attribute of the DataTransferCfg instance"
     REFERENCE
        "Information Model Mapping: CM-SM-CCAP-OSSI 
         UsTriggeredSpectrumCaptureCfg"
     ::= { docsPnmCmtsUtscObjects 2 }

docsPnmCmtsUtscCfgEntry OBJECT-TYPE
     SYNTAX      DocsPnmCmtsUtscCfgEntry
     MAX-ACCESS  not-accessible
     STATUS      current
     DESCRIPTION
         "The conceptual row of the docsPnmCmtsUtscCfgTable.
          The conceptual rows do not persist across device resets.
          A separate entry exists for every Upstream RF Port
          which supports the capability.
          This table supports the creation and deletion of at least one
          instance."
     INDEX { ifIndex,
             docsPnmCmtsUtscCfgIndex }
     ::= { docsPnmCmtsUtscCfgTable 1 }

DocsPnmCmtsUtscCfgEntry ::=
    SEQUENCE {
        docsPnmCmtsUtscCfgIndex                 Unsigned32,
        docsPnmCmtsUtscCfgLogicalChIfIndex      InterfaceIndexOrZero,
        docsPnmCmtsUtscCfgTriggerMode           INTEGER,
        docsPnmCmtsUtscCfgMinislotCount         Unsigned32,
        docsPnmCmtsUtscCfgSid                   Unsigned32,
        docsPnmCmtsUtscCfgCmMacAddr             MacAddress,
        docsPnmCmtsUtscCfgTimestamp             TimeStamp,
        docsPnmCmtsUtscCfgCenterFreq            Unsigned32,
        docsPnmCmtsUtscCfgSpan                  Unsigned32,
        docsPnmCmtsUtscCfgNumBins               Unsigned32,
        docsPnmCmtsUtscCfgAveraging             Unsigned32,
        docsPnmCmtsUtscCfgFilename              SnmpAdminString,
        docsPnmCmtsUtscCfgQualifyCenterFreq     Unsigned32,
        docsPnmCmtsUtscCfgQualifyBw             Unsigned32,
        docsPnmCmtsUtscCfgQualifyThrshld        TenthdB,
        docsPnmCmtsUtscCfgWindow                INTEGER,
        docsPnmCmtsUtscCfgOutputFormat          INTEGER,
        docsPnmCmtsUtscCfgRepeatPeriod          Unsigned32,
        docsPnmCmtsUtscCfgFreeRunDuration       Unsigned32,
        docsPnmCmtsUtscCfgTriggerCount          Unsigned32,
        docsPnmCmtsUtscCfgStatus                RowStatus,
        docsPnmCmtsUtscCfgBurstIuc              INTEGER,
        docsPnmCmtsUtscCfgMaxResultsPerFile     Unsigned32,
        docsPnmCmtsUtscCfgDestinationIndex      Unsigned32
        }

docsPnmCmtsUtscCfgIndex OBJECT-TYPE
     SYNTAX      Unsigned32 (0..4294967295)
     MAX-ACCESS  not-accessible
     STATUS      current
     DESCRIPTION
        "This key attribute is a unique identifier for a particular set
         of configuration settings. If the CCAP does not support
         multiple Upstream Triggered Spectrum Sample Capture
         configuration settings, the CCAP only supports a value of 1
         for this attribute and reject any attempt to configure it to a
         value other than 1."
     REFERENCE
        "Information Model Mapping: CM-SM-CCAP-OSSI 
         UsTriggeredSpectrumCaptureCfg::Index"
     ::= { docsPnmCmtsUtscCfgEntry 1 }

docsPnmCmtsUtscCfgLogicalChIfIndex OBJECT-TYPE
     SYNTAX      InterfaceIndexOrZero
     MAX-ACCESS  read-create
     STATUS      current
     DESCRIPTION
        "For SC-QAM upstream channels, this attribute is the interface
         index of the logical upstream channel (ifIndex 205) to which the
         sample capture trigger applies, when TriggerMode is miniSlotCount, 
         sid, idleSid, quietProbeSymbol, and burstIuc. 
        
        For OFDMA upstream channels this attribute is the interface index
        of the physical OFDMA upstream channel (ifIndex 278) to which the
        sample capture trigger applies, when TriggerMode is miniSlotCount,
        sid, idleSid, quietProbeSymbol, and burstIuc.
          
        The value 0 means the CCAP is triggering on something specific
        to the upstream RF port, not a specific channel.

         When the value of LogicalChannelIndex is the ifIndex of a     
         physical or logical channel and upstream triggered spectrum                     
         sample capture is initiated, the CCAP triggers on the                           
         assigned trigger mode event for the physical or logical channel                            
         indicated by the value of LogicalChannelIndex."
     REFERENCE
        "Information Model Mapping: CM-SM-CCAP-OSSI 
         UsTriggeredSpectrumCaptureCfg::LogicalChIfIndex"
     DEFVAL { 0 }
     ::= { docsPnmCmtsUtscCfgEntry 2 }

docsPnmCmtsUtscCfgTriggerMode OBJECT-TYPE
     SYNTAX      INTEGER {
                          other(1),
                          freeRunning(2),
                          miniSlotCount(3),
                          sid(4),
                          idleSid(5),
                          cmMac(6),
                          quietProbeSymbol(7),
                          burstIuc(8),
                          timestamp(9),
                          activeProbeSymbol(10)
                          }
     MAX-ACCESS  read-create
     STATUS      current
     DESCRIPTION
        "This attribute is used to control the trigger mode for the
         Upstream Triggered Spectrum Analysis sample capture. Values
         allowed for this attribute are listed and described below.
         Each trigger mode requires the Enable attribute to be set to
         true as well as the proper configuration settings applied which
         are applicable to the specific trigger mode.

         other: The CCAP initiates sampling the upstream spectrum as the
         result of a trigger condition not defined in this specification.

         freeRunning: The CCAP immediately initiates sampling and
         continues sampling until the length of time configured in
         attribute FreeRunDuration has transpired. Sampling terminates
         when the length of time configured in FreeRunDuration has
         elapsed or when FFT is disabled.  The interval between
         captures is RepeatPeriod, or the minimum period supported by
         the CCAP, whichever is greater.

         miniSlotCount: The CCAP initiates sampling when the minislot
         number equals the value configured for attribute MinislotCount.

         sid:The CCAP immediately initiates capturing samples
         corresponding to the Service Flow identified with the
         Service Identifier (SID) numbered with the value of
         attribute Sid. The CCAP continues to sample the configured
         upstream spectrum after being triggered on transmissions
         corresponding to the specified SID until FFT is disabled or a
         new configuration is applied.

         idleSid: The CCAP immediately initiates capturing samples
         during an idle period selected by the CCAP. The CCAP will
         continue to sample the configured upstream spectrum during
         transmissions corresponding to the idle SID until FFT is
         disabled or a new configuration is applied.

         cmMacAddr: The CCAP immediately initiates sampling data on a
         grant for any SID assigned to the cable modem whose MAC address
         is the value of attribute CmMac. The CCAP continues to sample
         the configured upstream spectrum during transmissions
         corresponding to the configured CM MAC until FFT is disabled
         or a new configuration is applied.

         quietProbeSymbol: The CCAP immediately initiates sampling data
         when a configured OFDMA Quiet Probe Symbol occurs. The CCAP
         will continue to sample the configured upstream spectrum during
         Quiet Probe Symbols until FFT is disabled or a new
         configuration is applied.
         The Upstream Triggered Spectrum Capture test with
         quietProbeSymbol trigger is different from the Upstream Capture
         for Active and Quiet Probes PNM feature in that the Upstream
         Triggered Spectrum Capture test is more general than the Upstream
         Capture for Active and Quiet Probes test. Upstream Triggered
         Spectrum Capture test can be done in any band, while the Upstream
         Capture for Active and Quiet Probes test is specifically for an
         OFDMA channel.

         burstIuc: The CCAP performs a sample capture when triggered by a
         grant for the IUC(Interval Usage Code), issued by the CCAP.
         If theTriggerCount is greater than one, then the capture is
         repeated when triggered by successive grants to the IUC  until
         the number of captures equals the TriggerCount. This mode can be
         used for triggering a spectrum capture for either an SC-QAM or
         OFDMA channel.

         timestamp: The CCAP performs a sample capture when the
         configured timestamp occurs.

         activeProbeSymbol: The CCAP performs a sample capture
         when triggered by a grant to the configured SID in a P-MAP.
         If the TriggerCount is greater than one, then the capture is
         repeated when triggered by successive grants to the SID
         configured for the active probe until the number of captures
         equals the TriggerCount. This mode can be used for triggering
         a spectrum capture for an  OFDMA channel only.

         Note that if the CCAP supports only one set of Upstream
         Triggered Spectrum Capture configuration, then if a test is
         configured with timestamp trigger it effectively blocks any
         other test setup and execution until it completes since setting
         up the other test will overwrite the timestamp test
         configuration."
     REFERENCE
        "Information Model Mapping: CM-SM-CCAP-OSSI 
         UsTriggeredSpectrumCaptureCfg::TriggerMode"
     DEFVAL { freeRunning }
     ::= { docsPnmCmtsUtscCfgEntry 3 }

docsPnmCmtsUtscCfgMinislotCount OBJECT-TYPE
     SYNTAX      Unsigned32
     MAX-ACCESS  read-create
     STATUS      current
     DESCRIPTION
        "This attribute specifies the minislot number at the beginning
         of which the CCAP starts the upstream spectrum sample capture.
         This attribute is applicable only when the TriggerMode
         attribute is set to MiniSlotCount and is ignored if
         TriggerMode is set to any other value."
     REFERENCE
        "Information Model Mapping: CM-SM-CCAP-OSSI 
         UsTriggeredSpectrumCaptureCfg::MinislotCount"
     DEFVAL { 0 }
     ::= { docsPnmCmtsUtscCfgEntry 4 }

docsPnmCmtsUtscCfgSid OBJECT-TYPE
     SYNTAX      Unsigned32
     MAX-ACCESS  read-create
     STATUS      current
     DESCRIPTION
        "This attribute specifies the SID corresponding to the CM which
         is granted a burst opportunity for the purpose of Upstream
         Triggered Spectrum Analysis.
         This attribute is applicable only when the TriggerMode attribute is
         set to Sid and is ignored if TriggerMode is set to any other value."
     REFERENCE
        "Information Model Mapping: CM-SM-CCAP-OSSI 
         UsTriggeredSpectrumCaptureCfg::Sid"
     DEFVAL { 0 }
     ::= { docsPnmCmtsUtscCfgEntry 5 }

docsPnmCmtsUtscCfgCmMacAddr OBJECT-TYPE
     SYNTAX      MacAddress
     MAX-ACCESS  read-create
     STATUS      current
     DESCRIPTION
        "This attribute specifies from which cable modem the CCAP will
         capture upstream transmissions.
         The CCAP triggers upstream spectrum sample capture on a grant
         for any SID assigned to the CM whose MAC address is configured in
         this attribute, and capture upstream spectrum samples when the
         burst corresponding to that grant is received by the CCAP. This
         attribute is used when the TriggerMode is CmMac and is an
         alternative to using Sid for the TriggerMode. This attribute is
         ignored if TriggerMode is set to any value other than CmMac."
     REFERENCE
        "Information Model Mapping: CM-SM-CCAP-OSSI 
         UsTriggeredSpectrumCaptureCfg::CmMacAddr"
     DEFVAL { '000000000000'H }
     ::= { docsPnmCmtsUtscCfgEntry 6 }

docsPnmCmtsUtscCfgTimestamp OBJECT-TYPE
     SYNTAX      TimeStamp
     MAX-ACCESS  read-create
     STATUS      current
     DESCRIPTION
        "This attribute specifies the specific time in the future
         when upstream spectrum sample capture is required to be
         initiated. If the FreeRunDuration and RepeatPeriod are both
         greater than zero, the capture repeats in freeRunning mode
         at a rate equal to the RepeatPeriod for the FreeRunDuration.
         If either the RepeatPeriod or FreeRunDuration is equal to zero,
         then only a single capture is performed when triggered by the
         timestamp. When the TriggerMode is 'timestamp' the Upstream Channel
         InterfaceIndex is ignored. This mode can be used for the entire
         upstream spectrum and is independent of channel type.
         
         If TriggerMode is set to 'timestamp', configuration settings have been applied, 
         and InitiateTest is true, the CCAP should initiate sampling when the configured 
         timestamp occurs. The CCAP will continue to sample the configured upstream spectrum 
         until FFT is disabled or a new configuration is applied; however, a single capture
         typically is made in this mode."
     REFERENCE
        "Information Model Mapping: CM-SM-CCAP-OSSI 
         UsTriggeredSpectrumCaptureCfg::Timestamp"
     DEFVAL { 0 }
     ::= { docsPnmCmtsUtscCfgEntry 7 }

docsPnmCmtsUtscCfgCenterFreq OBJECT-TYPE
     SYNTAX      Unsigned32
     UNITS       "Hertz"
     MAX-ACCESS  read-create
     STATUS      current
     DESCRIPTION
        "This attribute specifies the center frequency of the upstream
         spectrum to be sampled for analysis.   When this attribute is
         read, it provides the actual center frequency, which may be
         different from the requested (configured) center frequency
         due to implementation effects."
     REFERENCE
        "Information Model Mapping: CM-SM-CCAP-OSSI 
         UsTriggeredSpectrumCaptureCfg::CenterFreq"
     ::= { docsPnmCmtsUtscCfgEntry 8 }

docsPnmCmtsUtscCfgSpan OBJECT-TYPE
     SYNTAX      Unsigned32
     UNITS       "Hertz"
     MAX-ACCESS  read-create
     STATUS      current
     DESCRIPTION
        "This attribute determines the frequency span of the upstream
         spectrum sample capture.  When this attribute is read, it
         provides the actual span, which may be different from the
         requested (configured) span due to implementation effects."
     REFERENCE
        "Information Model Mapping: CM-SM-CCAP-OSSI 
         UsTriggeredSpectrumCaptureCfg::Span"
     ::= { docsPnmCmtsUtscCfgEntry 9 }

docsPnmCmtsUtscCfgNumBins OBJECT-TYPE
     SYNTAX      Unsigned32 (0..65535)
     MAX-ACCESS  read-create
     STATUS      current
     DESCRIPTION
        "This attribute determines the number of frequency bins or
         samples per span when sampling the upstream spectrum. When
         this attribute is read, it provides the actual number of bins,
         which may be different from the requested (configured) number
         of bins due to implementation effects.  The number of bins is
         typically less than the FFT length in use, due to filter
         rolloff at the edges of the analysis band.  A larger number
         of frequency bins will result in better frequency resolution,
         for a given frequency span."
     REFERENCE
        "Information Model Mapping: CM-SM-CCAP-OSSI 
         UsTriggeredSpectrumCaptureCfg::NumBins"
     ::= { docsPnmCmtsUtscCfgEntry 10 }

docsPnmCmtsUtscCfgAveraging OBJECT-TYPE
     SYNTAX      Unsigned32 (0..255)
     UNITS       "Samples"
     MAX-ACCESS  read-create
     STATUS      current
     DESCRIPTION
        "This attribute specifies whether the CCAP is to average
         spectral frequency domain sample power to remove spurious
         spectral peaks and troughs, and the number of samples to use
         to calculate the average power.
         The CCAP should not calculate the average of the upstream
         spectrum samples when the value of this attribute is zero.
         The CCAP should calculate the average power of upstream spectrum
         samples, over the number of samples specified by this attribute
         when the value of is nonzero.
         The CCAP should use quantities in the linear power domain when
         performing time averaging over multiple spectra.
         Time averaging provides for a smoother resulting spectrum. In time averaging, 
         the spectrum is captured multiple times, and each FFT bin is averaged over the 
         successive values in that bin to provide the final spectrum value for that bin. 
         A leaky integrator may be used to perform the averaging. 
         Let x = x_I + j*x_Q be the vector of time domain input samples to the FFT and 
         y = y_I + j*y_Q be the vector of complex output frequency bin values of the FFT. 
         Then p = |y|^2 = y_I^2 + y_Q^2 is the power or squared magnitude of the bin values 
         and r = |y| = sqrt(y_I^2 + y_Q^2) is the magnitude of the bin values. 
         The values may be converted to dB using s = 10*log10(p) = 20*log10(r). 
         Only values of p are used for time averaging. Magnitude values need to be squared 
         before averaging. dB values need to be converted into linear power using p = 10^(s/10)
         before averaging; after averaging, the smoothed bin values may be converted back to dB."
     REFERENCE
        "Information Model Mapping: CM-SM-CCAP-OSSI 
         UsTriggeredSpectrumCaptureCfg::Averaging"
     DEFVAL { 0 }
     ::= { docsPnmCmtsUtscCfgEntry 11 }

docsPnmCmtsUtscCfgFilename OBJECT-TYPE
     SYNTAX      SnmpAdminString
     MAX-ACCESS  read-create
     STATUS      current
     DESCRIPTION
        "This attribute specifies the name of the file with the upstream
         triggered spectrum capture data at the CCAP that is to be
         transferred from the CCAP using TFTP to the PNM server or other
         TFTP client. The content of the sample data file transferred
         from the CCAP using TFTP is the same as the content returned in
         attribute Output of the corresponding Result table.

         If the value of this attribute is an empty string, then a
         default filename value will be used. Otherwise, the value set
         will be used as the filename. If a default filename is
         generated, then that value will be returned in this attribute
         and will represent the filename that was used for the test.
         All subsequent tests should set this attribute to a meaningful
         value or to an 'empty string' value (to generate a new default
         filename) before starting a new test.

         If a default filename value is used, it is generated as the test
         name, plus a unique CCAP identifier (either a loopback address
         (IPv4 or IPv6) or FQDN), plus the current timestamp and the
         ifIndex of the interface on which the test runs. The timestamp
         is formatted as shown below:
          <Year:4d>-<Month:2d>-<Day:2d>_<Hour:2d>:<Minute:2d>:<Second:2d>.<Millisecond:3d>

         Hence, the format would be:
         PNMCcapUsSpecAn_<Unique CCAP Identifier>_<Timestamp>_<ifIndex>

         For example, the upstream spectrum sample capture filename format
         would be as shown below:
         PNMCcapUsSpecAn_ccap1.boulder.cablelabs.com_2018-06-26_10:50:14.451_24935767

         Refer to the Reference for the Format of upstream triggered
         spectrum capture file."
     REFERENCE
        "Information Model Mapping: CM-SM-CCAP-OSSI 
         UsTriggeredSpectrumCaptureCfg::Filename"
     DEFVAL { "" }
     ::= { docsPnmCmtsUtscCfgEntry 12 }

docsPnmCmtsUtscCfgQualifyCenterFreq OBJECT-TYPE
     SYNTAX      Unsigned32
     UNITS       "Hertz"
     MAX-ACCESS  read-create
     STATUS      current
     DESCRIPTION
        "This attribute specifies the center frequency of a band that is
         used to qualify a spectrum for upload.  The average of the FFT
         linear power values in this band is computed and compared to a
         threshold.  If the average power in the band is below the
         threshold, the spectrum is discarded.  If the power average is
         greater than or equal to the threshold, the spectrum is
         considered qualified."
     REFERENCE
        "Information Model Mapping: CM-SM-CCAP-OSSI 
         UsTriggeredSpectrumCaptureCfg::QualifyCenterFreq"
     DEFVAL { 0 }
     ::= { docsPnmCmtsUtscCfgEntry 13 }

docsPnmCmtsUtscCfgQualifyBw OBJECT-TYPE
     SYNTAX      Unsigned32
     UNITS       "Hertz"
     MAX-ACCESS  read-create
     STATUS      current
     DESCRIPTION
        "This attribute specifies the bandwidth of a band that is used
         to qualify a spectrum for upload.  The average of the FFT
         linear power values in this band is computed and compared to a
         threshold.  If the average power in the band is below the
         threshold, the spectrum is discarded.  If the power average is
         greater than or equal to the threshold, the spectrum is
         considered qualified."
     REFERENCE
        "Information Model Mapping: CM-SM-CCAP-OSSI 
         UsTriggeredSpectrumCaptureCfg::QualifyBw"
     DEFVAL { 5120000 }
     ::= { docsPnmCmtsUtscCfgEntry 14 }

docsPnmCmtsUtscCfgQualifyThrshld OBJECT-TYPE
     SYNTAX      TenthdB (-2147483648..2147483647)
     UNITS       "dB"
     MAX-ACCESS  read-create
     STATUS      current
     DESCRIPTION
        "This attribute specifies the threshold applied to qualify a
         spectrum for upload.  The average of the FFT linear power
         values in the specified band is computed and compared to this
         threshold.  If the average power in the band is below the
         threshold, the spectrum is discarded.  If the power average
         is greater than or equal to the threshold, the spectrum is
         considered qualified.  If this threshold is set to -100 dB or
         lower, the threshold qualification feature is disabled (all
         spectra are then considered qualified)."
     REFERENCE
        "Information Model Mapping: CM-SM-CCAP-OSSI 
         UsTriggeredSpectrumCaptureCfg::QualifyThrshld"
     DEFVAL { -100 }
     ::= { docsPnmCmtsUtscCfgEntry 15 }

docsPnmCmtsUtscCfgWindow OBJECT-TYPE
     SYNTAX      INTEGER {
                         other(1),
                         rectangular(2),
                         hann(3),
                         blackmanHarris(4),
                         hamming(5),
                         flatTop(6),
                         gaussian(7),
                         chebyshev(8)
                         }
     MAX-ACCESS  read-create
     STATUS      current
     DESCRIPTION
        "This attribute specifies the windowing function that will be
         used when performing the discrete Fourier transform for the
         upstream spectrum analysis. Use of 'modern' windowing functions
         not yet defined will likely be specified as 'other'.

         The CCAP is capable of implementing rectangular windowing
         and at least one of the following other window types when
         performing discrete Fourier transform on upstream spectrum
         sample data:
         - Hann windowing
         - Blackman Harris windowing.

         The CCAP should implement Hamming windowing for performing
         discrete Fourier transform on upstream spectrum sample data.

         The CCAP may implement Flat Top windowing for performing
         discrete Fourier transform on upstream spectrum sample data.

         The CCAP may implement Gaussian windowing for performing
         discrete Fourier transform on upstream spectrum sample data.

         The CCAP may implement Chebyshev windowing for performing
         discrete Fourier transform on upstream spectrum sample data."
     REFERENCE
        "Information Model Mapping: CM-SM-CCAP-OSSI 
         UsTriggeredSpectrumCaptureCfg::Window"
     DEFVAL { rectangular }
     ::= { docsPnmCmtsUtscCfgEntry 16 }

docsPnmCmtsUtscCfgOutputFormat OBJECT-TYPE
     SYNTAX      INTEGER {
                         timeIQ(1),
                         fftPower(2),
                         rawAdc(3),
                         fftIQ(4),
                         fftAmplitude(5),
                         fftDb(6)
                         }
     MAX-ACCESS  read-create
     STATUS      current
     DESCRIPTION
        "This attribute specifies the format of the data returned in the
         upstream spectrum sample capture file and in the Output
         attribute of the Results table.

         The CCAP is capable of reporting upstream spectrum sample
         FFT input data in complex time-domain in-phase and quadrature
         (I/Q) format. The enumeration value for complex time-domain I/Q
         format is timeIQ.

         The CCAP uses 4 bytes per upstream spectrum sample to
         represent the data when reporting in complex time-domain
         I/Q format.

         The CCAP is capable of reporting upstream spectrum sample
         FFT output data in power format. The enumeration value for
         power format is fftPower.

         The CCAP uses 4 bytes per bin to represent upstream
         spectrum sample FFT output data when reporting upstream
         spectrum sample data in power format.

         The CCAP may be capable of reporting upstream spectrum sample
         real FFT input data in raw analog-to-digital converter (ADC)
         output format. The enumeration value for raw ADC output format
         is rawAdc.

         The CCAP uses 2 bytes per upstream spectrum sample to
         represent the data when reporting in raw ADC output format.

         The CCAP may support reporting of upstream spectrum sample
         FFT output data in I/Q format. The enumeration value for I/Q
         format is fftIQ.

         The CCAP uses 4 bytes per bin to represent FFT output data
         when reporting upstream spectrum sample data in I/Q format.

         The CCAP may support reporting of upstream spectrum sample FFT
         output data in amplitude format. The enumeration value for
         amplitude format is fftAmplitude.

         The CCAP uses 2 bytes per bin to represent upstream
         spectrum sample FFT output data when reporting upstream
         spectrum sample data in amplitude format.

         The CCAP may support reporting of upstream spectrum sample FFT
         data in dB format using units of hundredths dB. The enumeration
         value for spectrum amplitude format is fftDb.

         The CCAP uses 2 bytes per bin to represent upstream spectrum
         sample FFT output data when reporting in dB format.

         The CCAP rejects any attempt to set OutputFormat to an
         optional value not supported by the CCAP."
     REFERENCE
        "Information Model Mapping: CM-SM-CCAP-OSSI 
         UsTriggeredSpectrumCaptureCfg::OutputFormat"
     DEFVAL { fftPower }
     ::= { docsPnmCmtsUtscCfgEntry 17 }

docsPnmCmtsUtscCfgRepeatPeriod OBJECT-TYPE
     SYNTAX      Unsigned32
     UNITS       "Microseconds"
     MAX-ACCESS  read-create
     STATUS      current
     DESCRIPTION
        "This attribute specifies the interval in microseconds between
         consecutive triggers for FFT sample capture.  The CCAP is
         permitted to trigger at larger intervals if unable to support
         the requested interval. Configuring a zero value indicates
         the test is to run once only.

         The CCAP rejects an attempt to set RepeatPeriod to a value
         greater than the current value of FreeRunDuration."
     REFERENCE
        "Information Model Mapping: CM-SM-CCAP-OSSI 
         UsTriggeredSpectrumCaptureCfg::RepeatPeriod"
     DEFVAL { 100000 }
     ::= { docsPnmCmtsUtscCfgEntry 18 }

docsPnmCmtsUtscCfgFreeRunDuration OBJECT-TYPE
     SYNTAX      Unsigned32
     UNITS       "Milliseconds"
     MAX-ACCESS  read-create
     STATUS      current
     DESCRIPTION
        "This attribute specifies the length of time in milliseconds
         for which the CCAP continues to capture and return FFT
         results when in free running mode.
         Sample captures are expected to take a few microseconds so if
         FreeRunDuration is set for longer than a sample capture
         duration the CCAP could potentially capture more sample data
         than it can store.
         
         On initiation of the Capture Upstream Spectrum test (i.e., free run mode)
         the CCAP should start a free run duration timer as configured to 
         bound the test duration.

         The CCAP rejects an attempt to set FreeRunDuration to a
         value less than  the current value of RepeatPeriod."
     REFERENCE
        "Information Model Mapping: CM-SM-CCAP-OSSI 
         UsTriggeredSpectrumCaptureCfg::FreeRunDuration"
     DEFVAL { 1000 }
     ::= { docsPnmCmtsUtscCfgEntry 19 }

docsPnmCmtsUtscCfgTriggerCount OBJECT-TYPE
     SYNTAX      Unsigned32
     MAX-ACCESS  read-create
     STATUS      current
     DESCRIPTION
        "This attribute determines the number of times to trigger
         upstream spectrum sample capture when InitiateTest
         is set to true and configured trigger conditions are met.
         The CCAP triggers upstream spectrum sample capture
         continuously when the value of TriggerCount is zero."
     REFERENCE
        "Information Model Mapping: CM-SM-CCAP-OSSI 
         UsTriggeredSpectrumCaptureCfg::TriggerCount"
     DEFVAL { 0 }
     ::= { docsPnmCmtsUtscCfgEntry 20 }

docsPnmCmtsUtscCfgStatus OBJECT-TYPE
     SYNTAX      RowStatus
     MAX-ACCESS  read-create
     STATUS      current
     DESCRIPTION
        "The status of this conceptual table row entry."
     ::= { docsPnmCmtsUtscCfgEntry 21 }

docsPnmCmtsUtscCfgBurstIuc OBJECT-TYPE
     SYNTAX      INTEGER {
                         other(1),
                         iuc1(2),
                         iuc2(3),
                         iuc3(4),
                         iuc4(5),
                         iuc5(6),
                         iuc6(7),
                         iuc9(8),
                         iuc10(9),
                         iuc11(10),
                         iuc12(11),
                         iuc13(12)
                         }
     MAX-ACCESS  read-create
     STATUS      current
     DESCRIPTION
        "This attribute configures the desired BurstIuc when the
         TriggerMode attribute is configured for burstIuc(8).
         IUCs that can be used include any request, station
         maintenance, initial maintenance, or data grant defined
         in [MULPI3.1]."
     REFERENCE
        "Information Model Mapping: CM-SM-CCAP-OSSI 
         UsTriggeredSpectrumCaptureCfg::BurstIuc"
     DEFVAL { other }
     ::= { docsPnmCmtsUtscCfgEntry 22 }
     
docsPnmCmtsUtscCfgMaxResultsPerFile OBJECT-TYPE
     SYNTAX      Unsigned32
     MAX-ACCESS  read-create
     STATUS      current
     DESCRIPTION
        "This attribute configures the maximum number of 
         capture result sets that the CCAP is allowed to 
         store in a capture file. When this attribute is 
         set to a non-zero value, the CCAP limits the number
         of capture result sets per file and creates partial
         capture result files. 
         During data capture, when the the number of result sets
         stored in a file reaches the value of MaxResultsPerFile,
         then the CCAP stops depositing results into the current file,
         makes the current file with partial results available for 
         immediate upload and starts depositing capture results into
         the next file. This process iterates until the upstream triggered
         spectrum capture is stopped.
         The format of the partial result file does not differ from the 
         format of a file with complete results.
         The value zero means that there is no administratively configured
         limit on the number of capture results in the capture file. 
         The maximum supported value for this attribute is left to vendor choice.
         When the filename is configured via 'Filename' attribute, in order
         to disambiguate multiple partial files, the CCAP appends '_' character
         and timestamp string to the configured string resulting in the 
         following format: Filename_<Timestamp>. "
      REFERENCE
        "Information Model Mapping: CM-SM-CCAP-OSSI 
         UsTriggeredSpectrumCaptureCfg::MaxResultsPerFile"
     DEFVAL { 0 }
     ::= { docsPnmCmtsUtscCfgEntry 23 }
     
docsPnmCmtsUtscCfgDestinationIndex OBJECT-TYPE
     SYNTAX      Unsigned32 
     MAX-ACCESS  read-write
     STATUS      current
     DESCRIPTION
        "This attribute allows the operator to optionally define a destination
        for the result file or files to be sent when they are available.  
        If this attribute is left empty, the device will create a local file 
        or files for the results. If the attribute has a value, the device uses 
        the instance in the DataTransferCfg defined by the DestinationIndex to 
        determine how to handle the results file or files."
     REFERENCE 
        "Information Model Mapping: CM-SP-CCAP-OSSI 
         UsTriggeredSpectrumCaptureCfg::DestinationIndex"
     ::= { docsPnmCmtsUtscCfgEntry 24 }


-- ---------------------------------------------------------------------
-- The CMTS Upstream Triggered Spectrum Capture Control Table
-- ---------------------------------------------------------------------
docsPnmCmtsUtscCtrlTable OBJECT-TYPE
     SYNTAX      SEQUENCE OF DocsPnmCmtsUtscCtrlEntry
     MAX-ACCESS  not-accessible
     STATUS      current
     DESCRIPTION
        "The Upstream Triggered Spectrum Capture Control table provides 
         command and control functionality for the Upstream Triggered 
         Spectrum Capture function. 
         This table supports the creation and deletion of multiple rows. 
         Rows are created and, or deleted when the corresponding
         UsTriggeredSpectrumCaptureCfg rows are created. The CCAP is not required
         persist rows in this table across reinitializations."
     REFERENCE
         "Information Model Mapping: CM-SP-CCAP-OSSI    
          UsTriggeredSpectrumCaptureCtrl"
     ::= { docsPnmCmtsUtscObjects 3 }

docsPnmCmtsUtscCtrlEntry OBJECT-TYPE
     SYNTAX      DocsPnmCmtsUtscCtrlEntry
     MAX-ACCESS  not-accessible
     STATUS      current
     DESCRIPTION
         "The conceptual row of the docsPnmCmtsUtscCtrlTable.
          The conceptual rows do not persist across device resets.
          A separate entry exists for every Upstream RF Port
          which supports the capability.
          This table supports the creation and deletion of at least one
          instance. Instances are created and/or deleted when the
          corresponding UsTriggeredSpectrumCaptureCfg object instances
          are instantiated."
     INDEX { ifIndex,
             docsPnmCmtsUtscCfgIndex }
     ::= { docsPnmCmtsUtscCtrlTable 1 }

DocsPnmCmtsUtscCtrlEntry ::=
    SEQUENCE {
        docsPnmCmtsUtscCtrlInitiateTest          TruthValue
        }

docsPnmCmtsUtscCtrlInitiateTest OBJECT-TYPE
     SYNTAX      TruthValue
     MAX-ACCESS  read-write
     STATUS      current
     DESCRIPTION
        "This attribute is used to trigger an Upstream Triggered
         Spectrum Capture. Setting this attribute to true applies
         all configured upstream triggered spectrum sample capture
         attributes and initiates the triggered upstream spectrum sample
         capture and sample output conversion process.
         Read-write attributes, which are used to configure the Upstream
         Triggered Spectrum Capture, can only be configured while a test
         is not in progress.
         The CCAP rejects any attempt to modify a
         UsTriggeredSpectrumCaptureCfg table attribute, or
         UsTriggeredSpectrumCaptureCtrl table attribute for the same
         instance of InitiateTest configured to true when the triggered
         spectrum capture is in progress as indicated by value 'busy'
         for MeasStatus.

         The CCAP allows writable UsTriggeredSpectrumCaptureCfg
         table attributes, or UsTriggeredSpectrumCaptureCtrl table
         attributes to be modified if the value of attribute MeasStatus
         for the instance is not 'busy'.
         The CCAP initiates an upstream triggered spectrum sample capture
         only if InitiateTest is set to
         true and all of the UsTriggeredSpectrumCaptureCfg configuration
         attributes are properly configured. Refer to section 7.3.4.1.6 and
         Table 1 of the Reference.
         While a test is in progress, this attribute returns the value
         true. Configuring a value of false for this attribute, while a
         test is in progress, will abort the currently executing test.
         If a test is aborted, the result data is discarded."
     REFERENCE
         "Information Model Mapping: CM-SP-CCAP-OSSI    
          UsTriggeredSpectrumCaptureCtrl::InitiateTest"
     ::= { docsPnmCmtsUtscCtrlEntry 1 }

-- ---------------------------------------------------------------------
-- The CMTS Upstream Triggered Spectrum Capture Status Table
-- ---------------------------------------------------------------------
docsPnmCmtsUtscStatusTable OBJECT-TYPE
     SYNTAX      SEQUENCE OF DocsPnmCmtsUtscStatusEntry
     MAX-ACCESS  not-accessible
     STATUS      current
     DESCRIPTION
        "The Upstream Triggered Spectrum Capture Status table provides functionality 
         for monitoring and reporting status of the Upstream Triggered Spectrum 
         Capture function. This table supports the creation and deletion of multiple 
         rows. Rows are created and, or deleted when the corresponding 
         UsTriggeredSpectrumCaptureCfg rows are created.
         The CCAP is not required to persist rows in this table across reinitializations."
     REFERENCE
         "Information Model Mapping: CM-SP-CCAP-OSSI    
          UsTriggeredSpectrumCaptureStatus"
     ::= { docsPnmCmtsUtscObjects 4 }

docsPnmCmtsUtscStatusEntry OBJECT-TYPE
     SYNTAX      DocsPnmCmtsUtscStatusEntry
     MAX-ACCESS  not-accessible
     STATUS      current
     DESCRIPTION
         "The conceptual row of the docsPnmCmtsUtscStatusTable.
          A separate entry exists for every Upstream RF Port
          which supports the capability."
     INDEX { ifIndex,
             docsPnmCmtsUtscCfgIndex }
     ::= { docsPnmCmtsUtscStatusTable 1 }

DocsPnmCmtsUtscStatusEntry ::=
    SEQUENCE {
        docsPnmCmtsUtscStatusMeasStatus             MeasStatusType,
        docsPnmCmtsUtscStatusCalibrationConstantK   Integer32
        }

docsPnmCmtsUtscStatusMeasStatus OBJECT-TYPE
     SYNTAX      MeasStatusType
     MAX-ACCESS  read-only
     STATUS      current
     DESCRIPTION
        "This attribute is used to report the status of the Upstream
         Triggered Spectrum Capture. When the value is
         sampleReady, the CCAP has completed capturing and recording
         samples. The MeasStatus attribute reports value 'busy' when 
         the test is running even after CCAP creates one or more 
         partial capture results files."
     REFERENCE
         "Information Model Mapping: CM-SP-CCAP-OSSI    
          UsTriggeredSpectrumCaptureStatus::MeasStatus"
     ::= { docsPnmCmtsUtscStatusEntry 1 }
     
docsPnmCmtsUtscStatusCalibrationConstantK OBJECT-TYPE
      SYNTAX      Integer32  (-32768..32767)
      UNITS       "HundredthsdB"
      MAX-ACCESS  read-only
      STATUS      current
      DESCRIPTION
        "This attribute is used to report the current value
        of CalibrationConstantK for the given upstream RF Port.
        The Calibration Constant may be affected by configuration 
        changes or other factors. If such changes occur, resulting
        in implied changes in the Calibration Constant, the CCAP
        will take that into account when populating the Calibration
        Constant entry in the file header elements and also updates
        the CalibrationConstantK MIB value. The Calibration Constant
        may be different on different ports. The CCAP maintains the 
        CalibrationConstantK and associated variable parameters which
        would affect the Calibration Constant across resets."
     REFERENCE
         "Information Model Mapping: CM-SP-CCAP-OSSI    
          UsTriggeredSpectrumCaptureStatus::CalibrationConstantK"
     ::= { docsPnmCmtsUtscStatusEntry 2 }

-- ---------------------------------------------------------------------
-- The CMTS Upstream Triggered Spectrum Capture Result Table
-- ---------------------------------------------------------------------
docsPnmCmtsUtscResultTable OBJECT-TYPE
     SYNTAX      SEQUENCE OF DocsPnmCmtsUtscResultEntry
     MAX-ACCESS  not-accessible
     STATUS      current
     DESCRIPTION
        "The Upstream Triggered Spectrum Capture Result table provides functionality 
         for reporting results of the Upstream Triggered Spectrum Capture function.
         This table supports the creation and deletion of multiple 
         rows. Rows are created and, or deleted when the corresponding 
         UsTriggeredSpectrumCaptureCfg rows are created."
     REFERENCE
         "Information Model Mapping: CM-SP-CCAP-OSSI    
          UsTriggeredSpectrumCaptureResult"
     ::= { docsPnmCmtsUtscObjects 5 }

docsPnmCmtsUtscResultEntry OBJECT-TYPE
     SYNTAX      DocsPnmCmtsUtscResultEntry
     MAX-ACCESS  not-accessible
     STATUS      current
     DESCRIPTION
         "The conceptual row of the docsPnmCmtsUtscResultTable.
          The conceptual rows do not persist across device resets.
          A separate entry exists for every Upstream RF Port
          which supports the capability."
     INDEX { ifIndex,
             docsPnmCmtsUtscCfgIndex }
     ::= { docsPnmCmtsUtscResultTable 1 }

DocsPnmCmtsUtscResultEntry ::=
    SEQUENCE {
        docsPnmCmtsUtscResultSampleRate                    Unsigned32,
        docsPnmCmtsUtscResultUsSampleSize                  Unsigned32,
        docsPnmCmtsUtscResultSampleTimestamp               TimeStamp,
        docsPnmCmtsUtscResultResolutionBw                  Unsigned32,
        docsPnmCmtsUtscResultOutput                        OCTET STRING,
        docsPnmCmtsUtscResultCalibrationConstantK          Integer32
        }

docsPnmCmtsUtscResultSampleRate OBJECT-TYPE
     SYNTAX      Unsigned32
     UNITS       "SamplesPerSecond"
     MAX-ACCESS  read-only
     STATUS      current
     DESCRIPTION
        "This attribute reports the FFT sample rate used by the CCAP
         when sampling the upstream spectrum."
     REFERENCE
         "Information Model Mapping: CM-SP-CCAP-OSSI    
          UsTriggeredSpectrumCaptureResult::SampleRate"
     ::= { docsPnmCmtsUtscResultEntry 1 }

docsPnmCmtsUtscResultUsSampleSize OBJECT-TYPE
     SYNTAX      Unsigned32
     UNITS       "Samples"
     MAX-ACCESS  read-only
     STATUS      current
     DESCRIPTION
        "This attribute reports the number of samples collected for FFT.
         The FFT payload size will be the number of samples multiplied
         by the number of bytes per sample as determined by
         OutputFormat. The duration of the FFT sample will be the number
         of samples divided by the sample rate as reported in attribute
         SampleRate."
     REFERENCE
         "Information Model Mapping: CM-SP-CCAP-OSSI    
          UsTriggeredSpectrumCaptureResult::UsSampleSize"
     ::= { docsPnmCmtsUtscResultEntry 2 }

docsPnmCmtsUtscResultSampleTimestamp OBJECT-TYPE
     SYNTAX      TimeStamp
     MAX-ACCESS  read-only
     STATUS      current
     DESCRIPTION
        "This attribute reports the date and time when the FFT sample
         was recorded."
     REFERENCE
         "Information Model Mapping: CM-SP-CCAP-OSSI    
          UsTriggeredSpectrumCaptureResult::SampleTimestamp"
     ::= { docsPnmCmtsUtscResultEntry 3 }

docsPnmCmtsUtscResultResolutionBw OBJECT-TYPE
     SYNTAX      Unsigned32
     UNITS       "Hertz"
     MAX-ACCESS  read-only
     STATUS      current
     DESCRIPTION
        "This attribute reports the resolution bandwidth used when
         samples were collected. The resolution bandwidth is the same
         as the bin spacing for rectangular windowing, is 1.5*bin
         spacing for Hanning window, etc.  The resolution bandwidth
         used by the CCAP is needed in order to obtain an accurate power
         measurement for all signals when both CW and noise-like
         (QAM, OFDM) signals are present in the spectrum. Value is in
         Hertz 3 dB below the filter peak."
     REFERENCE
         "Information Model Mapping: CM-SP-CCAP-OSSI    
          UsTriggeredSpectrumCaptureResult::ResolutionBw"
     ::= { docsPnmCmtsUtscResultEntry 4 }

docsPnmCmtsUtscResultOutput OBJECT-TYPE
     SYNTAX      OCTET STRING
     MAX-ACCESS  read-only
     STATUS      current
     DESCRIPTION
        "This attribute returns the upstream spectrum sample capture
         data in hexadecimal format according to the output format
         configured in attribute OutputFormat. Refer to the Reference
         for the format of the sample capture data returned by this
         attribute.
         This attribute provides an alternative to TFTP file transfer
         for reporting sample data. Due to small data sizes for upstream
         captures, this may be a more responsive method for screen
         updates than TFTP file transfer."
     REFERENCE
         "Information Model Mapping: CM-SP-CCAP-OSSI    
          UsTriggeredSpectrumCaptureResult::Output"
     ::= { docsPnmCmtsUtscResultEntry 5 }
      
docsPnmCmtsUtscResultCalibrationConstantK OBJECT-TYPE
      SYNTAX      Integer32  (-32768..32767)
      UNITS       "HundredthsdB"
      MAX-ACCESS  read-only
     STATUS      current
     DESCRIPTION
        "This attribute returns the calibration constant 'K' applied to all
         bins in an upstream spectrum capture, to allow the PNM server to obtain
         the upstream spectrum capture estimate in dBmV for each bin. It is the
         same value returned in the Upstream Triggered Spectrum Capture results
         file but this attribute enables visibility to the calibration constant
         'K' without having to parse a results file.
         
         The Calibration Constant may be affected by configuration changes 
         or other factors. If such changes occur, resulting in implied changes
         in the Calibration Constant, the CCAP will take that into account
         when populating the Calibration Constant entry in the file header
         elements and also updates the CalibrationConstantK MIB value. 
         The Calibration Constant may be different on different ports. 
         The CCAP maintains the CalibrationConstantK and associated variable
         parameters which would affect the Calibration Constant across resets."
     REFERENCE
         "Information Model Mapping: CM-SP-CCAP-OSSI    
          UsTriggeredSpectrumCaptureResult::CalibrationConstantK"
     ::= { docsPnmCmtsUtscResultEntry 6 }

-- ---------------------------------------------------------------------
-- Latency Histogram Report Configuration
-- ---------------------------------------------------------------------

-- Note: It was considered as part of OSSITASK-505 to move these tables to
-- another MIB as they are not part of Proactive Network Maintenance functions, 
-- and they are not correctly appended with docsPnm as other objects in this MIB.
-- However, the Low Latency DOCSIS specification text was added to the same part of
-- the specification as PNM specification text, so the MIB objects were included in
-- DOCS-PNM-MIB. The decision was made to keep these tables in the DOCS-PNM-MIB.

-- ---------------------------------------------------------------------
-- The CM Upstream Latency Histogram Report Configuration
-- ---------------------------------------------------------------------
docsCmLatencyRptCfgTable OBJECT-TYPE
     SYNTAX      SEQUENCE OF DocsCmLatencyRptCfgEntry
     MAX-ACCESS  not-accessible
     STATUS      current
     DESCRIPTION
        "This table provides configuration of the CM upstream latency 
         reporting. This enables the creation of latency report files 
         which consist of a series of latency measurements on a per 
         Service Flow basis over a provisioned period of time. 

        This table will have a row for each ifIndex for the modem."
     REFERENCE
         "Information Model Mapping: CM-SP-CM-OSSI    
          CmLatencyRpt"
     ::= { docsLatencyObjects 1}

docsCmLatencyRptCfgEntry OBJECT-TYPE
     SYNTAX      DocsCmLatencyRptCfgEntry
     MAX-ACCESS  not-accessible
     STATUS      current
     DESCRIPTION
        "The conceptual row of the docsPnmCmLatencyRptCfgTable. An instance
        is dynamically created and exists for an associated ifIndex upon
        which the test defined by this table can take place.

        The conceptual rows do not persist across device resets."
     INDEX { ifIndex }
     ::= { docsCmLatencyRptCfgTable 1 }

DocsCmLatencyRptCfgEntry ::=
    SEQUENCE {
        docsCmLatencyRptCfgSnapshotDuration   Unsigned32,
        docsCmLatencyRptCfgNumSnapshots       Unsigned32,
        docsCmLatencyRptCfgNumFiles           Unsigned32,
        docsCmLatencyRptCfgMeasStatus         MeasStatusType,
        docsCmLatencyRptCfgFileName           SnmpAdminString
     }

docsCmLatencyRptCfgSnapshotDuration OBJECT-TYPE
     SYNTAX      Unsigned32 (1..3600)
     UNITS       "seconds"
     MAX-ACCESS  read-write
     STATUS      current
     DESCRIPTION
        "This attribute represents the measurement duration of service flow
        latency estimates. One row of statistics per service flow is captured
        during this interval."
     REFERENCE
         "Information Model Mapping: CM-SP-CM-OSSI    
          CmLatencyRpt::SnapshotDuration"
     DEFVAL { 60 }
     ::= { docsCmLatencyRptCfgEntry 1 }

docsCmLatencyRptCfgNumSnapshots OBJECT-TYPE
     SYNTAX      Unsigned32 (1..2000)
     MAX-ACCESS  read-write
     STATUS      current
     DESCRIPTION
        "This attribute represents the number of Snapshots batched into a file.
        The total duration represented by the file is the product of the
        SnapshotDuration and NumSnapshots. Two examples follow. 
                  -  If SnapshotDuration is set to 1 second, and NumSnapshots is set to 
                      10, when enabled, the CM returns the latency data samples recorded 
                      once per second over the next 10-sec period. 
                  -  If SnapshotDuration is set to 300 seconds (5 mins), and NumSnapshots
                      is set to 288, when enabled, the CM returns the latency data samples
                      recorded once per 5-minute interval over the next 24-hour period. 
          Certain combinations of SnapshotDuration and NumSnapshots could result
          in an excessive file generation rate or excessive file size. 
          The CM MAY reject CmLatencyRpt attribute settings that cause an excessive
          processing load or resource requirement."
     REFERENCE
         "Information Model Mapping: CM-SP-CM-OSSI    
          CmLatencyRpt::NumSnapshots"
     DEFVAL { 10 }
     ::= { docsCmLatencyRptCfgEntry 2 }

docsCmLatencyRptCfgNumFiles OBJECT-TYPE
     SYNTAX      Unsigned32 (0..255)
     MAX-ACCESS  read-write
     STATUS      current
     DESCRIPTION
        "This attribute represents the number of file uploads to be performed
          as defined below:
          0                 File Generation Disabled
          1 .. 254        Number of files to generate. Counts down from this value to zero    
        The CM generates a latency report file when this value is set to a
        non-zero value.
        255                 Unlimited File Generation

       The CM starts generating a latency report file when this value is 
       set to a non-zero value. The CM closes the current latency report 
       file and decrement NumFiles by 1, when the SnapshotDuration * 
       NumSnapshots period is complete. The CM closes the current 
       latency report file and discontinue file generation if the NumFiles 
       attribute is set to zero or decrements to zero."
     REFERENCE
         "Information Model Mapping: CM-SP-CM-OSSI    
          CmLatencyRpt::NumFiles"
     DEFVAL { 0 }
     ::= { docsCmLatencyRptCfgEntry 3 }

docsCmLatencyRptCfgMeasStatus OBJECT-TYPE
     SYNTAX      MeasStatusType
     MAX-ACCESS  read-only
     STATUS      current
     DESCRIPTION
        "This attribute is used to determine the status of the measurement.
        The enumerated value, 'sampleReady', is not applicable."
     REFERENCE
         "Information Model Mapping: CM-SP-CM-OSSI    
          CmLatencyRpt::MeasStatus"
     ::= { docsCmLatencyRptCfgEntry 4 }

docsCmLatencyRptCfgFileName  OBJECT-TYPE
     SYNTAX      SnmpAdminString (SIZE (0..231))
     MAX-ACCESS  read-write
     STATUS      current
     DESCRIPTION
        "This attribute is the prefix for the name of the file which the
        CM creates to store latency histogram snapshots.

        This value can only be changed while a test is not in progress. An attempt
        to set this value while the value of 'docsCmLatencyRptMeasStatus'
        is 'busy' will return 'inconsistentValue'.

        If the value of this object is the default value (empty string), then
        a default filename value of 'UsLatencySum' will be used.  
        Otherwise, the value set will be used as the filename prefix
        as described below.

        The CM stores the test results in a file with a name consisting of the
        Filename plus the CM MAC Address plus the 'epoch time', using the format 
        <Filename><CM MAC address><epoch>, with underscores between <Filename>
        and <CM MAC address> and <epoch> having significance. The epoch time
        (also known as 'unix time') is defined as the number of seconds that have
        elapsed since midnight Coordinated Universal Time (UTC), Thursday, 1
        January 1970.

        Hence, the default format would be:

            UsLatencySum_<CM MAC address>_<epoch>

            For example: USLatencySum_0010181A2D11_1403405123"
     REFERENCE
         "Information Model Mapping: CM-SP-CM-OSSI    
          CmLatencyRpt::FileName"
     DEFVAL { "" }
     ::= { docsCmLatencyRptCfgEntry 5 }

-- ---------------------------------------------------------------------
-- The CMTS Downstream Latency Histogram Report Configuration
-- ---------------------------------------------------------------------
docsCmtsLatencyRptCfgTable OBJECT-TYPE
     SYNTAX      SEQUENCE OF DocsCmtsLatencyRptCfgEntry
     MAX-ACCESS  not-accessible
     STATUS      current
     DESCRIPTION
        "This table provides configuration attributes for CMTS downstream latency
        reporting. This enables the creation of latency report files which consist 
        of a series of latency measurements on a per Service Flow basis 
        over a provisioned period of time.

        This table will have a row for each CM."
     REFERENCE
         "Information Model Mapping: CM-SP-CCAP-OSSI    
          CmtsLatencyRpt"
     ::= { docsLatencyObjects 2}

docsCmtsLatencyRptCfgEntry OBJECT-TYPE
     SYNTAX      DocsCmtsLatencyRptCfgEntry
     MAX-ACCESS  not-accessible
     STATUS      current
     DESCRIPTION
        "The conceptual row of the docsCmtsLatencyRptCfgTable. An instance
        is dynamically created and exists for an associated ifIndex upon
        which the test defined by this table can take place. ifIndex
        represents an identifier assigned to the MAC Domain in which the
        cable modem associated with attribute CmMac is registered.

        The conceptual rows do not persist across device resets."
     INDEX { ifIndex,
             docsCmtsLatencyRptCfgCmMac
           }
     ::= { docsCmtsLatencyRptCfgTable 1 }

DocsCmtsLatencyRptCfgEntry ::=
    SEQUENCE {
        docsCmtsLatencyRptCfgCmMac              MacAddress,
        docsCmtsLatencyRptCfgSnapshotDuration   Unsigned32,
        docsCmtsLatencyRptCfgNumSnapshots       Unsigned32,
        docsCmtsLatencyRptCfgNumFiles           Unsigned32,
        docsCmtsLatencyRptCfgMeasStatus         MeasStatusType,
        docsCmtsLatencyRptCfgFileName           SnmpAdminString,
        docsCmtsLatencyRptCfgDestinationIndex   Unsigned32
     }

docsCmtsLatencyRptCfgCmMac OBJECT-TYPE
     SYNTAX      MacAddress
     MAX-ACCESS  not-accessible
     STATUS      current
     DESCRIPTION
        "This key represents the MAC address of the CM for which
        the CMTS will generate downstream QueueLatency Report(s)."
     REFERENCE
         "Information Model Mapping: CM-SP-CCAP-OSSI    
          CmtsLatencyRpt::CmMac"
     ::= { docsCmtsLatencyRptCfgEntry 1 }

docsCmtsLatencyRptCfgSnapshotDuration OBJECT-TYPE
     SYNTAX      Unsigned32 (1..3600)
     UNITS       "seconds"
     MAX-ACCESS  read-write
     STATUS      current
     DESCRIPTION
        "This attribute represents the measurement duration of service flow
        latency estimates. One row of statistics per service flow is captured
        during this interval."
     REFERENCE
         "Information Model Mapping: CM-SP-CCAP-OSSI    
          CmtsLatencyRpt::SnapshotDuration"
     DEFVAL { 60 }
     ::= { docsCmtsLatencyRptCfgEntry 2 }

docsCmtsLatencyRptCfgNumSnapshots OBJECT-TYPE
     SYNTAX      Unsigned32 (1..2000)
     MAX-ACCESS  read-write
     STATUS      current
     DESCRIPTION
        "This attribute represents the number of Snapshots batched into a file.
        The total duration represented by the file is the product of the
        SnapshotDuration and NumSnapshots."
     REFERENCE
         "Information Model Mapping: CM-SP-CCAP-OSSI    
          CmtsLatencyRpt::NumSnapshots"
     DEFVAL { 10 }
     ::= { docsCmtsLatencyRptCfgEntry 3 }

docsCmtsLatencyRptCfgNumFiles OBJECT-TYPE
     SYNTAX      Unsigned32 (0..255)
     MAX-ACCESS  read-write
     STATUS      current
     DESCRIPTION
        "This attribute represents the number of file uploads to be performed.
        The CMTS generates a latency report file when this value is set to a
        non-zero value.

        The CMTS closes the current latency report file and decrements the value
        of this object by 1, when the 'docsCmtsLatencyRptCfgSnapshotDuration' *
        'docsCmtsLatencyRptCfgNumSnapshots' period is complete.

        The CMTS closes the current latency report file and discontinue 
        file generation if the NumFiles attribute is set to zero or decrements
        to zero or if the CM deregisters.        
        
        The CMTS performs unlimited file generation if the value of this object
        is set to 255."
     REFERENCE
         "Information Model Mapping: CM-SP-CCAP-OSSI    
          CmtsLatencyRpt::NumFiles"
     DEFVAL { 0 }
     ::= { docsCmtsLatencyRptCfgEntry 4 }

docsCmtsLatencyRptCfgMeasStatus OBJECT-TYPE
     SYNTAX      MeasStatusType
     MAX-ACCESS  read-only
     STATUS      current
     DESCRIPTION
        "This attribute is used to determine the status of the measurement."
     REFERENCE
         "Information Model Mapping: CM-SP-CCAP-OSSI    
          CmtsLatencyRpt::MeasStatus"
     ::= { docsCmtsLatencyRptCfgEntry 5 }

docsCmtsLatencyRptCfgFileName  OBJECT-TYPE
     SYNTAX      SnmpAdminString (SIZE (0..231))
     MAX-ACCESS  read-write
     STATUS      current
     DESCRIPTION
        "This attribute is the prefix for the name of the file which the
        CMTS creates to store latency histogram snapshots.

        This value can only be changed while a test is not in progress. An attempt
        to set this value while the value of 'docsCmtsLatencyRptCfgMeasStatus'
        is 'busy' will return 'inconsistentValue'.

        If the value of this object is the default value (empty string), then
        a default filename 'DsLatencySum' will be used. Otherwise, the value set will
        be used as the filename prefix as described below.

        The CMTS stores the test results in a file with a name consisting
        of the FileName plus the CM MAC Address plus the 'epoch time'
        using the format <FileName><CM MAC address><epoch>. 
        The epoch time (also known as 'unix time') is defined as the number 
        of seconds that have elapsed since midnight Coordinated Universal Time 
        (UTC), Thursday, 1 January 1970. 
          
       Hence, the default format would be:
             DsLatencySum_<CM MAC address>_<epoch>
             For example: DSLatencySum_0010181A2D11_1403405123 "
     REFERENCE
         "Information Model Mapping: CM-SP-CCAP-OSSI    
          CmtsLatencyRpt::Filename"
     ::= { docsCmtsLatencyRptCfgEntry 6 }
     
     docsCmtsLatencyRptCfgDestinationIndex  OBJECT-TYPE
     SYNTAX      Unsigned32 (1..4294967295)
     MAX-ACCESS  read-write
     STATUS      current
     DESCRIPTION
        "This attribute is the index of the configured
        destination for the file upload."
     REFERENCE
         "Information Model Mapping: CM-SP-CCAP-OSSI    
          CmtsLatencyRpt::DestinationIndex"
     ::= { docsCmtsLatencyRptCfgEntry 7 }
-- ---------------------------------------------------------------------
-- Notification Objects
-- ---------------------------------------------------------------------
-- ---------------------------------------------------------
-- PNM Notifications
-- ---------------------------------------------------------
    


-- ---------------------------------------------------------------------
-- Compliance Statements
-- ---------------------------------------------------------------------

docsPnmCmtsCompliance MODULE-COMPLIANCE
     STATUS      current
     DESCRIPTION
        "The compliance statement for the CMTS."

    MODULE -- this MODULE
MANDATORY-GROUPS {
     docsPnmCmtsGroup,
     docsCcapFileTransferGroup,
     docsLatencyGroup 
     }
::= { docsPnmMibCompliances 1 }

docsPnmCmCompliance MODULE-COMPLIANCE
    STATUS      current
    DESCRIPTION
        "The compliance statement for the CM."

    MODULE -- this MODULE
MANDATORY-GROUPS {
     docsPnmBulkDataGroup,
     docsPnmCmGroup,
     docsLatencyGroup
     }
::= { docsPnmMibCompliances 2 }

docsPnmCmtsDeprecatedCompliance MODULE-COMPLIANCE
    STATUS      deprecated
    DESCRIPTION
        "The compliance statement for deprecated objects."

    MODULE -- this MODULE
    GROUP docsPnmCmtsDeprecatedGroup
    DESCRIPTION
        "This group contains objects which are deprecated
         from the MIB as of the current release."
    GROUP docsPnmCcapBulkDataGroup
    DESCRIPTION
        "This group contains Ccap bulk data objects which are
          deprecated from the MIB as of the current release."
::= { docsPnmMibCompliances 3 }
--
-- Compliance Groups
--

docsPnmBulkDataGroup OBJECT-GROUP
    OBJECTS {
        docsPnmBulkDestIpAddrType,
        docsPnmBulkDestIpAddr,
        docsPnmBulkDestPath,
        docsPnmBulkUploadControl,

        docsPnmBulkFileName,
        docsPnmBulkFileControl,
        docsPnmBulkFileUploadStatus
     }
    STATUS      current
    DESCRIPTION
         "Group of objects implemented for CM Bulk-Data support"
    ::= { docsPnmMibGroups 1 }


docsPnmCmtsGroup OBJECT-GROUP
    OBJECTS {
        docsPnmCmtsDsOfdmSymTrigEnable,
        docsPnmCmtsDsOfdmSymTrigGroupId,
        docsPnmCmtsDsOfdmSymFirstActSubCarIdx,
        docsPnmCmtsDsOfdmSymLastActSubCarIdx,
        docsPnmCmtsDsOfdmSymRxWindowing,
        docsPnmCmtsDsOfdmSymTransactionId,
        docsPnmCmtsDsOfdmSymSampleRate,
        docsPnmCmtsDsOfdmSymFftLength,
        docsPnmCmtsDsOfdmSymMeasStatus,
        docsPnmCmtsDsOfdmSymCaptFileName,
        docsPnmCmtsDsOfdmSymDestinationIndex,

        docsPnmCmtsDsOfdmNprStartSubcar,
        docsPnmCmtsDsOfdmNprStopSubcar,
        docsPnmCmtsDsOfdmNprEnable,
        docsPnmCmtsDsOfdmNprDuration,

        docsPnmCmtsUsOfdmaAQProbeCmMacAddr,
        docsPnmCmtsUsOfdmaAQProbeUseIdleSid,
        docsPnmCmtsUsOfdmaAQProbePreEqOn,
        docsPnmCmtsUsOfdmaAQProbeEnable,
        docsPnmCmtsUsOfdmaAQProbeTimeout,
        docsPnmCmtsUsOfdmaAQProbeNumSymToCapt,
        docsPnmCmtsUsOfdmaAQProbeMaxCaptSymbols,
        docsPnmCmtsUsOfdmaAQProbeNumSamples,
        docsPnmCmtsUsOfdmaAQProbeTimeStamp,
        docsPnmCmtsUsOfdmaAQProbeMeasStatus,
        docsPnmCmtsUsOfdmaAQProbeFileName,
        docsPnmCmtsUsOfdmaAQProbeFreqDomainSamples,
        docsPnmCmtsUsOfdmaAQProbeDestinationIndex,

        docsPnmCmtsUsImpNoiseEnable,
        docsPnmCmtsUsImpNoiseFreeRunDuration,
        docsPnmCmtsUsImpNoiseStTrigLvl,
        docsPnmCmtsUsImpNoiseEndTrigLvl,
        docsPnmCmtsUsImpNoiseCenterFrq,
        docsPnmCmtsUsImpNoiseMeasBw,
        docsPnmCmtsUsImpNoiseNumEvtsCnted,
        docsPnmCmtsUsImpNoiseLastEvtTimeStamp,
        docsPnmCmtsUsImpNoiseLastEvtDuration,
        docsPnmCmtsUsImpNoiseLastEvtAvgPwr,
        docsPnmCmtsUsImpNoiseMeasStatus,
        docsPnmCmtsUsImpNoiseFileName,
        docsPnmCmtsUsImpNoiseDestinationIndex,

        docsPnmCmtsUsHistEnable,
        docsPnmCmtsUsHistTimeOut,
        docsPnmCmtsUsHistMeasStatus,
        docsPnmCmtsUsHistFileName,
        docsPnmCmtsUsHistDestinationIndex,

        docsPnmCmtsUsOfdmaRxPwrEnable,
        docsPnmCmtsUsOfdmaRxPwrPreEq,
        docsPnmCmtsUsOfdmaRxPwrNumAvgs,
        docsPnmCmtsUsOfdmaRxPwrOnePtSixPsd,
        docsPnmCmtsUsOfdmaRxPwrMeasStatus,

        docsPnmCmtsUsOfdmaRxMerEnable,
        docsPnmCmtsUsOfdmaRxMerCmMac,
        docsPnmCmtsUsOfdmaRxMerPreEq,
        docsPnmCmtsUsOfdmaRxMerNumAvgs,
        docsPnmCmtsUsOfdmaRxMerMeasStatus,
        docsPnmCmtsUsOfdmaRxMerFileName,
        docsPnmCmtsUsOfdmaRxMerDestinationIndex,

        docsPnmCmtsOptReqOpCode,
        docsPnmCmtsOptReqProfileTest,
        docsPnmCmtsOptReqMaxDuration,
        docsPnmCmtsOptReqMaxCodewords,
        docsPnmCmtsOptReqMaxUncorrectableCws,
        docsPnmCmtsOptReqCwTaggingEnabled,
        docsPnmCmtsOptReqNcpFields,
        docsPnmCmtsOptReqMaxNcpCrcFails,
        docsPnmCmtsOptReqStatus,
        docsPnmCmtsOptReqMerThreshTemplateIndex,

        docsPnmCmtsOptMerThreshTemplateRxMerVsBitloadingTarget,
        docsPnmCmtsOptMerThreshTemplateRxMerMargin,
        docsPnmCmtsOptMerThreshTemplateStatus,

        docsPnmCmtsOptProfChgCfgDsProfList,
        docsPnmCmtsOptProfChgCfgStatus,

        docsPnmCmtsOptRespStatus,
        docsPnmCmtsOptRespFirstActiveSubcarrierNum,
        docsPnmCmtsOptRespMerData,
        docsPnmCmtsOptRespMerPassFailData,
        docsPnmCmtsOptRespNumSubcarriersBelowThresh,
        docsPnmCmtsOptRespSnrMarginData,
        docsPnmCmtsOptRespCodewordCt,
        docsPnmCmtsOptRespCorrectedCodewordCt,
        docsPnmCmtsOptRespUncorrectableCodewordCt,
        docsPnmCmtsOptRespNcpFieldCt,
        docsPnmCmtsOptRespNcpCrcFailCt,

        docsPnmCmtsUtscCapabTriggerMode,
        docsPnmCmtsUtscCapabOutputFormat,
        docsPnmCmtsUtscCapabWindow,
        docsPnmCmtsUtscCapabDescription,

        docsPnmCmtsUtscCfgLogicalChIfIndex,
        docsPnmCmtsUtscCfgTriggerMode,
        docsPnmCmtsUtscCfgMinislotCount,
        docsPnmCmtsUtscCfgSid,
        docsPnmCmtsUtscCfgCmMacAddr,
        docsPnmCmtsUtscCfgTimestamp,
        docsPnmCmtsUtscCfgCenterFreq,
        docsPnmCmtsUtscCfgSpan,
        docsPnmCmtsUtscCfgNumBins,
        docsPnmCmtsUtscCfgAveraging,
        docsPnmCmtsUtscCfgFilename,
        docsPnmCmtsUtscCfgQualifyCenterFreq,
        docsPnmCmtsUtscCfgQualifyBw,
        docsPnmCmtsUtscCfgQualifyThrshld,
        docsPnmCmtsUtscCfgWindow,
        docsPnmCmtsUtscCfgOutputFormat,
        docsPnmCmtsUtscCfgRepeatPeriod,
        docsPnmCmtsUtscCfgFreeRunDuration,
        docsPnmCmtsUtscCfgTriggerCount,
        docsPnmCmtsUtscCfgStatus,
        docsPnmCmtsUtscCfgBurstIuc,
        docsPnmCmtsUtscCfgMaxResultsPerFile,
        docsPnmCmtsUtscCfgDestinationIndex,

        docsPnmCmtsUtscCtrlInitiateTest,

        docsPnmCmtsUtscStatusMeasStatus,
        docsPnmCmtsUtscStatusCalibrationConstantK,

        docsPnmCmtsUtscResultSampleRate,
        docsPnmCmtsUtscResultUsSampleSize,
        docsPnmCmtsUtscResultSampleTimestamp,
        docsPnmCmtsUtscResultResolutionBw,
        docsPnmCmtsUtscResultOutput,
        docsPnmCmtsUtscResultCalibrationConstantK
     }
    STATUS      current
    DESCRIPTION
         "Group of objects implemented in the CMTS"
    ::= { docsPnmMibGroups 2 }

docsPnmCmGroup OBJECT-GROUP
    OBJECTS {
        docsPnmCmCtlTest,
        docsPnmCmCtlTestDuration,
        docsPnmCmCtlStatus,

        docsPnmCmDsOfdmSymTrigEnable,
        docsPnmCmDsOfdmSymTrigEnableTimeout,
        docsPnmCmDsOfdmSymTrigGroupId,
        docsPnmCmDsOfdmSymRxWindowing,
        docsPnmCmDsOfdmSymTransactionId,
        docsPnmCmDsOfdmSymSampleRate,
        docsPnmCmDsOfdmSymFftLength,
        docsPnmCmDsOfdmSymMeasStatus,
        docsPnmCmDsOfdmSymCaptFileName,

        docsPnmCmOfdmChEstCoefTrigEnable,
        docsPnmCmOfdmChEstCoefAmpRipplePkToPk,
        docsPnmCmOfdmChEstCoefAmpRippleRms,
        docsPnmCmOfdmChEstCoefAmpSlope,
        docsPnmCmOfdmChEstCoefGrpDelayRipplePkToPk,
        docsPnmCmOfdmChEstCoefGrpDelayRippleRms,
        docsPnmCmOfdmChEstCoefMeasStatus,
        docsPnmCmOfdmChEstCoefFileName,
        docsPnmCmOfdmChEstCoefAmpMean,
        docsPnmCmOfdmChEstCoefGrpDelaySlope,
        docsPnmCmOfdmChEstCoefGrpDelayMean,
        docsPnmCmDsOfdmModProfFileEnable,
        docsPnmCmDsOfdmModProfMeasStatus,
        docsPnmCmDsOfdmModProfFileName,

        docsPnmCmDsConstDispTrigEnable,
        docsPnmCmDsConstDispModOrderOffset,
        docsPnmCmDsConstDispNumSampleSymb,
        docsPnmCmDsConstDispSelModOrder,
        docsPnmCmDsConstDispMeasStatus,
        docsPnmCmDsConstDispFileName,

        docsPnmCmDsOfdmRxMerFileEnable,
        docsPnmCmDsOfdmRxMerPercentile,
        docsPnmCmDsOfdmRxMerMean,
        docsPnmCmDsOfdmRxMerStdDev,
        docsPnmCmDsOfdmRxMerThrVal,
        docsPnmCmDsOfdmRxMerThrHighestFreq,
        docsPnmCmDsOfdmRxMerMeasStatus,
        docsPnmCmDsOfdmRxMerFileName,

        docsPnmCmDsOfdmMerMarProfileId,
        docsPnmCmDsOfdmMerMarThrshldOffset,
        docsPnmCmDsOfdmMerMarMeasEnable,
        docsPnmCmDsOfdmMerMarNumSymPerSubCarToAvg,
        docsPnmCmDsOfdmMerMarReqAvgMer,
        docsPnmCmDsOfdmMerMarNumSubCarBelowThrshld,
        docsPnmCmDsOfdmMerMarMeasStatus,
        docsPnmCmDsOfdmMerMarMeasuredAvgMer,
        docsPnmCmDsOfdmMerMarAvgMerMargin,

        docsPnmCmDsOfdmFecSumType,
        docsPnmCmDsOfdmFecFileEnable,
        docsPnmCmDsOfdmFecMeasStatus,
        docsPnmCmDsOfdmFecFileName,

        docsPnmCmDsOfdmReqMerQam16,
        docsPnmCmDsOfdmReqMerQam64,
        docsPnmCmDsOfdmReqMerQam128,
        docsPnmCmDsOfdmReqMerQam256,
        docsPnmCmDsOfdmReqMerQam512,
        docsPnmCmDsOfdmReqMerQam1024,
        docsPnmCmDsOfdmReqMerQam2048,
        docsPnmCmDsOfdmReqMerQam4096,
        docsPnmCmDsOfdmReqMerQam8192,
        docsPnmCmDsOfdmReqMerQam16384,

        docsPnmCmDsHistEnable,
        docsPnmCmDsHistTimeOut,
        docsPnmCmDsHistMeasStatus,
        docsPnmCmDsHistFileName,

        docsPnmCmUsPreEqFileEnable,
        docsPnmCmUsPreEqAmpRipplePkToPk,
        docsPnmCmUsPreEqAmpRippleRms,
        docsPnmCmUsPreEqAmpSlope,
        docsPnmCmUsPreEqGrpDelayRipplePkToPk,
        docsPnmCmUsPreEqGrpDelayRippleRms,
        docsPnmCmUsPreEqPreEqCoAdjStatus,
        docsPnmCmUsPreEqMeasStatus,
        docsPnmCmUsPreEqLastUpdateFileName,
        docsPnmCmUsPreEqFileName,
        docsPnmCmUsPreEqAmpMean,
        docsPnmCmUsPreEqGrpDelaySlope,
        docsPnmCmUsPreEqGrpDelayMean,

        docsIf3CmSpectrumAnalysisCtrlCmdFileEnable,
        docsIf3CmSpectrumAnalysisCtrlCmdMeasStatus,
        docsIf3CmSpectrumAnalysisCtrlCmdFileName
     }
    STATUS      current
    DESCRIPTION
         "Group of objects implemented in the CM"
    ::= { docsPnmMibGroups 3 }

docsPnmCmtsDeprecatedGroup OBJECT-GROUP
    OBJECTS {
        docsPnmCmtsUsSpecAnEnable,
        docsPnmCmtsUsSpecAnTrigMode,
        docsPnmCmtsUsSpecAnMiniSlotCnt,
        docsPnmCmtsUsSpecAnSid,
        docsPnmCmtsUsSpecAnMiniSlotNum,
        docsPnmCmtsUsSpecAnCmMac,
        docsPnmCmtsUsSpecAnCenterFreq,
        docsPnmCmtsUsSpecAnSpan,
        docsPnmCmtsUsSpecAnNumberOfBins,
        docsPnmCmtsUsSpecAnMeasStatus,
        docsPnmCmtsUsSpecAnFileName,
        docsPnmCmtsOptMerThreshCfgRxMerVsBitloadingTarget,
        docsPnmCmtsOptMerThreshCfgRxMerMargin,
        docsPnmCmtsOptMerThreshCfgStatus,
        docsPnmCcapBulkDataControlDestIpAddrType,
        docsPnmCcapBulkDataControlDestIpAddr,
        docsPnmCcapBulkDataControlDestPath,
        docsPnmCcapBulkDataControlUploadControl,
        docsPnmCcapBulkDataControlPnmTestSelector
     }
    STATUS      deprecated
    DESCRIPTION
         "Deprecated Objects implemented in the CMTS"
    ::= { docsPnmMibGroups 4 }
    
docsPnmCcapBulkDataGroup OBJECT-GROUP
    OBJECTS {
        docsPnmCcapBulkDataControlDestIpAddrType,
        docsPnmCcapBulkDataControlDestIpAddr,
        docsPnmCcapBulkDataControlDestPath,
        docsPnmCcapBulkDataControlUploadControl,
        docsPnmCcapBulkDataControlPnmTestSelector,

        docsPnmBulkFileName,
        docsPnmBulkFileControl,
        docsPnmBulkFileUploadStatus

     }
    STATUS      deprecated
    DESCRIPTION
         "Group of objects implemented for CCAP Bulk-Data support"
    ::= { docsPnmMibGroups 5 }


docsLatencyGroup OBJECT-GROUP
    OBJECTS {
        docsCmtsLatencyRptCfgSnapshotDuration,
        docsCmtsLatencyRptCfgNumSnapshots,
        docsCmtsLatencyRptCfgNumFiles,
        docsCmtsLatencyRptCfgMeasStatus,
        docsCmtsLatencyRptCfgFileName,
        docsCmtsLatencyRptCfgDestinationIndex,

        docsCmLatencyRptCfgSnapshotDuration,
        docsCmLatencyRptCfgNumSnapshots,
        docsCmLatencyRptCfgNumFiles,
        docsCmLatencyRptCfgMeasStatus,
        docsCmLatencyRptCfgFileName
       }
    STATUS      current
    DESCRIPTION
         "Group of objects implemented for CM and CCAP Latency Reports"
    ::= { docsPnmMibGroups 6 }
    
docsCcapFileTransferGroup OBJECT-GROUP
    OBJECTS {
        docsPnmBulkDataTransferCfgDestHostname,
        docsPnmBulkDataTransferCfgDestHostIpAddrType,
        docsPnmBulkDataTransferCfgDestHostIpAddress,
        docsPnmBulkDataTransferCfgDestPort,
        docsPnmBulkDataTransferCfgDestBaseUri,
        docsPnmBulkDataTransferCfgProtocol,
        docsPnmBulkDataTransferCfgLocalStore,
        docsPnmBulkDataTransferCfgRowStatus,
        
        docsPnmBulkFileStatusLocalFilename,
        docsPnmBulkFileStatusFileStatus,
        docsPnmBulkFileStatusDateCreated,

        docsPnmBulkFileMgmtControl,
        docsPnmBulkFileMgmtDestIndex,
        docsPnmBulkFileMgmtDeleteFile         
        }
    STATUS      current
    DESCRIPTION
         "Group of objects implemented for CCAP Bulk File Transfer "
    ::= { docsPnmMibGroups 7}

END
